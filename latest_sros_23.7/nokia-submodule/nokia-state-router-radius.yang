submodule nokia-state-router-radius {

    yang-version "1.1";

    belongs-to nokia-state { prefix "state"; }

    import ietf-yang-types                { prefix "yang"; }
    import nokia-sros-yang-extensions     { prefix "sros-ext"; }
    import nokia-types-nat                { prefix "types-nat"; }
    import nokia-types-sros               { prefix "types-sros"; }

    sros-ext:sros-major-release "rel23";
    organization "Nokia";
    contact
        "Nokia SR OS Support
         Web: <http://www.nokia.com>";
    description
        "Nokia YANG Data model with operational state for RADIUS on SR OS based routers.

         Copyright 2016 Nokia. All rights reserved. Reproduction of this document
         is authorized on the condition that the foregoing copyright notice is included.

         This nokia-state-router-radius YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-router-radius {
        ///nokia-state/state/router/radius
        container radius {
            description "Enter the radius context";

            ///nokia-state/state/router/radius/proxy
            list proxy {
                key "name";
                description "Enter the proxy list instance";

                ///nokia-state/state/router/radius/proxy/name
                leaf name {
                    type types-sros:named-item;
                    description "RADIUS proxy name";
                }

                ///nokia-state/state/router/radius/proxy/cache
                container cache {
                    description "Enter the cache context";

                    ///nokia-state/state/router/radius/proxy/cache/entries
                    leaf entries {
                        type yang:gauge32;
                        description "Number of entries in the cache of this RADIUS Proxy Server.";
                    }

                    ///nokia-state/state/router/radius/proxy/cache/entries-registered
                    leaf entries-registered {
                        type yang:gauge32;
                        description "Number of RADIUS Proxy Server entries that have been registered by an application";
                    }

                    ///nokia-state/state/router/radius/proxy/cache/entry
                    list entry {
                        key "key";
                        description "Enter the entry list instance";

                        ///nokia-state/state/router/radius/proxy/cache/entry/key
                        leaf key {
                            type binary {
                                length "1..64";
                            }
                            description "The key of this cache entry.";
                        }

                        ///nokia-state/state/router/radius/proxy/cache/entry/age
                        leaf age {
                            type types-sros:time-interval;
                            description "The age of this cache entry.";
                        }

                        ///nokia-state/state/router/radius/proxy/cache/entry/time-left
                        leaf time-left {
                            type types-sros:time-interval;
                            description "The time left for this cache entry.";
                        }

                        ///nokia-state/state/router/radius/proxy/cache/entry/request-length
                        leaf request-length {
                            type uint32;
                            description "The length of the RADIUS Access-Request packet attribute(s) in the cache.";
                        }

                        ///nokia-state/state/router/radius/proxy/cache/entry/accept-length
                        leaf accept-length {
                            type uint32;
                            description "The length of the RADIUS Access-Accept packet attribute(s) in the cache.";
                        }

                        ///nokia-state/state/router/radius/proxy/cache/entry/registered
                        leaf registered {
                            type boolean;
                            description "Indicates if this cache entry is used by an application.";
                        }

                        ///nokia-state/state/router/radius/proxy/cache/entry/nas-address
                        leaf nas-address {
                            type types-sros:ipv4-address;
                            description "The NAS IPv4 address.";
                        }

                        ///nokia-state/state/router/radius/proxy/cache/entry/nas-ipv6-address
                        leaf nas-ipv6-address {
                            type types-sros:ipv6-address;
                            description "The NAS IPv6 address.";
                        }

                        ///nokia-state/state/router/radius/proxy/cache/entry/called-station-id
                        leaf called-station-id {
                            type binary {
                                length "0..64";
                            }
                            description "The Called-Station-Id in the RADIUS message.";
                        }

                    } // list entry

                } // container cache

                ///nokia-state/state/router/radius/proxy/statistics
                container statistics {
                    description "Enter the statistics context";

                    ///nokia-state/state/router/radius/proxy/statistics/rx
                    container rx {
                        description "Enter the rx context";

                        ///nokia-state/state/router/radius/proxy/statistics/rx/access-request
                        leaf access-request {
                            type yang:counter32;
                            description "The number of Access-Request packets received by this RADIUS Proxy Server.";
                        }

                        ///nokia-state/state/router/radius/proxy/statistics/rx/accounting-request
                        leaf accounting-request {
                            type yang:counter32;
                            description "The number of Accounting-Request packets received by this RADIUS Proxy Server.";
                        }

                        ///nokia-state/state/router/radius/proxy/statistics/rx/admin-down
                        leaf admin-down {
                            type yang:counter32;
                            description
                                "The number of packets received by this RADIUS Proxy Server
                                 that were rejected because it is administratively shut down.";
                        }

                        ///nokia-state/state/router/radius/proxy/statistics/rx/dropped
                        leaf dropped {
                            type yang:counter32;
                            description "The number of packets received by this RADIUS Proxy Server but rejected.";
                        }

                        ///nokia-state/state/router/radius/proxy/statistics/rx/dropped-by-python
                        leaf dropped-by-python {
                            type yang:counter32;
                            description "The number of packets received by this RADIUS Proxy Server but rejected by Python.";
                        }

                        ///nokia-state/state/router/radius/proxy/statistics/rx/invalid-accounting-status
                        leaf invalid-accounting-status {
                            type yang:counter32;
                            description
                                "The number of accounting packets received by this RADIUS Proxy Server that
                                 were rejected because they contained an invalid Acct-Status-Type attribute.";
                        }

                        ///nokia-state/state/router/radius/proxy/statistics/rx/invalid-attribute
                        leaf invalid-attribute {
                            type yang:counter32;
                            description
                                "The number of packets received by this RADIUS Proxy Server that were rejected
                                 because one of the attributes was incorrectly encoded.";
                        }

                        ///nokia-state/state/router/radius/proxy/statistics/rx/invalid-authenticator
                        leaf invalid-authenticator {
                            type yang:counter32;
                            description
                                "The number of accounting packets received by this RADIUS Proxy Server that
                                 were rejected because they contained an invalid Authenticator field.";
                        }

                        ///nokia-state/state/router/radius/proxy/statistics/rx/invalid-code
                        leaf invalid-code {
                            type yang:counter32;
                            description
                                "The number of packets received by this RADIUS Proxy Server
                                 that were rejected because they had an invalid Code field.";
                        }

                        ///nokia-state/state/router/radius/proxy/statistics/rx/invalid-length
                        leaf invalid-length {
                            type yang:counter32;
                            description
                                "The number of packets received by this RADIUS Proxy Server
                                 that were rejected because their length was invalid.";
                        }

                        ///nokia-state/state/router/radius/proxy/statistics/rx/invalid-message-authenticator
                        leaf invalid-message-authenticator {
                            type yang:counter32;
                            description
                                "The number of packets received by this RADIUS Proxy Server that were rejected
                                 because they contained an invalid Message-Authenticator attribute.";
                        }

                        ///nokia-state/state/router/radius/proxy/statistics/rx/invalid-password
                        leaf invalid-password {
                            type yang:counter32;
                            description
                                "The number of packets received by this RADIUS Proxy Server that were rejected
                                 because the User-Password attribute could not be decoded.";
                        }

                        ///nokia-state/state/router/radius/proxy/statistics/rx/invalid-user-name
                        leaf invalid-user-name {
                            type yang:counter32;
                            description
                                "The number of packets received by this RADIUS Proxy Server that were rejected
                                 because they contained an invalid User-Name attribute.";
                        }

                        ///nokia-state/state/router/radius/proxy/statistics/rx/aaa-policy-missing
                        leaf aaa-policy-missing {
                            type yang:counter32;
                            description
                                "The number of packets received by this RADIUS Proxy Server that were rejected
                                 because it has no RADIUS server policy configured for that type of packet.";
                        }

                        ///nokia-state/state/router/radius/proxy/statistics/rx/accounting-status-missing
                        leaf accounting-status-missing {
                            type yang:counter32;
                            description
                                "The number of accounting packets received by this RADIUS Proxy Server that
                                 were rejected because they contained no Acct-Status-Type attribute.";
                        }

                        ///nokia-state/state/router/radius/proxy/statistics/rx/load-balance-key-missing
                        leaf load-balance-key-missing {
                            type yang:counter32;
                            description
                                "The number of packets received by this RADIUS Proxy Server that were rejected
                                 because the selected RADIUS server policy's algorithm is set to 'hash-based'
                                 and no load-balance-key is configured.";
                        }

                        ///nokia-state/state/router/radius/proxy/statistics/rx/out-of-memory
                        leaf out-of-memory {
                            type yang:counter32;
                            description
                                "The number of packets that were rejected by this RADIUS Proxy Server
                                 because there was not enough memory to store them.";
                        }

                        ///nokia-state/state/router/radius/proxy/statistics/rx/packets
                        leaf packets {
                            type yang:counter32;
                            description "The number of packets received by this RADIUS Proxy Server.";
                        }

                        ///nokia-state/state/router/radius/proxy/statistics/rx/retransmit
                        leaf retransmit {
                            type yang:counter32;
                            description
                                "The number of packets received by this RADIUS Proxy Server
                                 that were rejected because they are retransmits.";
                        }

                        ///nokia-state/state/router/radius/proxy/statistics/rx/user-overload
                        leaf user-overload {
                            type yang:counter32;
                            description
                                "The number of packets that were rejected by this RADIUS server
                                 because the registered user indicated to be in overload.";
                        }

                    } // container rx

                    ///nokia-state/state/router/radius/proxy/statistics/tx
                    container tx {
                        description "Enter the tx context";

                        ///nokia-state/state/router/radius/proxy/statistics/tx/access-accept
                        leaf access-accept {
                            type yang:counter32;
                            description "The number of Access-Accept packets transmitted by this RADIUS Proxy Server.";
                        }

                        ///nokia-state/state/router/radius/proxy/statistics/tx/access-reject
                        leaf access-reject {
                            type yang:counter32;
                            description "The number of Access-Reject packets transmitted by this RADIUS Proxy Server.";
                        }

                        ///nokia-state/state/router/radius/proxy/statistics/tx/access-challenge
                        leaf access-challenge {
                            type yang:counter32;
                            description "The number of Access-Challenge packets transmitted by this RADIUS Proxy Server.";
                        }

                        ///nokia-state/state/router/radius/proxy/statistics/tx/accounting-response
                        leaf accounting-response {
                            type yang:counter32;
                            description "The number of Accounting-Response packets transmitted by this RADIUS Proxy Server.";
                        }

                        ///nokia-state/state/router/radius/proxy/statistics/tx/client-dropped-authentication
                        leaf client-dropped-authentication {
                            type yang:counter32;
                            description
                                "The number of packets that were dropped by a client registered for
                                 authentication packets.";
                        }

                        ///nokia-state/state/router/radius/proxy/statistics/tx/dropped
                        leaf dropped {
                            type yang:counter32;
                            description "The number of packets dropped by this RADIUS Proxy Server before transmission.";
                        }

                        ///nokia-state/state/router/radius/proxy/statistics/tx/dropped-by-python
                        leaf dropped-by-python {
                            type yang:counter32;
                            description
                                "The number of packets that were dropped by this RADIUS server
                                 because the packet was rejected by the Python script.";
                        }

                        ///nokia-state/state/router/radius/proxy/statistics/tx/out-of-memory
                        leaf out-of-memory {
                            type yang:counter32;
                            description
                                "The number of packets that could not be transmitted by this RADIUS Proxy Server
                                 because there was not enough memory.";
                        }

                        ///nokia-state/state/router/radius/proxy/statistics/tx/radius-server-missing
                        leaf radius-server-missing {
                            type yang:counter32;
                            description
                                "The number of packets that were dropped by this RADIUS server because
                                 the RADIUS server policy has no servers configured.";
                        }

                        ///nokia-state/state/router/radius/proxy/statistics/tx/send-failure
                        leaf send-failure {
                            type yang:counter32;
                            description
                                "The number of packets that were dropped by this RADIUS server because the packet
                                 could not get transmitted by one of the servers in the RADIUS server policy.";
                        }

                        ///nokia-state/state/router/radius/proxy/statistics/tx/server-authenticator-fail
                        leaf server-authenticator-fail {
                            type yang:counter32;
                            description
                                "The number of client packets that were dropped because the RADIUS server replied
                                 with a packet which failed authentication (invalid response Authenticator
                                 or Message-Authenticator attribute).";
                        }

                        ///nokia-state/state/router/radius/proxy/statistics/tx/server-invalid-attribute
                        leaf server-invalid-attribute {
                            type yang:counter32;
                            description
                                "The number of client packets that were dropped because the RADIUS server
                                 replied with a packet with an invalid attribute.";
                        }

                        ///nokia-state/state/router/radius/proxy/statistics/tx/server-invalid-code
                        leaf server-invalid-code {
                            type yang:counter32;
                            description
                                "The number of client packets that were dropped because the RADIUS server
                                 replied with a packet with an invalid Code field.";
                        }

                        ///nokia-state/state/router/radius/proxy/statistics/tx/server-timeout
                        leaf server-timeout {
                            type yang:counter32;
                            description
                                "The number of client packets that were dropped because the RADIUS servers have
                                 timed out.";
                        }

                        ///nokia-state/state/router/radius/proxy/statistics/tx/user-overload
                        leaf user-overload {
                            type yang:counter32;
                            description
                                "The number of packets that were dropped because the registered
                                 user indicated to be in overload.";
                        }

                        ///nokia-state/state/router/radius/proxy/statistics/tx/cache
                        container cache {
                            description "Enter the cache context";

                            ///nokia-state/state/router/radius/proxy/statistics/tx/cache/attribute-too-long
                            leaf attribute-too-long {
                                type yang:counter32;
                                description
                                    "The number of packets that could not be cached by this RADIUS Proxy Server
                                     because the total length of the attributes is too long.";
                            }

                            ///nokia-state/state/router/radius/proxy/statistics/tx/cache/key-too-long
                            leaf key-too-long {
                                type yang:counter32;
                                description
                                    "The number of packets that could not be cached by this RADIUS Proxy Server
                                     because the key information present in the packet was too long.";
                            }

                            ///nokia-state/state/router/radius/proxy/statistics/tx/cache/max-entries
                            leaf max-entries {
                                type yang:counter32;
                                description
                                    "The number of packets that could not be cached by this RADIUS Proxy Server
                                     because the limit has been reached.";
                            }

                            ///nokia-state/state/router/radius/proxy/statistics/tx/cache/key-missing
                            leaf key-missing {
                                type yang:counter32;
                                description
                                    "The number of packets that could not be cached by this RADIUS Proxy Server
                                     because the key information was not present in the packet.";
                            }

                        } // container cache

                    } // container tx

                    ///nokia-state/state/router/radius/proxy/statistics/group-member
                    list group-member {
                        key "group-id member-id";
                        description "Enter the group-member list instance";

                        ///nokia-state/state/router/radius/proxy/statistics/group-member/group-id
                        leaf group-id {
                            type uint32;
                            description "The identifier of the ISA group.";
                        }

                        ///nokia-state/state/router/radius/proxy/statistics/group-member/member-id
                        leaf member-id {
                            type types-nat:bb-group-member;
                            description "The identifier of the ISA Group member.";
                        }

                        ///nokia-state/state/router/radius/proxy/statistics/group-member/rx
                        container rx {
                            description "Enter the rx context";

                            ///nokia-state/state/router/radius/proxy/statistics/group-member/rx/aaa-policy-missing
                            leaf aaa-policy-missing {
                                type yang:counter32;
                                description
                                    "The number of packets received by this RADIUS Proxy Server that were rejected
                                     because it has no ISA RADIUS server policy configured for that type of packet.";
                            }

                            ///nokia-state/state/router/radius/proxy/statistics/group-member/rx/access-request
                            leaf access-request {
                                type yang:counter32;
                                description "The number of Access-Request packets received by this RADIUS Proxy Server.";
                            }

                            ///nokia-state/state/router/radius/proxy/statistics/group-member/rx/accounting-request
                            leaf accounting-request {
                                type yang:counter32;
                                description "The number of Accounting-Request packets received by this RADIUS Proxy Server.";
                            }

                            ///nokia-state/state/router/radius/proxy/statistics/group-member/rx/accounting-status-missing
                            leaf accounting-status-missing {
                                type yang:counter32;
                                description
                                    "The number of accounting packets received by this RADIUS Proxy Server that
                                     were rejected because they contained no Acct-Status-Type attribute.";
                            }

                            ///nokia-state/state/router/radius/proxy/statistics/group-member/rx/context-limit-reached
                            leaf context-limit-reached {
                                type yang:counter32;
                                description
                                    "The number of packets received by this RADIUS Proxy Server that were rejected
                                     because the limit of client contexts was reached.";
                            }

                            ///nokia-state/state/router/radius/proxy/statistics/group-member/rx/dropped
                            leaf dropped {
                                type yang:counter32;
                                description "The number of packets received by this RADIUS Proxy Server but dropped.";
                            }

                            ///nokia-state/state/router/radius/proxy/statistics/group-member/rx/invalid-accounting-status
                            leaf invalid-accounting-status {
                                type yang:counter32;
                                description
                                    "The number of accounting packets received by this RADIUS Proxy Server that
                                     were rejected because they contained an invalid Acct-Status-Type attribute.";
                            }

                            ///nokia-state/state/router/radius/proxy/statistics/group-member/rx/invalid-attribute
                            leaf invalid-attribute {
                                type yang:counter32;
                                description
                                    "The number of packets received by this RADIUS Proxy Server that were rejected
                                     because one of the attributes was incorrectly encoded.";
                            }

                            ///nokia-state/state/router/radius/proxy/statistics/group-member/rx/invalid-authenticator
                            leaf invalid-authenticator {
                                type yang:counter32;
                                description
                                    "The number of accounting packets received by this RADIUS Proxy Server that
                                     were rejected because they contained an invalid Authenticator field.";
                            }

                            ///nokia-state/state/router/radius/proxy/statistics/group-member/rx/invalid-message-authenticator
                            leaf invalid-message-authenticator {
                                type yang:counter32;
                                description
                                    "The number of packets received by this RADIUS Proxy Server that were rejected
                                     because they contained an invalid Message-Authenticator attribute.";
                            }

                            ///nokia-state/state/router/radius/proxy/statistics/group-member/rx/invalid-password
                            leaf invalid-password {
                                type yang:counter32;
                                description
                                    "The number of packets received by this RADIUS Proxy Server that were rejected
                                     because the User-Password attribute could not be decoded.";
                            }

                            ///nokia-state/state/router/radius/proxy/statistics/group-member/rx/management-overload
                            leaf management-overload {
                                type yang:counter32;
                                description
                                    "The number of packets that were rejected by this RADIUS server
                                     because the ISA management core is not able to process any
                                     new RADIUS requests due to overload.";
                            }

                            ///nokia-state/state/router/radius/proxy/statistics/group-member/rx/packets
                            leaf packets {
                                type yang:counter32;
                                description "The number of packets received by this RADIUS Proxy Server.";
                            }

                            ///nokia-state/state/router/radius/proxy/statistics/group-member/rx/retransmit
                            leaf retransmit {
                                type yang:counter32;
                                description
                                    "The number of packets received by this RADIUS Proxy Server
                                     that were rejected because they are retransmitted.";
                            }

                            ///nokia-state/state/router/radius/proxy/statistics/group-member/rx/ue-mac-missing
                            leaf ue-mac-missing {
                                type yang:counter32;
                                description
                                    "The number of packets received by this RADIUS Proxy Server that were rejected
                                     because the UE MAC address was not present in the packet.";
                            }

                            ///nokia-state/state/router/radius/proxy/statistics/group-member/rx/wrong-purpose
                            leaf wrong-purpose {
                                type yang:counter32;
                                description
                                    "The number of packets received by this RADIUS Proxy Server that were rejected
                                     because the value configured is not matching the type of packet.";
                            }

                        } // container rx

                        ///nokia-state/state/router/radius/proxy/statistics/group-member/tx
                        container tx {
                            description "Enter the tx context";

                            ///nokia-state/state/router/radius/proxy/statistics/group-member/tx/access-accept
                            leaf access-accept {
                                type yang:counter32;
                                description "The number of Access-Accept packets transmitted by this RADIUS Proxy Server.";
                            }

                            ///nokia-state/state/router/radius/proxy/statistics/group-member/tx/access-reject
                            leaf access-reject {
                                type yang:counter32;
                                description "The number of Access-Reject packets transmitted by this RADIUS Proxy Server.";
                            }

                            ///nokia-state/state/router/radius/proxy/statistics/group-member/tx/access-challenge
                            leaf access-challenge {
                                type yang:counter32;
                                description "The number of Access-Challenge packets transmitted by this RADIUS Proxy Server.";
                            }

                            ///nokia-state/state/router/radius/proxy/statistics/group-member/tx/accounting-response
                            leaf accounting-response {
                                type yang:counter32;
                                description "The number of Accounting-Response packets transmitted by this RADIUS Proxy Server.";
                            }

                            ///nokia-state/state/router/radius/proxy/statistics/group-member/tx/dropped
                            leaf dropped {
                                type yang:counter32;
                                description "The number of packets dropped by this RADIUS Proxy Server before transmission.";
                            }

                            ///nokia-state/state/router/radius/proxy/statistics/group-member/tx/send-failure
                            leaf send-failure {
                                type yang:counter32;
                                description
                                    "The number of packets that were dropped by this RADIUS server because the packet
                                     could not get transmitted to one of the servers in the ISA RADIUS server policy.";
                            }

                            ///nokia-state/state/router/radius/proxy/statistics/group-member/tx/server-authenticator-fail
                            leaf server-authenticator-fail {
                                type yang:counter32;
                                description
                                    "The number of client packets that were dropped because the RADIUS server replied
                                     with a packet with an invalid response Authenticator.";
                            }

                            ///nokia-state/state/router/radius/proxy/statistics/group-member/tx/server-invalid-attribute
                            leaf server-invalid-attribute {
                                type yang:counter32;
                                description
                                    "The number of client packets that were dropped because the RADIUS server
                                     replied with a packet with an invalid attribute.";
                            }

                            ///nokia-state/state/router/radius/proxy/statistics/group-member/tx/server-message-authenticator-fail
                            leaf server-message-authenticator-fail {
                                type yang:counter32;
                                description
                                    "The number of client packets that were dropped because the RADIUS server replied
                                     with a packet with an invalid Message-Authenticator attribute.";
                            }

                            ///nokia-state/state/router/radius/proxy/statistics/group-member/tx/server-timeout
                            leaf server-timeout {
                                type yang:counter32;
                                description
                                    "The number of client packets that were dropped because the RADIUS servers have
                                     timed out.";
                            }

                        } // container tx

                    } // list group-member

                } // container statistics

            } // list proxy

        } // container radius

    } // grouping state-router-radius

}
