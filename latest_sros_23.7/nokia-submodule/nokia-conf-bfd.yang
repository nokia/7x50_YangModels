submodule nokia-conf-bfd {

    yang-version "1.1";

    belongs-to nokia-conf { prefix "conf"; }

    import nokia-sros-yang-extensions     { prefix "sros-ext"; }
    import nokia-types-sros               { prefix "types-sros"; }

    include nokia-conf-groups;

    sros-ext:sros-major-release "rel23";
    organization "Nokia";
    contact
        "Nokia SR OS Support
         Web: <http://www.nokia.com>";
    description
        "Nokia YANG Data model to configure BFD protocol on SR OS based routers.

         Copyright 2016 Nokia. All rights reserved. Reproduction of this document
         is authorized on the condition that the foregoing copyright notice is included.

         This nokia-conf-bfd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-02-28";

    grouping conf-bfd {
        ///nokia-conf/configure/bfd
        container bfd {
            description "Enter the bfd context";

            ///nokia-conf/configure/bfd/apply-groups
            leaf-list apply-groups {
                type leafref {
                    path "../../groups/group/name";
                }
                max-elements 8;
                ordered-by user;
                description "Apply a configuration group at this level";
            }

            ///nokia-conf/configure/bfd/apply-groups-exclude
            leaf-list apply-groups-exclude {
                type leafref {
                    path "../../groups/group/name";
                }
                max-elements 8;
                ordered-by user;
                description "Exclude a configuration group at this level";
            }

            ///nokia-conf/configure/bfd/bfd-template
            list bfd-template {
                key "name";
                description "Enter the bfd-template list instance";

                ///nokia-conf/configure/bfd/bfd-template/name
                leaf name {
                    type types-sros:named-item;
                    description "BFD template name";
                }

                ///nokia-conf/configure/bfd/bfd-template/echo-receive
                leaf echo-receive {
                    type uint32 {
                        range "100..100000";
                    }
                    units "milliseconds";
                    default "100";
                    description "Echo receive interval";
                }

                ///nokia-conf/configure/bfd/bfd-template/multiplier
                leaf multiplier {
                    type uint32 {
                        range "1..20";
                    }
                    default "3";
                    description "Detection multiplier";
                }

                ///nokia-conf/configure/bfd/bfd-template/receive-interval
                leaf receive-interval {
                    type uint32 {
                        range "10..100000";
                    }
                    units "milliseconds";
                    default "100";
                    description "Receive interval";
                }

                ///nokia-conf/configure/bfd/bfd-template/transmit-interval
                leaf transmit-interval {
                    type uint32 {
                        range "10..100000";
                    }
                    units "milliseconds";
                    default "100";
                    description "Transmit interval";
                }

                ///nokia-conf/configure/bfd/bfd-template/type
                leaf type {
                    type enumeration {
                        enum cpm-np                         { value 1; }
                        enum fp                             { value 3; }
                    }
                    description "Local termination point for the BFD session";
                }

                ///nokia-conf/configure/bfd/bfd-template/apply-groups
                leaf-list apply-groups {
                    type leafref {
                        path "../../../groups/group/name";
                    }
                    max-elements 8;
                    ordered-by user;
                    description "Apply a configuration group at this level";
                }

                ///nokia-conf/configure/bfd/bfd-template/apply-groups-exclude
                leaf-list apply-groups-exclude {
                    type leafref {
                        path "../../../groups/group/name";
                    }
                    max-elements 8;
                    ordered-by user;
                    description "Exclude a configuration group at this level";
                }

            } // list bfd-template

            ///nokia-conf/configure/bfd/seamless-bfd
            container seamless-bfd {
                description "Enter the seamless-bfd context";

                ///nokia-conf/configure/bfd/seamless-bfd/reflector
                list reflector {
                    key "name";
                    max-elements 1;
                    description "Enter the reflector list instance";

                    ///nokia-conf/configure/bfd/seamless-bfd/reflector/name
                    leaf name {
                        type types-sros:named-item;
                        description "S-BFD reflector name";
                    }

                    ///nokia-conf/configure/bfd/seamless-bfd/reflector/admin-state
                    leaf admin-state {
                        type types-sros:admin-state;
                        default "disable";
                        description "Administrative state of the seamless BFD reflector";
                    }

                    ///nokia-conf/configure/bfd/seamless-bfd/reflector/discriminator
                    leaf discriminator {
                        type uint32 {
                            range "524288..526335";
                        }
                        sros-ext:auto-restart-to-modify;
                        description "Discriminator of the seamless BFD reflector";
                    }

                    ///nokia-conf/configure/bfd/seamless-bfd/reflector/description
                    leaf description {
                        type types-sros:description;
                        description "Text description";
                    }

                    ///nokia-conf/configure/bfd/seamless-bfd/reflector/local-state
                    leaf local-state {
                        type enumeration {
                            enum admin-down                     { value 0; }
                            enum up                             { value 3; }
                        }
                        default "up";
                        description "Local state of the seamless BFD reflector";
                    }

                    ///nokia-conf/configure/bfd/seamless-bfd/reflector/apply-groups
                    leaf-list apply-groups {
                        type leafref {
                            path "../../../../groups/group/name";
                        }
                        max-elements 8;
                        ordered-by user;
                        description "Apply a configuration group at this level";
                    }

                    ///nokia-conf/configure/bfd/seamless-bfd/reflector/apply-groups-exclude
                    leaf-list apply-groups-exclude {
                        type leafref {
                            path "../../../../groups/group/name";
                        }
                        max-elements 8;
                        ordered-by user;
                        description "Exclude a configuration group at this level";
                    }

                } // list reflector

            } // container seamless-bfd

        } // container bfd

    } // grouping conf-bfd

}
