submodule nokia-state-port-access {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel23";
    organization "Nokia";
    contact
        "Nokia SR OS Support
         Web: <http://www.nokia.com>";
    description
        "Nokia YANG Data model with operational state for access port parameters on SR OS based routers.

         Copyright 2016 Nokia. All rights reserved. Reproduction of this document
         is authorized on the condition that the foregoing copyright notice is included.

         This nokia-state-port-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-30";

    grouping state-port-access {
        container access {
            description "Enter the access context";

            container egress {
                description "Enter the egress context";

                list pool {
                    key "name";
                    description "Enter the pool list instance";

                    leaf name {
                        type types-sros:named-item;
                        description "Pool name for the access port";
                    }

                    container pool-usage {
                        description "Enter the pool-usage context";

                        leaf total-pool-size {
                            type uint32;
                            units "kilobytes";
                            description "Total buffer pools size.";
                        }

                        leaf total-pool-in-use {
                            type uint32;
                            units "kilobytes";
                            description "Total buffer pools size in use.";
                        }

                        leaf shared-pool-size {
                            type uint32;
                            units "kilobytes";
                            description "Total shared pools size.";
                        }

                        leaf shared-pool-in-use {
                            type uint32;
                            units "kilobytes";
                            description "Total shared pools size in use.";
                        }

                        leaf reserved-pool-size {
                            type uint32;
                            units "kilobytes";
                            description "Total reserved pools size.";
                        }

                        leaf reserved-pool-in-use {
                            type uint32;
                            units "kilobytes";
                            description "Total reserved pools size in use.";
                        }

                    } // container pool-usage


                } // list pool

            } // container egress

            container ingress {
                description "Enter the ingress context";

                list pool {
                    key "name";
                    description "Enter the pool list instance";

                    leaf name {
                        type types-sros:named-item;
                        description "Pool name for the access port";
                    }

                    container pool-usage {
                        description "Enter the pool-usage context";

                        leaf total-pool-size {
                            type uint32;
                            units "kilobytes";
                            description "Total buffer pools size.";
                        }

                        leaf total-pool-in-use {
                            type uint32;
                            units "kilobytes";
                            description "Total buffer pools size in use.";
                        }

                        leaf shared-pool-size {
                            type uint32;
                            units "kilobytes";
                            description "Total shared pools size.";
                        }

                        leaf shared-pool-in-use {
                            type uint32;
                            units "kilobytes";
                            description "Total shared pools size in use.";
                        }

                        leaf reserved-pool-size {
                            type uint32;
                            units "kilobytes";
                            description "Total reserved pools size.";
                        }

                        leaf reserved-pool-in-use {
                            type uint32;
                            units "kilobytes";
                            description "Total reserved pools size in use.";
                        }

                    } // container pool-usage


                } // list pool

            } // container ingress

        } // container access

    } // grouping state-port-access

}
