submodule nokia-conf-router-ripng {

    yang-version "1.1";

    belongs-to nokia-conf { prefix "conf"; }

    import nokia-sros-yang-extensions     { prefix "sros-ext"; }
    import nokia-types-ripng              { prefix "types-ripng"; }
    import nokia-types-sros               { prefix "types-sros"; }

    include nokia-conf-groups;
    include nokia-conf-policy-options;

    sros-ext:sros-major-release "rel23";
    organization "Nokia";
    contact
        "Nokia SR OS Support
         Web: <http://www.nokia.com>";
    description
        "Nokia YANG Data model to configure router ripng protocol attributes on SR OS based routers.

         Copyright 2016 Nokia. All rights reserved. Reproduction of this document
         is authorized on the condition that the foregoing copyright notice is included.

         This nokia-conf-router-ripng YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-09-16";

    grouping conf-router-ripng {
        ///nokia-conf/configure/router/ripng
        container ripng {
            presence "Enable the ripng context";
            description "Enable the ripng context";

            ///nokia-conf/configure/router/ripng/admin-state
            leaf admin-state {
                type types-sros:admin-state;
                default "enable";
                description "Administrative state of the RIPng instance";
            }

            ///nokia-conf/configure/router/ripng/description
            leaf description {
                type types-sros:description;
                description "Text description";
            }

            ///nokia-conf/configure/router/ripng/bfd-liveness
            leaf bfd-liveness {
                type boolean;
                default "false";
                description "Enable BFD to control the state of protocol adjacency";
            }

            ///nokia-conf/configure/router/ripng/check-zero
            leaf check-zero {
                type boolean;
                default "false";
                description "Enable checking of mandatory zero fields";
            }

            ///nokia-conf/configure/router/ripng/export-policy
            leaf-list export-policy {
                type leafref {
                    path "../../../policy-options/policy-statement/name";
                }
                max-elements 5;
                ordered-by user;
                description "Policies to determine exported routes";
            }

            ///nokia-conf/configure/router/ripng/import-policy
            leaf-list import-policy {
                type leafref {
                    path "../../../policy-options/policy-statement/name";
                }
                max-elements 5;
                ordered-by user;
                description "Import policies to decide routes for routing table";
            }

            ///nokia-conf/configure/router/ripng/message-size
            leaf message-size {
                type types-ripng:message-size;
                default "25";
                description "Maximum number of routes in the message";
            }

            ///nokia-conf/configure/router/ripng/metric-in
            leaf metric-in {
                type types-ripng:metric;
                default "1";
                description "Metric added to routes received from the neighbor";
            }

            ///nokia-conf/configure/router/ripng/metric-out
            leaf metric-out {
                type types-ripng:metric;
                default "1";
                description "Metric added to routes exported into RIPng";
            }

            ///nokia-conf/configure/router/ripng/preference
            leaf preference {
                type types-ripng:preference;
                default "100";
                description "Route preference";
            }

            ///nokia-conf/configure/router/ripng/receive
            leaf receive {
                type types-ripng:receive;
                default "ripng";
                description "Accepted version on received packets";
            }

            ///nokia-conf/configure/router/ripng/send
            leaf send {
                type enumeration {
                    enum none                           { value 1; }
                    enum ripng                          { value 5; }
                }
                default "ripng";
                description "RIPng version and method used to send RIPng updates";
            }

            ///nokia-conf/configure/router/ripng/split-horizon
            leaf split-horizon {
                type boolean;
                default "true";
                description "Enable split horizon and poison reverse";
            }

            ///nokia-conf/configure/router/ripng/apply-groups
            leaf-list apply-groups {
                type leafref {
                    path "../../../groups/group/name";
                }
                max-elements 8;
                ordered-by user;
                description "Apply a configuration group at this level";
            }

            ///nokia-conf/configure/router/ripng/apply-groups-exclude
            leaf-list apply-groups-exclude {
                type leafref {
                    path "../../../groups/group/name";
                }
                max-elements 8;
                ordered-by user;
                description "Exclude a configuration group at this level";
            }

            ///nokia-conf/configure/router/ripng/export-limit
            container export-limit {
                presence "Enable the export-limit context";
                description "Enable the export-limit context";

                ///nokia-conf/configure/router/ripng/export-limit/number
                leaf number {
                    type uint32 {
                        range "1..max";
                    }
                    mandatory true;
                    description "Maximum routes or prefixes exported from route table";
                }

                ///nokia-conf/configure/router/ripng/export-limit/log-percent
                leaf log-percent {
                    type uint32 {
                        range "1..100";
                    }
                    description "Export limit before warning and SNMP notification sent";
                }

            } // container export-limit

            ///nokia-conf/configure/router/ripng/timers
            container timers {
                presence "Enable the timers context";
                description "Enable the timers context";

                ///nokia-conf/configure/router/ripng/timers/update
                leaf update {
                    type types-ripng:timer-update;
                    mandatory true;
                    description "Timer that controls the frequency of updates";
                }

                ///nokia-conf/configure/router/ripng/timers/timeout
                leaf timeout {
                    type types-ripng:timer-timeout;
                    mandatory true;
                    description "RIP timeout timer";
                }

                ///nokia-conf/configure/router/ripng/timers/flush
                leaf flush {
                    type types-ripng:timer-flush;
                    mandatory true;
                    description "RIP flush timer";
                }

            } // container timers

            ///nokia-conf/configure/router/ripng/group
            list group {
                key "group-name";
                description "Enter the group list instance";

                ///nokia-conf/configure/router/ripng/group/group-name
                leaf group-name {
                    type types-sros:named-item;
                    description "RIP group name";
                }

                ///nokia-conf/configure/router/ripng/group/admin-state
                leaf admin-state {
                    type types-sros:admin-state;
                    default "enable";
                    description "Administrative state of RIPng neighbor interface group";
                }

                ///nokia-conf/configure/router/ripng/group/description
                leaf description {
                    type types-sros:description;
                    description "Text description";
                }

                ///nokia-conf/configure/router/ripng/group/export-policy
                leaf-list export-policy {
                    type leafref {
                        path "../../../../policy-options/policy-statement/name";
                    }
                    max-elements 5;
                    ordered-by user;
                    description "Policies used to rule which routes are exported to RIP";
                }

                ///nokia-conf/configure/router/ripng/group/import-policy
                leaf-list import-policy {
                    type leafref {
                        path "../../../../policy-options/policy-statement/name";
                    }
                    max-elements 5;
                    ordered-by user;
                    description "Policies to decide routes accepted from RIP neighbors";
                }

                ///nokia-conf/configure/router/ripng/group/bfd-liveness
                leaf bfd-liveness {
                    type boolean;
                    description "Enable BFD to control the state of protocol adjacency";
                }

                ///nokia-conf/configure/router/ripng/group/check-zero
                leaf check-zero {
                    type boolean;
                    description "Enable checking of mandatory zero fields";
                }

                ///nokia-conf/configure/router/ripng/group/message-size
                leaf message-size {
                    type types-ripng:message-size;
                    description "Maximum number of routes in the message";
                }

                ///nokia-conf/configure/router/ripng/group/metric-in
                leaf metric-in {
                    type types-ripng:metric;
                    description "Metric added to routes received from the neighbor";
                }

                ///nokia-conf/configure/router/ripng/group/metric-out
                leaf metric-out {
                    type types-ripng:metric;
                    description "Metric added to routes exported into RIPng";
                }

                ///nokia-conf/configure/router/ripng/group/preference
                leaf preference {
                    type types-ripng:preference;
                    description "Route preference";
                }

                ///nokia-conf/configure/router/ripng/group/receive
                leaf receive {
                    type types-ripng:receive;
                    description "Accepted version on received packets";
                }

                ///nokia-conf/configure/router/ripng/group/split-horizon
                leaf split-horizon {
                    type boolean;
                    description "Enable split horizon and poison reverse";
                }

                ///nokia-conf/configure/router/ripng/group/send
                leaf send {
                    type enumeration {
                        enum none                           { value 1; }
                        enum ripng                          { value 5; }
                    }
                    description "RIPng version and method used to send RIPng updates";
                }

                ///nokia-conf/configure/router/ripng/group/apply-groups
                leaf-list apply-groups {
                    type leafref {
                        path "../../../../groups/group/name";
                    }
                    max-elements 8;
                    ordered-by user;
                    description "Apply a configuration group at this level";
                }

                ///nokia-conf/configure/router/ripng/group/apply-groups-exclude
                leaf-list apply-groups-exclude {
                    type leafref {
                        path "../../../../groups/group/name";
                    }
                    max-elements 8;
                    ordered-by user;
                    description "Exclude a configuration group at this level";
                }

                ///nokia-conf/configure/router/ripng/group/timers
                container timers {
                    presence "Enable the timers context";
                    description "Enable the timers context";

                    ///nokia-conf/configure/router/ripng/group/timers/update
                    leaf update {
                        type types-ripng:timer-update;
                        mandatory true;
                        description "Timer that controls the frequency of updates";
                    }

                    ///nokia-conf/configure/router/ripng/group/timers/timeout
                    leaf timeout {
                        type types-ripng:timer-timeout;
                        mandatory true;
                        description "RIP timeout timer";
                    }

                    ///nokia-conf/configure/router/ripng/group/timers/flush
                    leaf flush {
                        type types-ripng:timer-flush;
                        mandatory true;
                        description "RIP flush timer";
                    }

                } // container timers

                ///nokia-conf/configure/router/ripng/group/neighbor
                list neighbor {
                    key "interface-name";
                    description "Enter the neighbor list instance";

                    ///nokia-conf/configure/router/ripng/group/neighbor/interface-name
                    leaf interface-name {
                        type types-sros:interface-name;
                        description "Neighbor added to the RIPng group through the interface";
                    }

                    ///nokia-conf/configure/router/ripng/group/neighbor/admin-state
                    leaf admin-state {
                        type types-sros:admin-state;
                        default "enable";
                        description "Administrative state of the RIPng neighbor";
                    }

                    ///nokia-conf/configure/router/ripng/group/neighbor/description
                    leaf description {
                        type types-sros:description;
                        description "Text description";
                    }

                    ///nokia-conf/configure/router/ripng/group/neighbor/export-policy
                    leaf-list export-policy {
                        type leafref {
                            path "../../../../../policy-options/policy-statement/name";
                        }
                        max-elements 5;
                        ordered-by user;
                        description "Policies used to rule which routes are exported to RIP";
                    }

                    ///nokia-conf/configure/router/ripng/group/neighbor/import-policy
                    leaf-list import-policy {
                        type leafref {
                            path "../../../../../policy-options/policy-statement/name";
                        }
                        max-elements 5;
                        ordered-by user;
                        description "Policies to decide routes accepted from RIP neighbors";
                    }

                    ///nokia-conf/configure/router/ripng/group/neighbor/bfd-liveness
                    leaf bfd-liveness {
                        type boolean;
                        description "Enable BFD to control the state of protocol adjacency";
                    }

                    ///nokia-conf/configure/router/ripng/group/neighbor/check-zero
                    leaf check-zero {
                        type boolean;
                        description "Enable checking of mandatory zero fields";
                    }

                    ///nokia-conf/configure/router/ripng/group/neighbor/message-size
                    leaf message-size {
                        type types-ripng:message-size;
                        description "Maximum number of routes in the message";
                    }

                    ///nokia-conf/configure/router/ripng/group/neighbor/metric-in
                    leaf metric-in {
                        type types-ripng:metric;
                        description "Metric added to routes received from the neighbor";
                    }

                    ///nokia-conf/configure/router/ripng/group/neighbor/metric-out
                    leaf metric-out {
                        type types-ripng:metric;
                        description "Metric added to routes exported into RIPng";
                    }

                    ///nokia-conf/configure/router/ripng/group/neighbor/preference
                    leaf preference {
                        type types-ripng:preference;
                        description "Route preference";
                    }

                    ///nokia-conf/configure/router/ripng/group/neighbor/receive
                    leaf receive {
                        type types-ripng:receive;
                        description "Accepted version on received packets";
                    }

                    ///nokia-conf/configure/router/ripng/group/neighbor/split-horizon
                    leaf split-horizon {
                        type boolean;
                        description "Enable split horizon and poison reverse";
                    }

                    ///nokia-conf/configure/router/ripng/group/neighbor/send
                    leaf send {
                        type enumeration {
                            enum none                           { value 1; }
                            enum ripng                          { value 5; }
                            enum unicast                        { value 6; }
                        }
                        description "RIPng version and method used to send RIPng updates";
                    }

                    ///nokia-conf/configure/router/ripng/group/neighbor/apply-groups
                    leaf-list apply-groups {
                        type leafref {
                            path "../../../../../groups/group/name";
                        }
                        max-elements 8;
                        ordered-by user;
                        description "Apply a configuration group at this level";
                    }

                    ///nokia-conf/configure/router/ripng/group/neighbor/apply-groups-exclude
                    leaf-list apply-groups-exclude {
                        type leafref {
                            path "../../../../../groups/group/name";
                        }
                        max-elements 8;
                        ordered-by user;
                        description "Exclude a configuration group at this level";
                    }

                    ///nokia-conf/configure/router/ripng/group/neighbor/timers
                    container timers {
                        presence "Enable the timers context";
                        description "Enable the timers context";

                        ///nokia-conf/configure/router/ripng/group/neighbor/timers/update
                        leaf update {
                            type types-ripng:timer-update;
                            mandatory true;
                            description "Timer that controls the frequency of updates";
                        }

                        ///nokia-conf/configure/router/ripng/group/neighbor/timers/timeout
                        leaf timeout {
                            type types-ripng:timer-timeout;
                            mandatory true;
                            description "RIP timeout timer";
                        }

                        ///nokia-conf/configure/router/ripng/group/neighbor/timers/flush
                        leaf flush {
                            type types-ripng:timer-flush;
                            mandatory true;
                            description "RIP flush timer";
                        }

                    } // container timers

                    ///nokia-conf/configure/router/ripng/group/neighbor/unicast-address
                    list unicast-address {
                        key "address";
                        description "Add a list entry for unicast-address";

                        ///nokia-conf/configure/router/ripng/group/neighbor/unicast-address/address
                        leaf address {
                            type types-sros:ipv6-unicast-address;
                            description "Unicast address for the neighbor";
                        }

                    } // list unicast-address

                } // list neighbor

            } // list group

        } // container ripng

    } // grouping conf-router-ripng

}
