submodule nokia-conf-svc-vprn-ospf {

    yang-version "1.1";

    belongs-to nokia-conf { prefix "conf"; }

    import nokia-sros-yang-extensions     { prefix "sros-ext"; }
    import nokia-types-igp                { prefix "types-igp"; }
    import nokia-types-ospf               { prefix "types-ospf"; }
    import nokia-types-router             { prefix "types-router"; }
    import nokia-types-sros               { prefix "types-sros"; }

    include nokia-conf-groups;
    include nokia-conf-policy-options;
    include nokia-conf-routing-options;
    include nokia-conf-system;
    include nokia-conf-system-ned;
    include nokia-conf-system-security;

    sros-ext:sros-major-release "rel23";
    organization "Nokia";
    contact
        "Nokia SR OS Support
         Web: <http://www.nokia.com>";
    description
        "Nokia YANG Data model to configure vprn ospf protocol attributes on SR OS based routers.

         Copyright 2016 Nokia. All rights reserved. Reproduction of this document
         is authorized on the condition that the foregoing copyright notice is included.

         This nokia-conf-svc-vprn-ospf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-02-22";

    grouping conf-svc-vprn-ospf {
        ///nokia-conf/configure/service/vprn/ospf
        list ospf {
            key "ospf-instance";
            max-elements 32;
            description "Enter the ospf list instance";

            ///nokia-conf/configure/service/vprn/ospf/ospf-instance
            leaf ospf-instance {
                type uint32 {
                    range "0";
                }
                description "Specifies the value of the integrated OSPF instance.";
            }

            ///nokia-conf/configure/service/vprn/ospf/admin-state
            leaf admin-state {
                type types-sros:admin-state;
                default "disable";
                description "Administrative state of the OSPF instance";
            }

            ///nokia-conf/configure/service/vprn/ospf/router-id
            leaf router-id {
                type types-igp:router-id;
                sros-ext:auto-restart-to-modify;
                description "Unique router ID for the OSPF instance";
            }

            ///nokia-conf/configure/service/vprn/ospf/advertise-router-capability
            leaf advertise-router-capability {
                type types-ospf:advertise-router-capability-type;
                default "false";
                description "Allow router advertisement capabilities";
            }

            ///nokia-conf/configure/service/vprn/ospf/external-preference
            leaf external-preference {
                type int32 {
                    range "1..255";
                }
                default "150";
                description "Preference for OSPF external routes";
            }

            ///nokia-conf/configure/service/vprn/ospf/export-policy
            leaf-list export-policy {
                type leafref {
                    path "../../../../policy-options/policy-statement/name";
                }
                max-elements 5;
                ordered-by user;
                description "Export policies that determine exported routes";
            }

            ///nokia-conf/configure/service/vprn/ospf/import-policy
            leaf-list import-policy {
                type leafref {
                    path "../../../../policy-options/policy-statement/name";
                }
                max-elements 5;
                ordered-by user;
                description "Import policy names for routes from IGP to route table";
            }

            ///nokia-conf/configure/service/vprn/ospf/multicast-import
            leaf multicast-import {
                type boolean;
                default "false";
                description "Submit routes into the multicast Route Table Manager";
            }

            ///nokia-conf/configure/service/vprn/ospf/overload-include-ext-1
            leaf overload-include-ext-1 {
                type boolean;
                default "false";
                description "Advertise routes with maximum metric value for overload";
            }

            ///nokia-conf/configure/service/vprn/ospf/overload-include-ext-2
            leaf overload-include-ext-2 {
                type boolean;
                default "false";
                description "Advertise routes with maximum metric value for overload";
            }

            ///nokia-conf/configure/service/vprn/ospf/overload-include-stub
            leaf overload-include-stub {
                type boolean;
                default "false";
                description "Advertise all stub interfaces with max metric value";
            }

            ///nokia-conf/configure/service/vprn/ospf/overload
            leaf overload {
                type boolean;
                default "false";
                description "Change local router state to appear overloaded";
            }

            ///nokia-conf/configure/service/vprn/ospf/preference
            leaf preference {
                type int32 {
                    range "1..255";
                }
                default "10";
                description "Preference for OSPF internal routes";
            }

            ///nokia-conf/configure/service/vprn/ospf/reference-bandwidth
            leaf reference-bandwidth {
                type types-sros:reference-bandwidth-ext;
                units "kilobps";
                default "100000000";
                description "Bandwidth to reference default costing of interfaces";
            }

            ///nokia-conf/configure/service/vprn/ospf/unicast-import
            leaf unicast-import {
                type boolean;
                default "true";
                description "Submit routes into the unicast Route Table Manager";
            }

            ///nokia-conf/configure/service/vprn/ospf/compatible-rfc1583
            leaf compatible-rfc1583 {
                type boolean;
                default "true";
                description "OSPF summary and external route calculations";
            }

            ///nokia-conf/configure/service/vprn/ospf/ignore-dn-bit
            leaf ignore-dn-bit {
                type boolean;
                default "false";
                description "Ignore the DN bit for OSPF LSA packets for the instance";
            }

            ///nokia-conf/configure/service/vprn/ospf/suppress-dn-bit
            leaf suppress-dn-bit {
                type boolean;
                default "false";
                description "Suppress the DN bit setting for OSPF LSA packets";
            }

            ///nokia-conf/configure/service/vprn/ospf/super-backbone
            leaf super-backbone {
                type boolean;
                default "false";
                description "Enable/disable super-backbone functionality.";
            }

            ///nokia-conf/configure/service/vprn/ospf/vpn-tag
            leaf vpn-tag {
                type uint32;
                default "0";
                description "OSPF VPN tag";
            }

            ///nokia-conf/configure/service/vprn/ospf/apply-groups
            leaf-list apply-groups {
                type leafref {
                    path "../../../../groups/group/name";
                }
                max-elements 8;
                ordered-by user;
                description "Apply a configuration group at this level";
            }

            ///nokia-conf/configure/service/vprn/ospf/apply-groups-exclude
            leaf-list apply-groups-exclude {
                type leafref {
                    path "../../../../groups/group/name";
                }
                max-elements 8;
                ordered-by user;
                description "Exclude a configuration group at this level";
            }

            ///nokia-conf/configure/service/vprn/ospf/external-db-overflow
            container external-db-overflow {
                presence "Enable the external-db-overflow context";
                description "Enable the external-db-overflow context";

                ///nokia-conf/configure/service/vprn/ospf/external-db-overflow/limit
                leaf limit {
                    type uint32 {
                        range "0..2147483647";
                    }
                    default "0";
                    description "Number of external LSA at which overload is triggered";
                }

                ///nokia-conf/configure/service/vprn/ospf/external-db-overflow/interval
                leaf interval {
                    type uint32 {
                        range "0..2147483647";
                    }
                    units "seconds";
                    default "0";
                    description "Time during which the router operates in overload";
                }

            } // container external-db-overflow

            ///nokia-conf/configure/service/vprn/ospf/export-limit
            container export-limit {
                presence "Enable the export-limit context";
                description "Enable the export-limit context";

                ///nokia-conf/configure/service/vprn/ospf/export-limit/number
                leaf number {
                    type uint32 {
                        range "1..max";
                    }
                    mandatory true;
                    description "Maximum routes or prefixes exported from route table";
                }

                ///nokia-conf/configure/service/vprn/ospf/export-limit/log-percent
                leaf log-percent {
                    type uint32 {
                        range "1..100";
                    }
                    description "Export limit before warning and SNMP notification sent";
                }

            } // container export-limit

            ///nokia-conf/configure/service/vprn/ospf/overload-on-boot
            container overload-on-boot {
                presence "Enable the overload-on-boot context";
                description "Enable the overload-on-boot context";

                ///nokia-conf/configure/service/vprn/ospf/overload-on-boot/timeout
                leaf timeout {
                    type uint32 {
                        range "60..1800";
                    }
                    units "seconds";
                    description "Time during which the router operates in overload state before reestablishing normal operations";
                }

            } // container overload-on-boot

            ///nokia-conf/configure/service/vprn/ospf/rib-priority
            container rib-priority {
                description "Enter the rib-priority context";

                ///nokia-conf/configure/service/vprn/ospf/rib-priority/high
                container high {
                    description "Enter the high context";

                    ///nokia-conf/configure/service/vprn/ospf/rib-priority/high/prefix-list
                    leaf prefix-list {
                        type leafref {
                            path "../../../../../../policy-options/prefix-list/name";
                        }
                        description "Higher priority list used during OSPF route calculation";
                    }

                } // container high

            } // container rib-priority

            ///nokia-conf/configure/service/vprn/ospf/rtr-adv-lsa-limit
            container rtr-adv-lsa-limit {
                presence "Enable the rtr-adv-lsa-limit context";
                description "Enable the rtr-adv-lsa-limit context";

                ///nokia-conf/configure/service/vprn/ospf/rtr-adv-lsa-limit/max-lsa-count
                leaf max-lsa-count {
                    type uint32 {
                        range "1..max";
                    }
                    mandatory true;
                    description "Max number of LSAs one router can advertise";
                }

                ///nokia-conf/configure/service/vprn/ospf/rtr-adv-lsa-limit/log-only
                leaf log-only {
                    type boolean;
                    default "false";
                    description "Log the event without triggering overload";
                }

                ///nokia-conf/configure/service/vprn/ospf/rtr-adv-lsa-limit/warning-threshold
                leaf warning-threshold {
                    type uint32 {
                        range "0..100";
                    }
                    units "percent";
                    default "0";
                    description "Percentage of the max LSA count that causes a warning";
                }

                ///nokia-conf/configure/service/vprn/ospf/rtr-adv-lsa-limit/overload-timeout
                leaf overload-timeout {
                    type types-igp:overload-timeout;
                    default "forever";
                    description "Maximum time in overload after LSA limit is reached";
                }

            } // container rtr-adv-lsa-limit

            ///nokia-conf/configure/service/vprn/ospf/graceful-restart
            container graceful-restart {
                presence "Enable the graceful-restart context";
                description "Enable the graceful-restart context";

                ///nokia-conf/configure/service/vprn/ospf/graceful-restart/helper-mode
                leaf helper-mode {
                    type boolean;
                    default "true";
                    description "Enable graceful restart helper for OSPF";
                }

                ///nokia-conf/configure/service/vprn/ospf/graceful-restart/strict-lsa-checking
                leaf strict-lsa-checking {
                    type boolean;
                    default "true";
                    description "Perform strict LSA checking during graceful restart";
                }

            } // container graceful-restart

            ///nokia-conf/configure/service/vprn/ospf/timers
            container timers {
                description "Enter the timers context";

                ///nokia-conf/configure/service/vprn/ospf/timers/incremental-spf-wait
                leaf incremental-spf-wait {
                    type uint32 {
                        range "0..1000";
                    }
                    units "milliseconds";
                    default "1000";
                    description "Delay time before an incremental SPF calculation starts";
                }

                ///nokia-conf/configure/service/vprn/ospf/timers/lsa-accumulate
                leaf lsa-accumulate {
                    type uint32 {
                        range "0..1000";
                    }
                    units "milliseconds";
                    default "1000";
                    description "Delay to gather LSAs before advertising to neighbors";
                }

                ///nokia-conf/configure/service/vprn/ospf/timers/lsa-arrival
                leaf lsa-arrival {
                    type uint32 {
                        range "0..600000";
                    }
                    units "milliseconds";
                    default "1000";
                    description "Min delay between receipt of same LSAs from neighbors";
                }

                ///nokia-conf/configure/service/vprn/ospf/timers/redistribute-delay
                leaf redistribute-delay {
                    type uint32 {
                        range "0..1000";
                    }
                    units "milliseconds";
                    default "1000";
                    description "Hold down timer for external routes into OSPF";
                }

                ///nokia-conf/configure/service/vprn/ospf/timers/lsa-generate
                container lsa-generate {
                    description "Enter the lsa-generate context";

                    ///nokia-conf/configure/service/vprn/ospf/timers/lsa-generate/max-lsa-wait
                    leaf max-lsa-wait {
                        type uint32 {
                            range "10..600000";
                        }
                        units "milliseconds";
                        default "5000";
                        description "Max time between two LSAs being generated";
                    }

                    ///nokia-conf/configure/service/vprn/ospf/timers/lsa-generate/lsa-initial-wait
                    leaf lsa-initial-wait {
                        type uint32 {
                            range "10..600000";
                        }
                        units "milliseconds";
                        default "5000";
                        description "First wait period between OSPF LSA generation";
                    }

                    ///nokia-conf/configure/service/vprn/ospf/timers/lsa-generate/lsa-second-wait
                    leaf lsa-second-wait {
                        type uint32 {
                            range "10..600000";
                        }
                        units "milliseconds";
                        default "5000";
                        description "Hold time between the first and second LSA generation";
                    }

                } // container lsa-generate

                ///nokia-conf/configure/service/vprn/ospf/timers/spf-wait
                container spf-wait {
                    description "Enter the spf-wait context";

                    ///nokia-conf/configure/service/vprn/ospf/timers/spf-wait/spf-max-wait
                    leaf spf-max-wait {
                        type uint32 {
                            range "10..120000";
                        }
                        units "milliseconds";
                        default "10000";
                        description "Max interval between two consecutive SPF calculations";
                    }

                    ///nokia-conf/configure/service/vprn/ospf/timers/spf-wait/spf-initial-wait
                    leaf spf-initial-wait {
                        type uint32 {
                            range "10..100000";
                        }
                        units "milliseconds";
                        default "1000";
                        description "Initial SPF calculation delay after a topology change";
                    }

                    ///nokia-conf/configure/service/vprn/ospf/timers/spf-wait/spf-second-wait
                    leaf spf-second-wait {
                        type uint32 {
                            range "10..100000";
                        }
                        units "milliseconds";
                        default "1000";
                        description "Hold time between the first and second SPF calculation";
                    }

                } // container spf-wait

            } // container timers

            ///nokia-conf/configure/service/vprn/ospf/loopfree-alternate
            container loopfree-alternate {
                presence "Enable the loopfree-alternate context";
                description "Enable the loopfree-alternate context";

                ///nokia-conf/configure/service/vprn/ospf/loopfree-alternate/exclude
                container exclude {
                    description "Enter the exclude context";

                    ///nokia-conf/configure/service/vprn/ospf/loopfree-alternate/exclude/prefix-policy
                    leaf-list prefix-policy {
                        type leafref {
                            path "../../../../../../policy-options/policy-statement/name";
                        }
                        max-elements 5;
                        ordered-by user;
                        description "Policy to exclude prefixes from LFA SPF calculation";
                    }

                } // container exclude

            } // container loopfree-alternate

            ///nokia-conf/configure/service/vprn/ospf/vpn-domain
            container vpn-domain {
                presence "Enable the vpn-domain context";
                description "Enable the vpn-domain context";

                ///nokia-conf/configure/service/vprn/ospf/vpn-domain/id
                leaf id {
                    type types-igp:system-id;
                    description "OSPF VPN domain ID";
                }

                ///nokia-conf/configure/service/vprn/ospf/vpn-domain/type
                leaf type {
                    type types-ospf:vpn-domain-type;
                    mandatory true;
                    description "VPN domain type";
                }

            } // container vpn-domain

            ///nokia-conf/configure/service/vprn/ospf/area
            list area {
                key "area-id";
                description "Enter the area list instance";

                ///nokia-conf/configure/service/vprn/ospf/area/area-id
                leaf area-id {
                    type types-sros:ipv4-address;
                    description "Area-ID attribute";
                }

                ///nokia-conf/configure/service/vprn/ospf/area/advertise-router-capability
                leaf advertise-router-capability {
                    type boolean;
                    default "true";
                    description "Allow router advertisement capabilities";
                }

                ///nokia-conf/configure/service/vprn/ospf/area/blackhole-aggregate
                leaf blackhole-aggregate {
                    type boolean;
                    default "true";
                    description "Install a low priority blackhole route to avoid loops";
                }

                ///nokia-conf/configure/service/vprn/ospf/area/export-policy
                leaf-list export-policy {
                    type leafref {
                        path "../../../../../policy-options/policy-statement/name";
                    }
                    max-elements 5;
                    ordered-by user;
                    description "Type 3 Summary-LSA/OSPFv3 inter-area-prefix-LSA route";
                }

                ///nokia-conf/configure/service/vprn/ospf/area/import-policy
                leaf-list import-policy {
                    type leafref {
                        path "../../../../../policy-options/policy-statement/name";
                    }
                    max-elements 5;
                    ordered-by user;
                    description "Route imported as Summary Type 3/Inter-Area-Prefix-LSA";
                }

                ///nokia-conf/configure/service/vprn/ospf/area/loopfree-alternate-exclude
                leaf loopfree-alternate-exclude {
                    type boolean;
                    default "false";
                    description "Exclude interfaces in OSPF areas in SPF LFA computation";
                }

                ///nokia-conf/configure/service/vprn/ospf/area/advertise-ne-profile
                leaf advertise-ne-profile {
                    type leafref {
                        path "../../../../../system/network-element-discovery/profile/name";
                    }
                    description "Network element profile to be advertised";
                }

                ///nokia-conf/configure/service/vprn/ospf/area/apply-groups
                leaf-list apply-groups {
                    type leafref {
                        path "../../../../../groups/group/name";
                    }
                    max-elements 8;
                    ordered-by user;
                    description "Apply a configuration group at this level";
                }

                ///nokia-conf/configure/service/vprn/ospf/area/apply-groups-exclude
                leaf-list apply-groups-exclude {
                    type leafref {
                        path "../../../../../groups/group/name";
                    }
                    max-elements 8;
                    ordered-by user;
                    description "Exclude a configuration group at this level";
                }

                ///nokia-conf/configure/service/vprn/ospf/area/stub
                container stub {
                    presence "Enable the stub context";
                    description "Enable the stub context";

                    ///nokia-conf/configure/service/vprn/ospf/area/stub/default-metric
                    leaf default-metric {
                        type uint32 {
                            range "1..16777214";
                        }
                        default "1";
                        description "Metric used by ABR for default route into the stub area";
                    }

                    ///nokia-conf/configure/service/vprn/ospf/area/stub/summaries
                    leaf summaries {
                        type boolean;
                        default "true";
                        description "Send summary (Type 3) LSAs into the stub area on an ABR";
                    }

                } // container stub

                ///nokia-conf/configure/service/vprn/ospf/area/nssa
                container nssa {
                    presence "Enable the nssa context";
                    description "Enable the nssa context";

                    ///nokia-conf/configure/service/vprn/ospf/area/nssa/redistribute-external
                    leaf redistribute-external {
                        type boolean;
                        default "true";
                        description "Redistribute external routes into the NSSA";
                    }

                    ///nokia-conf/configure/service/vprn/ospf/area/nssa/summaries
                    leaf summaries {
                        type boolean;
                        default "true";
                        description "Send summary (Type 3) LSAs into the NSSA on an ABR";
                    }

                    ///nokia-conf/configure/service/vprn/ospf/area/nssa/area-range
                    list area-range {
                        key "ip-prefix-mask";
                        description "Enter the area-range list instance";

                        ///nokia-conf/configure/service/vprn/ospf/area/nssa/area-range/ip-prefix-mask
                        leaf ip-prefix-mask {
                            type types-sros:ipv4-unicast-prefix;
                            description "IPv4 unicast address prefix and mask";
                        }

                        ///nokia-conf/configure/service/vprn/ospf/area/nssa/area-range/advertise
                        leaf advertise {
                            type boolean;
                            default "true";
                            description "Advertise summarized range of addresses to other areas";
                        }

                        ///nokia-conf/configure/service/vprn/ospf/area/nssa/area-range/apply-groups
                        leaf-list apply-groups {
                            type leafref {
                                path "../../../../../../../groups/group/name";
                            }
                            max-elements 8;
                            ordered-by user;
                            description "Apply a configuration group at this level";
                        }

                        ///nokia-conf/configure/service/vprn/ospf/area/nssa/area-range/apply-groups-exclude
                        leaf-list apply-groups-exclude {
                            type leafref {
                                path "../../../../../../../groups/group/name";
                            }
                            max-elements 8;
                            ordered-by user;
                            description "Exclude a configuration group at this level";
                        }

                    } // list area-range

                    ///nokia-conf/configure/service/vprn/ospf/area/nssa/originate-default-route
                    container originate-default-route {
                        presence "Enable the originate-default-route context";
                        description "Enable the originate-default-route context";

                        ///nokia-conf/configure/service/vprn/ospf/area/nssa/originate-default-route/type-nssa
                        leaf type-nssa {
                            type boolean;
                            default "false";
                            description "Generate a default route using NSSA-LSA type";
                        }

                        ///nokia-conf/configure/service/vprn/ospf/area/nssa/originate-default-route/adjacency-check
                        leaf adjacency-check {
                            type boolean;
                            default "false";
                            description "Perform adjacency checks before originating a default route";
                        }

                    } // container originate-default-route

                } // container nssa

                ///nokia-conf/configure/service/vprn/ospf/area/area-range
                list area-range {
                    key "ip-prefix-mask";
                    description "Enter the area-range list instance";

                    ///nokia-conf/configure/service/vprn/ospf/area/area-range/ip-prefix-mask
                    leaf ip-prefix-mask {
                        type types-sros:ipv4-unicast-prefix;
                        description "IPv4 unicast address prefix and mask";
                    }

                    ///nokia-conf/configure/service/vprn/ospf/area/area-range/advertise
                    leaf advertise {
                        type boolean;
                        default "true";
                        description "Advertise summarized range of addresses to other areas";
                    }

                    ///nokia-conf/configure/service/vprn/ospf/area/area-range/apply-groups
                    leaf-list apply-groups {
                        type leafref {
                            path "../../../../../../groups/group/name";
                        }
                        max-elements 8;
                        ordered-by user;
                        description "Apply a configuration group at this level";
                    }

                    ///nokia-conf/configure/service/vprn/ospf/area/area-range/apply-groups-exclude
                    leaf-list apply-groups-exclude {
                        type leafref {
                            path "../../../../../../groups/group/name";
                        }
                        max-elements 8;
                        ordered-by user;
                        description "Exclude a configuration group at this level";
                    }

                } // list area-range

                ///nokia-conf/configure/service/vprn/ospf/area/interface
                list interface {
                    key "interface-name";
                    description "Enter the interface list instance";

                    ///nokia-conf/configure/service/vprn/ospf/area/interface/interface-name
                    leaf interface-name {
                        type types-sros:interface-name;
                        description "IP interface name";
                    }

                    ///nokia-conf/configure/service/vprn/ospf/area/interface/advertise-router-capability
                    leaf advertise-router-capability {
                        type boolean;
                        default "true";
                        description "Allow router advertisement capabilities";
                    }

                    ///nokia-conf/configure/service/vprn/ospf/area/interface/advertise-subnet
                    leaf advertise-subnet {
                        type boolean;
                        default "true";
                        description "Advertise point-to-point interfaces as subnet routes";
                    }

                    ///nokia-conf/configure/service/vprn/ospf/area/interface/interface-type
                    leaf interface-type {
                        type types-ospf:interface-type;
                        sros-ext:immutable;
                        description "Interface type";
                    }

                    ///nokia-conf/configure/service/vprn/ospf/area/interface/lsa-filter-out
                    leaf lsa-filter-out {
                        type types-ospf:lsa-filter-out;
                        default "none";
                        description "LSA flooding reduction";
                    }

                    ///nokia-conf/configure/service/vprn/ospf/area/interface/metric
                    leaf metric {
                        type uint32 {
                            range "1..65535";
                        }
                        description "Route cost metric for the interface";
                    }

                    ///nokia-conf/configure/service/vprn/ospf/area/interface/mtu
                    leaf mtu {
                        type types-router:ip-mtu-ext;
                        description "MTU for the OSPF to use on the interface";
                    }

                    ///nokia-conf/configure/service/vprn/ospf/area/interface/passive
                    leaf passive {
                        type boolean;
                        description "Advertise passive interfaces as OSPF interfaces";
                    }

                    ///nokia-conf/configure/service/vprn/ospf/area/interface/poll-interval
                    leaf poll-interval {
                        type uint32;
                        units "seconds";
                        default "120";
                        description "Interval for Hellos to non-adjacent OSPF NBMA neighbor";
                    }

                    ///nokia-conf/configure/service/vprn/ospf/area/interface/priority
                    leaf priority {
                        type uint16 {
                            range "0..255";
                        }
                        default "1";
                        description "Interface priority in the DR election on the subnet";
                    }

                    ///nokia-conf/configure/service/vprn/ospf/area/interface/rib-priority
                    leaf rib-priority {
                        type types-ospf:rib-priority;
                        description "RIB priority for OSPF";
                    }

                    ///nokia-conf/configure/service/vprn/ospf/area/interface/load-balancing-weight
                    leaf load-balancing-weight {
                        type uint32 {
                            range "1..max";
                        }
                        description "Configure load-balancing-weight.";
                    }

                    ///nokia-conf/configure/service/vprn/ospf/area/interface/admin-state
                    leaf admin-state {
                        type types-sros:admin-state;
                        default "enable";
                        description "Administrative state of the OSPF interface";
                    }

                    ///nokia-conf/configure/service/vprn/ospf/area/interface/hello-interval
                    leaf hello-interval {
                        type uint32 {
                            range "1..65535";
                        }
                        units "seconds";
                        default "10";
                        description "Time between OSPF Hellos of this interface";
                    }

                    ///nokia-conf/configure/service/vprn/ospf/area/interface/dead-interval
                    leaf dead-interval {
                        type uint32 {
                            range "2..65535";
                        }
                        units "seconds";
                        description "OSPF wait time for Hellos before neighbor declared down";
                    }

                    ///nokia-conf/configure/service/vprn/ospf/area/interface/retransmit-interval
                    leaf retransmit-interval {
                        type uint32 {
                            range "1..1800";
                        }
                        units "seconds";
                        default "5";
                        description "Time before OSPF retransmits an unacknowledged LSA";
                    }

                    ///nokia-conf/configure/service/vprn/ospf/area/interface/transit-delay
                    leaf transit-delay {
                        type uint32 {
                            range "1..1800";
                        }
                        units "seconds";
                        default "1";
                        description "Required LSA transmit time";
                    }

                    ///nokia-conf/configure/service/vprn/ospf/area/interface/authentication-keychain
                    leaf authentication-keychain {
                        type leafref {
                            path "../../../../../../system/security/keychains/keychain/keychain-name";
                        }
                        description "TCP authentication keychain for the session";
                    }

                    ///nokia-conf/configure/service/vprn/ospf/area/interface/authentication-key
                    leaf authentication-key {
                        type types-sros:encrypted-leaf {
                            length "1..38";
                        }
                        description "Authentication key";
                    }

                    ///nokia-conf/configure/service/vprn/ospf/area/interface/authentication-type
                    leaf authentication-type {
                        type types-ospf:authentication-type;
                        description "Authentication type used on OSPF interface";
                    }

                    ///nokia-conf/configure/service/vprn/ospf/area/interface/apply-groups
                    leaf-list apply-groups {
                        type leafref {
                            path "../../../../../../groups/group/name";
                        }
                        max-elements 8;
                        ordered-by user;
                        description "Apply a configuration group at this level";
                    }

                    ///nokia-conf/configure/service/vprn/ospf/area/interface/apply-groups-exclude
                    leaf-list apply-groups-exclude {
                        type leafref {
                            path "../../../../../../groups/group/name";
                        }
                        max-elements 8;
                        ordered-by user;
                        description "Exclude a configuration group at this level";
                    }

                    ///nokia-conf/configure/service/vprn/ospf/area/interface/bfd-liveness
                    container bfd-liveness {
                        presence "Enable the bfd-liveness context";
                        description "Enable the bfd-liveness context";

                        ///nokia-conf/configure/service/vprn/ospf/area/interface/bfd-liveness/remain-down-on-failure
                        leaf remain-down-on-failure {
                            type boolean;
                            default "false";
                            description "Force adjacency down on failure until session returns";
                        }

                        ///nokia-conf/configure/service/vprn/ospf/area/interface/bfd-liveness/strict
                        leaf strict {
                            type boolean;
                            default "false";
                            description "Enable BFD strict mode";
                        }

                        ///nokia-conf/configure/service/vprn/ospf/area/interface/bfd-liveness/strict-mode-holddown
                        leaf strict-mode-holddown {
                            type int32 {
                                range "1..600";
                            }
                            units "seconds";
                            description "Adjacency up time delay after BFD session establishment";
                        }

                    } // container bfd-liveness

                    ///nokia-conf/configure/service/vprn/ospf/area/interface/loopfree-alternate
                    container loopfree-alternate {
                        description "Enter the loopfree-alternate context";

                        ///nokia-conf/configure/service/vprn/ospf/area/interface/loopfree-alternate/exclude
                        leaf exclude {
                            type boolean;
                            default "false";
                            description "Enable fast reroute at OSPF primary interface level";
                        }

                        ///nokia-conf/configure/service/vprn/ospf/area/interface/loopfree-alternate/policy-map
                        container policy-map {
                            presence "Enable the policy-map context";
                            description "Enable the policy-map context";

                            ///nokia-conf/configure/service/vprn/ospf/area/interface/loopfree-alternate/policy-map/route-nh-template
                            leaf route-nh-template {
                                type leafref {
                                    path "../../../../../../../../routing-options/route-next-hop-policy/template/template-name";
                                }
                                mandatory true;
                                description "Route next hop policy template name";
                            }

                        } // container policy-map

                    } // container loopfree-alternate

                    ///nokia-conf/configure/service/vprn/ospf/area/interface/message-digest-key
                    list message-digest-key {
                        key "key-id";
                        description "Enter the message-digest-key list instance";

                        ///nokia-conf/configure/service/vprn/ospf/area/interface/message-digest-key/key-id
                        leaf key-id {
                            type uint16 {
                                range "1..255";
                            }
                            description "Message digest index";
                        }

                        ///nokia-conf/configure/service/vprn/ospf/area/interface/message-digest-key/md5
                        leaf md5 {
                            type types-sros:encrypted-leaf {
                                length "1..51";
                            }
                            mandatory true;
                            description "MD5 hash key";
                        }

                        ///nokia-conf/configure/service/vprn/ospf/area/interface/message-digest-key/apply-groups
                        leaf-list apply-groups {
                            type leafref {
                                path "../../../../../../../groups/group/name";
                            }
                            max-elements 8;
                            ordered-by user;
                            description "Apply a configuration group at this level";
                        }

                        ///nokia-conf/configure/service/vprn/ospf/area/interface/message-digest-key/apply-groups-exclude
                        leaf-list apply-groups-exclude {
                            type leafref {
                                path "../../../../../../../groups/group/name";
                            }
                            max-elements 8;
                            ordered-by user;
                            description "Exclude a configuration group at this level";
                        }

                    } // list message-digest-key

                    ///nokia-conf/configure/service/vprn/ospf/area/interface/neighbor
                    list neighbor {
                        key "address";
                        description "Add a list entry for neighbor";

                        ///nokia-conf/configure/service/vprn/ospf/area/interface/neighbor/address
                        leaf address {
                            type types-sros:ipv4-unicast-address;
                            description "IPv4 address of the OSPFv2 neighbor";
                        }

                    } // list neighbor

                } // list interface

                ///nokia-conf/configure/service/vprn/ospf/area/virtual-link
                list virtual-link {
                    key "router-id transit-area";
                    description "Enter the virtual-link list instance";

                    ///nokia-conf/configure/service/vprn/ospf/area/virtual-link/router-id
                    leaf router-id {
                        type types-sros:ipv4-address;
                        description "Router identity of the virtual link neighbor";
                    }

                    ///nokia-conf/configure/service/vprn/ospf/area/virtual-link/transit-area
                    leaf transit-area {
                        type leafref {
                            path "../../../area/area-id";
                        }
                        description "Transit area that links backbone area to area without physical connection with the backbone";
                    }

                    ///nokia-conf/configure/service/vprn/ospf/area/virtual-link/admin-state
                    leaf admin-state {
                        type types-sros:admin-state;
                        default "enable";
                        description "Administrative state of the OSPF interface";
                    }

                    ///nokia-conf/configure/service/vprn/ospf/area/virtual-link/hello-interval
                    leaf hello-interval {
                        type uint32 {
                            range "1..65535";
                        }
                        units "seconds";
                        default "10";
                        description "Time between OSPF Hellos of this interface";
                    }

                    ///nokia-conf/configure/service/vprn/ospf/area/virtual-link/dead-interval
                    leaf dead-interval {
                        type uint32 {
                            range "2..65535";
                        }
                        units "seconds";
                        description "OSPF wait time for Hellos before neighbor declared down";
                    }

                    ///nokia-conf/configure/service/vprn/ospf/area/virtual-link/retransmit-interval
                    leaf retransmit-interval {
                        type uint32 {
                            range "1..1800";
                        }
                        units "seconds";
                        default "5";
                        description "Time before OSPF retransmits an unacknowledged LSA";
                    }

                    ///nokia-conf/configure/service/vprn/ospf/area/virtual-link/transit-delay
                    leaf transit-delay {
                        type uint32 {
                            range "1..1800";
                        }
                        units "seconds";
                        default "1";
                        description "Required LSA transmit time";
                    }

                    ///nokia-conf/configure/service/vprn/ospf/area/virtual-link/authentication-keychain
                    leaf authentication-keychain {
                        type leafref {
                            path "../../../../../../system/security/keychains/keychain/keychain-name";
                        }
                        description "TCP authentication keychain for the session";
                    }

                    ///nokia-conf/configure/service/vprn/ospf/area/virtual-link/authentication-key
                    leaf authentication-key {
                        type types-sros:encrypted-leaf {
                            length "1..38";
                        }
                        description "Authentication key";
                    }

                    ///nokia-conf/configure/service/vprn/ospf/area/virtual-link/authentication-type
                    leaf authentication-type {
                        type types-ospf:authentication-type;
                        description "Authentication type used on OSPF interface";
                    }

                    ///nokia-conf/configure/service/vprn/ospf/area/virtual-link/apply-groups
                    leaf-list apply-groups {
                        type leafref {
                            path "../../../../../../groups/group/name";
                        }
                        max-elements 8;
                        ordered-by user;
                        description "Apply a configuration group at this level";
                    }

                    ///nokia-conf/configure/service/vprn/ospf/area/virtual-link/apply-groups-exclude
                    leaf-list apply-groups-exclude {
                        type leafref {
                            path "../../../../../../groups/group/name";
                        }
                        max-elements 8;
                        ordered-by user;
                        description "Exclude a configuration group at this level";
                    }

                    ///nokia-conf/configure/service/vprn/ospf/area/virtual-link/message-digest-key
                    list message-digest-key {
                        key "key-id";
                        description "Enter the message-digest-key list instance";

                        ///nokia-conf/configure/service/vprn/ospf/area/virtual-link/message-digest-key/key-id
                        leaf key-id {
                            type uint16 {
                                range "1..255";
                            }
                            description "Message digest index";
                        }

                        ///nokia-conf/configure/service/vprn/ospf/area/virtual-link/message-digest-key/md5
                        leaf md5 {
                            type types-sros:encrypted-leaf {
                                length "1..51";
                            }
                            mandatory true;
                            description "MD5 hash key";
                        }

                        ///nokia-conf/configure/service/vprn/ospf/area/virtual-link/message-digest-key/apply-groups
                        leaf-list apply-groups {
                            type leafref {
                                path "../../../../../../../groups/group/name";
                            }
                            max-elements 8;
                            ordered-by user;
                            description "Apply a configuration group at this level";
                        }

                        ///nokia-conf/configure/service/vprn/ospf/area/virtual-link/message-digest-key/apply-groups-exclude
                        leaf-list apply-groups-exclude {
                            type leafref {
                                path "../../../../../../../groups/group/name";
                            }
                            max-elements 8;
                            ordered-by user;
                            description "Exclude a configuration group at this level";
                        }

                    } // list message-digest-key

                } // list virtual-link

                ///nokia-conf/configure/service/vprn/ospf/area/sham-link
                list sham-link {
                    key "interface ip-address";
                    description "Enter the sham-link list instance";

                    ///nokia-conf/configure/service/vprn/ospf/area/sham-link/interface
                    leaf interface {
                        type types-sros:interface-name;
                        description "Local interface name used for the sham-link";
                    }

                    ///nokia-conf/configure/service/vprn/ospf/area/sham-link/ip-address
                    leaf ip-address {
                        type types-sros:ipv4-unicast-address;
                        description "IP address of the sham-link neighbor";
                    }

                    ///nokia-conf/configure/service/vprn/ospf/area/sham-link/admin-state
                    leaf admin-state {
                        type types-sros:admin-state;
                        default "enable";
                        description "Administrative state of the OSPF interface";
                    }

                    ///nokia-conf/configure/service/vprn/ospf/area/sham-link/hello-interval
                    leaf hello-interval {
                        type uint32 {
                            range "1..65535";
                        }
                        units "seconds";
                        default "10";
                        description "Time between OSPF Hellos of this interface";
                    }

                    ///nokia-conf/configure/service/vprn/ospf/area/sham-link/dead-interval
                    leaf dead-interval {
                        type uint32 {
                            range "2..65535";
                        }
                        units "seconds";
                        description "OSPF wait time for Hellos before neighbor declared down";
                    }

                    ///nokia-conf/configure/service/vprn/ospf/area/sham-link/retransmit-interval
                    leaf retransmit-interval {
                        type uint32 {
                            range "1..1800";
                        }
                        units "seconds";
                        default "5";
                        description "Time before OSPF retransmits an unacknowledged LSA";
                    }

                    ///nokia-conf/configure/service/vprn/ospf/area/sham-link/transit-delay
                    leaf transit-delay {
                        type uint32 {
                            range "1..1800";
                        }
                        units "seconds";
                        default "1";
                        description "Required LSA transmit time";
                    }

                    ///nokia-conf/configure/service/vprn/ospf/area/sham-link/authentication-keychain
                    leaf authentication-keychain {
                        type leafref {
                            path "../../../../../../system/security/keychains/keychain/keychain-name";
                        }
                        description "TCP authentication keychain for the session";
                    }

                    ///nokia-conf/configure/service/vprn/ospf/area/sham-link/authentication-key
                    leaf authentication-key {
                        type types-sros:encrypted-leaf {
                            length "1..38";
                        }
                        description "Authentication key to send and receive OSPF packets";
                    }

                    ///nokia-conf/configure/service/vprn/ospf/area/sham-link/authentication-type
                    leaf authentication-type {
                        type types-ospf:authentication-type;
                        description "Authentication type to be used";
                    }

                    ///nokia-conf/configure/service/vprn/ospf/area/sham-link/metric
                    leaf metric {
                        type uint32 {
                            range "1..65535";
                        }
                        default "1";
                        description "Explicit route cost metric that is applied to the sham link";
                    }

                    ///nokia-conf/configure/service/vprn/ospf/area/sham-link/apply-groups
                    leaf-list apply-groups {
                        type leafref {
                            path "../../../../../../groups/group/name";
                        }
                        max-elements 8;
                        ordered-by user;
                        description "Apply a configuration group at this level";
                    }

                    ///nokia-conf/configure/service/vprn/ospf/area/sham-link/apply-groups-exclude
                    leaf-list apply-groups-exclude {
                        type leafref {
                            path "../../../../../../groups/group/name";
                        }
                        max-elements 8;
                        ordered-by user;
                        description "Exclude a configuration group at this level";
                    }

                    ///nokia-conf/configure/service/vprn/ospf/area/sham-link/message-digest-key
                    list message-digest-key {
                        key "key-id";
                        description "Enter the message-digest-key list instance";

                        ///nokia-conf/configure/service/vprn/ospf/area/sham-link/message-digest-key/key-id
                        leaf key-id {
                            type uint16 {
                                range "1..255";
                            }
                            description "Message digest index";
                        }

                        ///nokia-conf/configure/service/vprn/ospf/area/sham-link/message-digest-key/md5
                        leaf md5 {
                            type types-sros:encrypted-leaf {
                                length "1..51";
                            }
                            mandatory true;
                            description "MD5 key or hash key";
                        }

                        ///nokia-conf/configure/service/vprn/ospf/area/sham-link/message-digest-key/apply-groups
                        leaf-list apply-groups {
                            type leafref {
                                path "../../../../../../../groups/group/name";
                            }
                            max-elements 8;
                            ordered-by user;
                            description "Apply a configuration group at this level";
                        }

                        ///nokia-conf/configure/service/vprn/ospf/area/sham-link/message-digest-key/apply-groups-exclude
                        leaf-list apply-groups-exclude {
                            type leafref {
                                path "../../../../../../../groups/group/name";
                            }
                            max-elements 8;
                            ordered-by user;
                            description "Exclude a configuration group at this level";
                        }

                    } // list message-digest-key

                } // list sham-link

            } // list area

        } // list ospf

    } // grouping conf-svc-vprn-ospf

}
