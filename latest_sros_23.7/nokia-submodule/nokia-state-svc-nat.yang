submodule nokia-state-svc-nat {

    yang-version "1.1";

    belongs-to nokia-state { prefix "state"; }

    import ietf-yang-types                { prefix "yang"; }
    import nokia-sros-yang-extensions     { prefix "sros-ext"; }
    import nokia-types-isa                { prefix "types-isa"; }
    import nokia-types-nat                { prefix "types-nat"; }
    import nokia-types-services           { prefix "types-services"; }
    import nokia-types-sros               { prefix "types-sros"; }

    include nokia-state-esa;

    sros-ext:sros-major-release "rel23";
    organization "Nokia";
    contact
        "Nokia SR OS Support
         Web: <http://www.nokia.com>";
    description
        "Nokia YANG Data model with operational state for NAT configuration common to all router instances on SR OS based routers.

         Copyright 2016 Nokia. All rights reserved. Reproduction of this document
         is authorized on the condition that the foregoing copyright notice is included.

         This nokia-state-svc-nat YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-04-28";

    grouping state-svc-nat {
        ///nokia-state/state/service/nat
        container nat {
            description "Enable the nat context";

            ///nokia-state/state/service/nat/nat-policy
            list nat-policy {
                key "name";
                description "Enter the nat-policy list instance";

                ///nokia-state/state/service/nat/nat-policy/name
                leaf name {
                    type types-sros:external-named-item;
                    description "NAT policy name";
                }

                ///nokia-state/state/service/nat/nat-policy/statistics
                container statistics {
                    description "Enter the statistics context";

                    ///nokia-state/state/service/nat/nat-policy/statistics/mda
                    list mda {
                        key "mda-id";
                        description "Enter the mda list instance";

                        ///nokia-state/state/service/nat/nat-policy/statistics/mda/mda-id
                        leaf mda-id {
                            type types-isa:slot-mda;
                            description "An ISA NAT group MDA";
                        }

                        ///nokia-state/state/service/nat/nat-policy/statistics/mda/hosts
                        container hosts {
                            description "Enter the hosts context";

                            ///nokia-state/state/service/nat/nat-policy/statistics/mda/hosts/active
                            leaf active {
                                type uint32;
                                description "Number of active hosts";
                            }

                            ///nokia-state/state/service/nat/nat-policy/statistics/mda/hosts/peak
                            leaf peak {
                                type uint32;
                                description "Maximum number of hosts that were active together up to this point in time";
                            }

                        } // container hosts

                        ///nokia-state/state/service/nat/nat-policy/statistics/mda/sessions
                        container sessions {
                            description "Enter the sessions context";

                            ///nokia-state/state/service/nat/nat-policy/statistics/mda/sessions/tcp
                            container tcp {
                                description "Enter the tcp context";

                                ///nokia-state/state/service/nat/nat-policy/statistics/mda/sessions/tcp/created
                                leaf created {
                                    type uint32;
                                    description "Created TCP sessions";
                                }

                                ///nokia-state/state/service/nat/nat-policy/statistics/mda/sessions/tcp/destroyed
                                leaf destroyed {
                                    type uint32;
                                    description "Destroyed TCP sessions";
                                }

                            } // container tcp

                            ///nokia-state/state/service/nat/nat-policy/statistics/mda/sessions/udp
                            container udp {
                                description "Enter the udp context";

                                ///nokia-state/state/service/nat/nat-policy/statistics/mda/sessions/udp/created
                                leaf created {
                                    type uint32;
                                    description "Created UDP sessions";
                                }

                                ///nokia-state/state/service/nat/nat-policy/statistics/mda/sessions/udp/destroyed
                                leaf destroyed {
                                    type uint32;
                                    description "Destroyed UDP sessions";
                                }

                            } // container udp

                            ///nokia-state/state/service/nat/nat-policy/statistics/mda/sessions/icmp-query
                            container icmp-query {
                                description "Enter the icmp-query context";

                                ///nokia-state/state/service/nat/nat-policy/statistics/mda/sessions/icmp-query/created
                                leaf created {
                                    type uint32;
                                    description "Created ICPM query sessions";
                                }

                                ///nokia-state/state/service/nat/nat-policy/statistics/mda/sessions/icmp-query/destroyed
                                leaf destroyed {
                                    type uint32;
                                    description "Destroyed ICPM query sessions";
                                }

                            } // container icmp-query

                            ///nokia-state/state/service/nat/nat-policy/statistics/mda/sessions/gre-query
                            container gre-query {
                                description "Enter the gre-query context";

                                ///nokia-state/state/service/nat/nat-policy/statistics/mda/sessions/gre-query/created
                                leaf created {
                                    type uint32;
                                    description "Created GRE query sessions";
                                }

                                ///nokia-state/state/service/nat/nat-policy/statistics/mda/sessions/gre-query/destroyed
                                leaf destroyed {
                                    type uint32;
                                    description "Destroyed GRE query sessions";
                                }

                            } // container gre-query

                        } // container sessions

                    } // list mda

                    ///nokia-state/state/service/nat/nat-policy/statistics/esa
                    list esa {
                        key "esa-id vm";
                        description "Enter the esa list instance";

                        ///nokia-state/state/service/nat/nat-policy/statistics/esa/esa-id
                        leaf esa-id {
                            type leafref {
                                path "../../../../../../esa/esa-id";
                            }
                            description "ESA used by the ISA NAT group";
                        }

                        ///nokia-state/state/service/nat/nat-policy/statistics/esa/vm
                        leaf vm {
                            type leafref {
                                path "../../../../../../esa[esa-id=current()/../esa-id]/vm/vm-id";
                            }
                            description "ESA-VM used by the ISA NAT group";
                        }

                        ///nokia-state/state/service/nat/nat-policy/statistics/esa/hosts
                        container hosts {
                            description "Enter the hosts context";

                            ///nokia-state/state/service/nat/nat-policy/statistics/esa/hosts/active
                            leaf active {
                                type uint32;
                                description "Number of active hosts";
                            }

                            ///nokia-state/state/service/nat/nat-policy/statistics/esa/hosts/peak
                            leaf peak {
                                type uint32;
                                description "Maximum number of hosts that were active together up to this point in time";
                            }

                        } // container hosts

                        ///nokia-state/state/service/nat/nat-policy/statistics/esa/sessions
                        container sessions {
                            description "Enter the sessions context";

                            ///nokia-state/state/service/nat/nat-policy/statistics/esa/sessions/tcp
                            container tcp {
                                description "Enter the tcp context";

                                ///nokia-state/state/service/nat/nat-policy/statistics/esa/sessions/tcp/created
                                leaf created {
                                    type uint32;
                                    description "Created TCP sessions";
                                }

                                ///nokia-state/state/service/nat/nat-policy/statistics/esa/sessions/tcp/destroyed
                                leaf destroyed {
                                    type uint32;
                                    description "Destroyed TCP sessions";
                                }

                            } // container tcp

                            ///nokia-state/state/service/nat/nat-policy/statistics/esa/sessions/udp
                            container udp {
                                description "Enter the udp context";

                                ///nokia-state/state/service/nat/nat-policy/statistics/esa/sessions/udp/created
                                leaf created {
                                    type uint32;
                                    description "Created UDP sessions";
                                }

                                ///nokia-state/state/service/nat/nat-policy/statistics/esa/sessions/udp/destroyed
                                leaf destroyed {
                                    type uint32;
                                    description "Destroyed UDP sessions";
                                }

                            } // container udp

                            ///nokia-state/state/service/nat/nat-policy/statistics/esa/sessions/icmp-query
                            container icmp-query {
                                description "Enter the icmp-query context";

                                ///nokia-state/state/service/nat/nat-policy/statistics/esa/sessions/icmp-query/created
                                leaf created {
                                    type uint32;
                                    description "Created ICPM query sessions";
                                }

                                ///nokia-state/state/service/nat/nat-policy/statistics/esa/sessions/icmp-query/destroyed
                                leaf destroyed {
                                    type uint32;
                                    description "Destroyed ICPM query sessions";
                                }

                            } // container icmp-query

                            ///nokia-state/state/service/nat/nat-policy/statistics/esa/sessions/gre-query
                            container gre-query {
                                description "Enter the gre-query context";

                                ///nokia-state/state/service/nat/nat-policy/statistics/esa/sessions/gre-query/created
                                leaf created {
                                    type uint32;
                                    description "Created GRE query sessions";
                                }

                                ///nokia-state/state/service/nat/nat-policy/statistics/esa/sessions/gre-query/destroyed
                                leaf destroyed {
                                    type uint32;
                                    description "Destroyed GRE query sessions";
                                }

                            } // container gre-query

                        } // container sessions

                    } // list esa

                } // container statistics

            } // list nat-policy

            ///nokia-state/state/service/nat/deterministic-script
            container deterministic-script {
                description "Enter the deterministic-script context";

                ///nokia-state/state/service/nat/deterministic-script/saved
                leaf saved {
                    type boolean;
                    description
                        "Informs the operator whether the deterministic script for logging
                         purposes has been saved when deterministic NAT is configured

                         To preserve logging information, the script generated by deterministic NAT
                         that contains information about the deterministic mappings should be saved
                         locally on SR or on a remote server. The script is NOT saved automatically
                         and instead it should be explicitly saved by the operator.";
                }

                ///nokia-state/state/service/nat/deterministic-script/last-save-result
                leaf last-save-result {
                    type types-nat:deterministic-script-save-result;
                    description "Result of the last save action";
                }

                ///nokia-state/state/service/nat/deterministic-script/last-save-time
                leaf last-save-time {
                    type types-sros:date-time;
                    description "When the Deterministic script was last successfully saved";
                }

            } // container deterministic-script

            ///nokia-state/state/service/nat/map-t
            container map-t {
                description "Enter the map-t context";

                ///nokia-state/state/service/nat/map-t/domain
                list domain {
                    key "name";
                    description "Enter the domain list instance";

                    ///nokia-state/state/service/nat/map-t/domain/name
                    leaf name {
                        type types-sros:named-item;
                        description "MAP domain name";
                    }

                    ///nokia-state/state/service/nat/map-t/domain/service-name
                    leaf service-name {
                        type types-services:service-name;
                        description "Routing context in which the domain is instantiated and active";
                    }

                    ///nokia-state/state/service/nat/map-t/domain/mapping-rule
                    list mapping-rule {
                        key "rule-name";
                        description "Enter the mapping-rule list instance";

                        ///nokia-state/state/service/nat/map-t/domain/mapping-rule/rule-name
                        leaf rule-name {
                            type types-sros:named-item;
                            description "The name that identifies this mapping rule";
                        }

                        ///nokia-state/state/service/nat/map-t/domain/mapping-rule/address-sharing-ratio
                        leaf address-sharing-ratio {
                            type yang:gauge32;
                            description
                                "Number of MAP Customer Edge (CE) sharing the same IP address.
                                 The value zero indicates that each CE is assigned its own IPv4 prefix.";
                        }

                        ///nokia-state/state/service/nat/map-t/domain/mapping-rule/excluded-ports
                        leaf excluded-ports {
                            type yang:gauge32;
                            description "Number of ports excluded from mapping with this rule";
                        }

                        ///nokia-state/state/service/nat/map-t/domain/mapping-rule/ports-per-user
                        leaf ports-per-user {
                            type yang:gauge32;
                            description "Number of ports available per MAP Customer Edge (CE)";
                        }

                    } // list mapping-rule

                } // list domain

                ///nokia-state/state/service/nat/map-t/statistics
                container statistics {
                    description "Enter the statistics context";

                    ///nokia-state/state/service/nat/map-t/statistics/fragmentation
                    container fragmentation {
                        description "Enter the fragmentation context";

                        ///nokia-state/state/service/nat/map-t/statistics/fragmentation/rx-resolved
                        leaf rx-resolved {
                            type yang:counter64;
                            description "Fragments that are resolved without buffering";
                        }

                        ///nokia-state/state/service/nat/map-t/statistics/fragmentation/rx-unresolved
                        leaf rx-unresolved {
                            type yang:counter64;
                            description
                                "Number of fragments that were queued in the system
                                 since the last clearing of the stats";
                        }

                        ///nokia-state/state/service/nat/map-t/statistics/fragmentation/tx-frags
                        leaf tx-frags {
                            type yang:counter64;
                            description
                                "Number of fragments that were resolved and
                                 forwarded out of the fragmentation logic";
                        }

                        ///nokia-state/state/service/nat/map-t/statistics/fragmentation/dropped
                        leaf dropped {
                            type yang:counter64;
                            description "Number of dropped fragments";
                        }

                        ///nokia-state/state/service/nat/map-t/statistics/fragmentation/created-flows
                        leaf created-flows {
                            type yang:counter64;
                            description
                                "Number of flow records created since the last
                                 clearing of the statistics. Flow record creation
                                 is triggered by the first fragment of a packet.";
                        }

                        ///nokia-state/state/service/nat/map-t/statistics/fragmentation/flow-collisions
                        leaf flow-collisions {
                            type yang:counter64;
                            description
                                "Number of flow collisions (overlapping first
                                 fragments) since the last clearing of the statistics";
                        }

                        ///nokia-state/state/service/nat/map-t/statistics/fragmentation/exceeded-max-flows
                        leaf exceeded-max-flows {
                            type yang:counter64;
                            description "Number of times the maximum number of flows is exceeded";
                        }

                        ///nokia-state/state/service/nat/map-t/statistics/fragmentation/exceeded-max-timeouts
                        leaf exceeded-max-timeouts {
                            type yang:counter64;
                            description
                                "Number of fragments that have timed out since the
                                 last clearing of the statistics";
                        }

                        ///nokia-state/state/service/nat/map-t/statistics/fragmentation/exceeded-max-buffers
                        leaf exceeded-max-buffers {
                            type yang:counter64;
                            description "Number of times the maximum number of buffers is exceeded";
                        }

                        ///nokia-state/state/service/nat/map-t/statistics/fragmentation/exceeded-max-buffers-per-flow
                        leaf exceeded-max-buffers-per-flow {
                            type yang:counter64;
                            description
                                "Number of times a fragment count per flow has
                                 exceeded the maximum value";
                        }

                        ///nokia-state/state/service/nat/map-t/statistics/fragmentation/in-use-flows
                        leaf in-use-flows {
                            type types-sros:percent;
                            description "Percentage of currently processed flows (flow records)";
                        }

                        ///nokia-state/state/service/nat/map-t/statistics/fragmentation/max-flows
                        leaf max-flows {
                            type types-sros:percent;
                            description
                                "Maximum number of flows (flow records) reached
                                 since the last clearing of the statistics";
                        }

                        ///nokia-state/state/service/nat/map-t/statistics/fragmentation/in-use-buffers
                        leaf in-use-buffers {
                            type types-sros:percent;
                            description "Percentage of in-use buffers";
                        }

                        ///nokia-state/state/service/nat/map-t/statistics/fragmentation/max-buffers
                        leaf max-buffers {
                            type types-sros:percent;
                            description
                                "Maximum number of buffers allocated in the system
                                 since the last clearing of the statistics";
                        }

                    } // container fragmentation

                } // container statistics

            } // container map-t

            ///nokia-state/state/service/nat/statistics
            container statistics {
                description "Enter the statistics context";

                ///nokia-state/state/service/nat/statistics/dropped
                container dropped {
                    description "Enter the dropped context";

                    ///nokia-state/state/service/nat/statistics/dropped/radius-interim-updates
                    leaf radius-interim-updates {
                        type yang:counter64;
                        description
                            "The number of dropped RADIUS accounting interim update
                             messages generated by NAT";
                    }

                } // container dropped

            } // container statistics

        } // container nat

    } // grouping state-svc-nat

}
