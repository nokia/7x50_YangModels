submodule nokia-conf-svc-vprn-msdp {

    yang-version "1.1";

    belongs-to nokia-conf { prefix "conf"; }

    import nokia-sros-yang-extensions     { prefix "sros-ext"; }
    import nokia-types-sros               { prefix "types-sros"; }

    include nokia-conf-groups;
    include nokia-conf-policy-options;

    sros-ext:sros-major-release "rel23";
    organization "Nokia";
    contact
        "Nokia SR OS Support
         Web: <http://www.nokia.com>";
    description
        "Nokia YANG Data model to configure  The Multicast Source Discovery Protocol (MSDP) is used to connect multicast routing domains. on SR OS based routers.

         Copyright 2016 Nokia. All rights reserved. Reproduction of this document
         is authorized on the condition that the foregoing copyright notice is included.

         This nokia-conf-svc-vprn-msdp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping conf-svc-vprn-msdp {
        ///nokia-conf/configure/service/vprn/msdp
        container msdp {
            presence "Enable the msdp context";
            description "Enable the msdp context";

            ///nokia-conf/configure/service/vprn/msdp/active-source-limit
            leaf active-source-limit {
                type int32 {
                    range "0..1000000";
                }
                description "Maximum number of active messages accepted by MSDP";
            }

            ///nokia-conf/configure/service/vprn/msdp/admin-state
            leaf admin-state {
                type types-sros:admin-state;
                default "enable";
                description "Administrative state of MSDP";
            }

            ///nokia-conf/configure/service/vprn/msdp/export-policy
            leaf-list export-policy {
                type leafref {
                    path "../../../../policy-options/policy-statement/name";
                }
                max-elements 5;
                ordered-by user;
                description "Policies to export source active state into MSDP";
            }

            ///nokia-conf/configure/service/vprn/msdp/import-policy
            leaf-list import-policy {
                type leafref {
                    path "../../../../policy-options/policy-statement/name";
                }
                max-elements 5;
                ordered-by user;
                description "Policy to import source active state from MSDP";
            }

            ///nokia-conf/configure/service/vprn/msdp/local-address
            leaf local-address {
                type types-sros:ipv4-unicast-address;
                description "Local end of an MSDP session";
            }

            ///nokia-conf/configure/service/vprn/msdp/data-encapsulation
            leaf data-encapsulation {
                type boolean;
                default "true";
                description "Enable encapsulation of multicast data used by MSDP";
            }

            ///nokia-conf/configure/service/vprn/msdp/rpf-table
            leaf rpf-table {
                type enumeration {
                    enum rtable-m                       { value 0; }
                    enum rtable-u                       { value 1; }
                    enum both                           { value 2; }
                }
                default "rtable-u";
                description "Route tables for RPF lookup";
            }

            ///nokia-conf/configure/service/vprn/msdp/source-active-cache-lifetime
            leaf source-active-cache-lifetime {
                type uint32 {
                    range "90..600";
                }
                units "seconds";
                default "90";
                description "Lifetime of SA entries in the cache";
            }

            ///nokia-conf/configure/service/vprn/msdp/apply-groups
            leaf-list apply-groups {
                type leafref {
                    path "../../../../groups/group/name";
                }
                max-elements 8;
                ordered-by user;
                description "Apply a configuration group at this level";
            }

            ///nokia-conf/configure/service/vprn/msdp/apply-groups-exclude
            leaf-list apply-groups-exclude {
                type leafref {
                    path "../../../../groups/group/name";
                }
                max-elements 8;
                ordered-by user;
                description "Exclude a configuration group at this level";
            }

            ///nokia-conf/configure/service/vprn/msdp/receive-message-rate
            container receive-message-rate {
                description "Enter the receive-message-rate context";

                ///nokia-conf/configure/service/vprn/msdp/receive-message-rate/rate
                leaf rate {
                    type uint32 {
                        range "10..10000";
                    }
                    description "Number of MSDP messages read from the TCP session";
                }

                ///nokia-conf/configure/service/vprn/msdp/receive-message-rate/time
                leaf time {
                    type uint32 {
                        range "1..600";
                    }
                    units "seconds";
                    description "Limit of MSDP messages read from the TCP session";
                }

                ///nokia-conf/configure/service/vprn/msdp/receive-message-rate/threshold
                leaf threshold {
                    type uint32 {
                        range "1..1000000";
                    }
                    description "Limit for MSDP messages read from the TCP session";
                }

            } // container receive-message-rate

            ///nokia-conf/configure/service/vprn/msdp/group
            list group {
                key "name";
                description "Enter the group list instance";

                ///nokia-conf/configure/service/vprn/msdp/group/name
                leaf name {
                    type types-sros:named-item;
                    description "MSDP group name";
                }

                ///nokia-conf/configure/service/vprn/msdp/group/active-source-limit
                leaf active-source-limit {
                    type int32 {
                        range "0..1000000";
                    }
                    description "Maximum number of active messages accepted by MSDP";
                }

                ///nokia-conf/configure/service/vprn/msdp/group/admin-state
                leaf admin-state {
                    type types-sros:admin-state;
                    default "enable";
                    description "Administrative state of MSDP";
                }

                ///nokia-conf/configure/service/vprn/msdp/group/export-policy
                leaf-list export-policy {
                    type leafref {
                        path "../../../../../policy-options/policy-statement/name";
                    }
                    max-elements 5;
                    ordered-by user;
                    description "Policies to export source active state into MSDP";
                }

                ///nokia-conf/configure/service/vprn/msdp/group/import-policy
                leaf-list import-policy {
                    type leafref {
                        path "../../../../../policy-options/policy-statement/name";
                    }
                    max-elements 5;
                    ordered-by user;
                    description "Policy to import source active state from MSDP";
                }

                ///nokia-conf/configure/service/vprn/msdp/group/local-address
                leaf local-address {
                    type types-sros:ipv4-unicast-address;
                    description "Local end of an MSDP session";
                }

                ///nokia-conf/configure/service/vprn/msdp/group/mode
                leaf mode {
                    type enumeration {
                        enum standard                       { value 1; }
                        enum mesh-group                     { value 2; }
                    }
                    default "standard";
                    description "Topology of groups of peers";
                }

                ///nokia-conf/configure/service/vprn/msdp/group/apply-groups
                leaf-list apply-groups {
                    type leafref {
                        path "../../../../../groups/group/name";
                    }
                    max-elements 8;
                    ordered-by user;
                    description "Apply a configuration group at this level";
                }

                ///nokia-conf/configure/service/vprn/msdp/group/apply-groups-exclude
                leaf-list apply-groups-exclude {
                    type leafref {
                        path "../../../../../groups/group/name";
                    }
                    max-elements 8;
                    ordered-by user;
                    description "Exclude a configuration group at this level";
                }

                ///nokia-conf/configure/service/vprn/msdp/group/receive-message-rate
                container receive-message-rate {
                    description "Enter the receive-message-rate context";

                    ///nokia-conf/configure/service/vprn/msdp/group/receive-message-rate/rate
                    leaf rate {
                        type uint32 {
                            range "10..10000";
                        }
                        description "Number of MSDP messages read from the TCP session";
                    }

                    ///nokia-conf/configure/service/vprn/msdp/group/receive-message-rate/time
                    leaf time {
                        type uint32 {
                            range "1..600";
                        }
                        units "seconds";
                        description "Limit of MSDP messages read from the TCP session";
                    }

                    ///nokia-conf/configure/service/vprn/msdp/group/receive-message-rate/threshold
                    leaf threshold {
                        type uint32 {
                            range "1..1000000";
                        }
                        description "Limit for MSDP messages read from the TCP session";
                    }

                } // container receive-message-rate

                ///nokia-conf/configure/service/vprn/msdp/group/peer
                list peer {
                    key "ip-address";
                    description "Enter the peer list instance";

                    ///nokia-conf/configure/service/vprn/msdp/group/peer/ip-address
                    leaf ip-address {
                        type types-sros:ipv4-unicast-address;
                        description "IP address of the remote MSDP router for peering";
                    }

                    ///nokia-conf/configure/service/vprn/msdp/group/peer/active-source-limit
                    leaf active-source-limit {
                        type int32 {
                            range "0..1000000";
                        }
                        description "Maximum number of active messages accepted by MSDP";
                    }

                    ///nokia-conf/configure/service/vprn/msdp/group/peer/admin-state
                    leaf admin-state {
                        type types-sros:admin-state;
                        default "enable";
                        description "Administrative state of MSDP";
                    }

                    ///nokia-conf/configure/service/vprn/msdp/group/peer/export-policy
                    leaf-list export-policy {
                        type leafref {
                            path "../../../../../../policy-options/policy-statement/name";
                        }
                        max-elements 5;
                        ordered-by user;
                        description "Policies to export source active state into MSDP";
                    }

                    ///nokia-conf/configure/service/vprn/msdp/group/peer/import-policy
                    leaf-list import-policy {
                        type leafref {
                            path "../../../../../../policy-options/policy-statement/name";
                        }
                        max-elements 5;
                        ordered-by user;
                        description "Policy to import source active state from MSDP";
                    }

                    ///nokia-conf/configure/service/vprn/msdp/group/peer/local-address
                    leaf local-address {
                        type types-sros:ipv4-unicast-address;
                        description "Local end of an MSDP session";
                    }

                    ///nokia-conf/configure/service/vprn/msdp/group/peer/default-peer
                    leaf default-peer {
                        type boolean;
                        default "false";
                        description "Enable/Disable default peer as MSDP peer";
                    }

                    ///nokia-conf/configure/service/vprn/msdp/group/peer/authentication-key
                    leaf authentication-key {
                        type types-sros:encrypted-leaf {
                            length "1..370";
                        }
                        description "MD5 authentication key for the MSDP peering session";
                    }

                    ///nokia-conf/configure/service/vprn/msdp/group/peer/apply-groups
                    leaf-list apply-groups {
                        type leafref {
                            path "../../../../../../groups/group/name";
                        }
                        max-elements 8;
                        ordered-by user;
                        description "Apply a configuration group at this level";
                    }

                    ///nokia-conf/configure/service/vprn/msdp/group/peer/apply-groups-exclude
                    leaf-list apply-groups-exclude {
                        type leafref {
                            path "../../../../../../groups/group/name";
                        }
                        max-elements 8;
                        ordered-by user;
                        description "Exclude a configuration group at this level";
                    }

                    ///nokia-conf/configure/service/vprn/msdp/group/peer/receive-message-rate
                    container receive-message-rate {
                        description "Enter the receive-message-rate context";

                        ///nokia-conf/configure/service/vprn/msdp/group/peer/receive-message-rate/rate
                        leaf rate {
                            type uint32 {
                                range "10..10000";
                            }
                            description "Number of MSDP messages read from the TCP session";
                        }

                        ///nokia-conf/configure/service/vprn/msdp/group/peer/receive-message-rate/time
                        leaf time {
                            type uint32 {
                                range "1..600";
                            }
                            units "seconds";
                            description "Limit of MSDP messages read from the TCP session";
                        }

                        ///nokia-conf/configure/service/vprn/msdp/group/peer/receive-message-rate/threshold
                        leaf threshold {
                            type uint32 {
                                range "1..1000000";
                            }
                            description "Limit for MSDP messages read from the TCP session";
                        }

                    } // container receive-message-rate

                } // list peer

            } // list group

            ///nokia-conf/configure/service/vprn/msdp/peer
            list peer {
                key "ip-address";
                description "Enter the peer list instance";

                ///nokia-conf/configure/service/vprn/msdp/peer/ip-address
                leaf ip-address {
                    type types-sros:ipv4-unicast-address;
                    description "IP address of the remote MSDP router for peering";
                }

                ///nokia-conf/configure/service/vprn/msdp/peer/active-source-limit
                leaf active-source-limit {
                    type int32 {
                        range "0..1000000";
                    }
                    description "Maximum number of active messages accepted by MSDP";
                }

                ///nokia-conf/configure/service/vprn/msdp/peer/admin-state
                leaf admin-state {
                    type types-sros:admin-state;
                    default "enable";
                    description "Administrative state of MSDP";
                }

                ///nokia-conf/configure/service/vprn/msdp/peer/export-policy
                leaf-list export-policy {
                    type leafref {
                        path "../../../../../policy-options/policy-statement/name";
                    }
                    max-elements 5;
                    ordered-by user;
                    description "Policies to export source active state into MSDP";
                }

                ///nokia-conf/configure/service/vprn/msdp/peer/import-policy
                leaf-list import-policy {
                    type leafref {
                        path "../../../../../policy-options/policy-statement/name";
                    }
                    max-elements 5;
                    ordered-by user;
                    description "Policy to import source active state from MSDP";
                }

                ///nokia-conf/configure/service/vprn/msdp/peer/local-address
                leaf local-address {
                    type types-sros:ipv4-unicast-address;
                    description "Local end of an MSDP session";
                }

                ///nokia-conf/configure/service/vprn/msdp/peer/default-peer
                leaf default-peer {
                    type boolean;
                    default "false";
                    description "Enable/Disable default peer as MSDP peer";
                }

                ///nokia-conf/configure/service/vprn/msdp/peer/authentication-key
                leaf authentication-key {
                    type types-sros:encrypted-leaf {
                        length "1..370";
                    }
                    description "MD5 authentication key for the MSDP peering session";
                }

                ///nokia-conf/configure/service/vprn/msdp/peer/apply-groups
                leaf-list apply-groups {
                    type leafref {
                        path "../../../../../groups/group/name";
                    }
                    max-elements 8;
                    ordered-by user;
                    description "Apply a configuration group at this level";
                }

                ///nokia-conf/configure/service/vprn/msdp/peer/apply-groups-exclude
                leaf-list apply-groups-exclude {
                    type leafref {
                        path "../../../../../groups/group/name";
                    }
                    max-elements 8;
                    ordered-by user;
                    description "Exclude a configuration group at this level";
                }

                ///nokia-conf/configure/service/vprn/msdp/peer/receive-message-rate
                container receive-message-rate {
                    description "Enter the receive-message-rate context";

                    ///nokia-conf/configure/service/vprn/msdp/peer/receive-message-rate/rate
                    leaf rate {
                        type uint32 {
                            range "10..10000";
                        }
                        description "Number of MSDP messages read from the TCP session";
                    }

                    ///nokia-conf/configure/service/vprn/msdp/peer/receive-message-rate/time
                    leaf time {
                        type uint32 {
                            range "1..600";
                        }
                        units "seconds";
                        description "Limit of MSDP messages read from the TCP session";
                    }

                    ///nokia-conf/configure/service/vprn/msdp/peer/receive-message-rate/threshold
                    leaf threshold {
                        type uint32 {
                            range "1..1000000";
                        }
                        description "Limit for MSDP messages read from the TCP session";
                    }

                } // container receive-message-rate

            } // list peer

            ///nokia-conf/configure/service/vprn/msdp/source
            list source {
                key "ip-prefix";
                description "Enter the source list instance";

                ///nokia-conf/configure/service/vprn/msdp/source/ip-prefix
                leaf ip-prefix {
                    type types-sros:ipv4-unicast-prefix;
                    description "Source IP address for accepted active source messages";
                }

                ///nokia-conf/configure/service/vprn/msdp/source/active-source-limit
                leaf active-source-limit {
                    type int32 {
                        range "0..1000000";
                    }
                    description "Number of active source messages accepted by MSDP";
                }

                ///nokia-conf/configure/service/vprn/msdp/source/apply-groups
                leaf-list apply-groups {
                    type leafref {
                        path "../../../../../groups/group/name";
                    }
                    max-elements 8;
                    ordered-by user;
                    description "Apply a configuration group at this level";
                }

                ///nokia-conf/configure/service/vprn/msdp/source/apply-groups-exclude
                leaf-list apply-groups-exclude {
                    type leafref {
                        path "../../../../../groups/group/name";
                    }
                    max-elements 8;
                    ordered-by user;
                    description "Exclude a configuration group at this level";
                }

            } // list source

        } // container msdp

    } // grouping conf-svc-vprn-msdp

}
