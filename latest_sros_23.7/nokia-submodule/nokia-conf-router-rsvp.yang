submodule nokia-conf-router-rsvp {

    yang-version "1.1";

    belongs-to nokia-conf { prefix "conf"; }

    import nokia-sros-yang-extensions     { prefix "sros-ext"; }
    import nokia-types-mpls               { prefix "types-mpls"; }
    import nokia-types-rsvp               { prefix "types-rsvp"; }
    import nokia-types-sros               { prefix "types-sros"; }

    include nokia-conf-groups;
    include nokia-conf-router;
    include nokia-conf-system;
    include nokia-conf-system-security;

    sros-ext:sros-major-release "rel23";
    organization "Nokia";
    contact
        "Nokia SR OS Support
         Web: <http://www.nokia.com>";
    description
        "Nokia YANG Data model to configure RSVP protocol on SR OS based routers.

         Copyright 2016 Nokia. All rights reserved. Reproduction of this document
         is authorized on the condition that the foregoing copyright notice is included.

         This nokia-conf-router-rsvp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-05-04";

    grouping conf-router-rsvp {
        ///nokia-conf/configure/router/rsvp
        container rsvp {
            presence "Enable the rsvp context";
            description "Enable the rsvp context";

            ///nokia-conf/configure/router/rsvp/authentication-over-bypass
            leaf authentication-over-bypass {
                type boolean;
                default "false";
                description "Enable MD5 authentication over bypass LSP of PLR and MP";
            }

            ///nokia-conf/configure/router/rsvp/entropy-label-capability
            leaf entropy-label-capability {
                type boolean;
                default "false";
                description "Allow receiving and processing of the entropy label and ELI on incoming packets of RSVP LSPs";
            }

            ///nokia-conf/configure/router/rsvp/graceful-shutdown
            leaf graceful-shutdown {
                type boolean;
                default "false";
                description "Initiate a graceful shutdown of all RSVP interfaces on the node";
            }

            ///nokia-conf/configure/router/rsvp/implicit-null-label
            leaf implicit-null-label {
                type boolean;
                sros-ext:auto-restart-to-modify;
                default "false";
                description "Signal the implicit null option for all RSVP LSPs";
            }

            ///nokia-conf/configure/router/rsvp/keep-multiplier
            leaf keep-multiplier {
                type uint32 {
                    range "1..255";
                }
                default "3";
                description "Value for the keep-multiplier to declare a reservation or neighbor as down";
            }

            ///nokia-conf/configure/router/rsvp/include-node-id-in-rro
            leaf include-node-id-in-rro {
                type boolean;
                default "false";
                description "Include the node-id sub-object in the RRO (Record Route Object) on the RSVP instance";
            }

            ///nokia-conf/configure/router/rsvp/p2mp-merge-point-abort-timer
            leaf p2mp-merge-point-abort-timer {
                type uint32 {
                    range "1..65535";
                }
                units "seconds";
                description "Merge pointer timer for abort timer";
            }

            ///nokia-conf/configure/router/rsvp/p2p-merge-point-abort-timer
            leaf p2p-merge-point-abort-timer {
                type uint32 {
                    range "1..65535";
                }
                units "seconds";
                description "Merge pointer timer for P2P paths";
            }

            ///nokia-conf/configure/router/rsvp/preemption-timer
            leaf preemption-timer {
                type uint32 {
                    range "0..1800";
                }
                units "seconds";
                default "300";
                description "Preemption timer for the MPLS instance";
            }

            ///nokia-conf/configure/router/rsvp/rapid-retransmit-time
            leaf rapid-retransmit-time {
                type uint32 {
                    range "1..100";
                }
                units "deciseconds";
                default "5";
                description "Rapid retransmission interval to reliably deliver RSVP messages";
            }

            ///nokia-conf/configure/router/rsvp/rapid-retry-limit
            leaf rapid-retry-limit {
                type uint32 {
                    range "1..6";
                }
                default "3";
                description "Rapid retry limit to reliably deliver RSVP messages";
            }

            ///nokia-conf/configure/router/rsvp/refresh-reduction-over-bypass
            leaf refresh-reduction-over-bypass {
                type boolean;
                default "false";
                description "Enable refresh reduction capabilities over tunnels";
            }

            ///nokia-conf/configure/router/rsvp/refresh-time
            leaf refresh-time {
                type uint32 {
                    range "1..65535";
                }
                units "seconds";
                default "30";
                description "Interval between refresh messages";
            }

            ///nokia-conf/configure/router/rsvp/admin-state
            leaf admin-state {
                type types-sros:admin-state;
                default "disable";
                description "Administrative state of RSVP";
            }

            ///nokia-conf/configure/router/rsvp/te-down-threshold
            leaf-list te-down-threshold {
                type types-rsvp:rsvp-te-threshold-level;
                max-elements 16;
                ordered-by user;
                description "Value for the te-down-threshold";
            }

            ///nokia-conf/configure/router/rsvp/te-up-threshold
            leaf-list te-up-threshold {
                type types-rsvp:rsvp-te-threshold-level;
                max-elements 16;
                ordered-by user;
                description "Value for the te-up-threshold";
            }

            ///nokia-conf/configure/router/rsvp/apply-groups
            leaf-list apply-groups {
                type leafref {
                    path "../../../groups/group/name";
                }
                max-elements 8;
                ordered-by user;
                description "Apply a configuration group at this level";
            }

            ///nokia-conf/configure/router/rsvp/apply-groups-exclude
            leaf-list apply-groups-exclude {
                type leafref {
                    path "../../../groups/group/name";
                }
                max-elements 8;
                ordered-by user;
                description "Exclude a configuration group at this level";
            }

            ///nokia-conf/configure/router/rsvp/graceful-restart
            container graceful-restart {
                description "Enter the graceful-restart context";

                ///nokia-conf/configure/router/rsvp/graceful-restart/max-recovery
                leaf max-recovery {
                    type uint32 {
                        range "1..1800";
                    }
                    units "seconds";
                    default "300";
                    description "Maximum time to wait before a graceful helper recovers the session";
                }

                ///nokia-conf/configure/router/rsvp/graceful-restart/max-restart
                leaf max-restart {
                    type uint32 {
                        range "1..300";
                    }
                    units "seconds";
                    default "120";
                    description "Maximum time that a graceful helper waits for session restart after the neighbor is considered down";
                }

            } // container graceful-restart

            ///nokia-conf/configure/router/rsvp/msg-pacing
            container msg-pacing {
                presence "Enable the msg-pacing context";
                description "Enable the msg-pacing context";

                ///nokia-conf/configure/router/rsvp/msg-pacing/max-burst
                leaf max-burst {
                    type uint32 {
                        range "100..1000";
                    }
                    default "650";
                    description "Maximum RSVP messages that are sent over a specified period when message pacing is enabled";
                }

                ///nokia-conf/configure/router/rsvp/msg-pacing/period
                leaf period {
                    type uint32 {
                        range "100..1000";
                    }
                    units "milliseconds";
                    default "100";
                    description "Time for RSVP message pacing";
                }

            } // container msg-pacing

            ///nokia-conf/configure/router/rsvp/te-threshold-update
            container te-threshold-update {
                presence "Enable the te-threshold-update context";
                description "Enable the te-threshold-update context";

                ///nokia-conf/configure/router/rsvp/te-threshold-update/on-cac-failure
                leaf on-cac-failure {
                    type boolean;
                    default "false";
                    description "CAC (Call Admission Control) failure-triggered IGP update";
                }

                ///nokia-conf/configure/router/rsvp/te-threshold-update/update-timer
                leaf update-timer {
                    type uint32 {
                        range "1..300";
                    }
                    units "seconds";
                    description "Timer-based IGP updates";
                }

            } // container te-threshold-update

            ///nokia-conf/configure/router/rsvp/dbw-accounting
            container dbw-accounting {
                presence "Enable the dbw-accounting context";
                description "Enable the dbw-accounting context";

                ///nokia-conf/configure/router/rsvp/dbw-accounting/dbw-multiplier
                leaf dbw-multiplier {
                    type uint32 {
                        range "0..1000";
                    }
                    units "percent";
                    default "100";
                    description "Dark Bandwidth multiplier";
                }

                ///nokia-conf/configure/router/rsvp/dbw-accounting/sample-interval
                leaf sample-interval {
                    type uint32 {
                        range "10..600";
                    }
                    units "seconds";
                    default "30";
                    description "Dark Bandwidth sample interval";
                }

                ///nokia-conf/configure/router/rsvp/dbw-accounting/sample-multiplier
                leaf sample-multiplier {
                    type uint32 {
                        range "1..10";
                    }
                    default "3";
                    description "Dark Bandwidth sample multiplier";
                }

                ///nokia-conf/configure/router/rsvp/dbw-accounting/up-threshold
                container up-threshold {
                    description "Enter the up-threshold context";

                    ///nokia-conf/configure/router/rsvp/dbw-accounting/up-threshold/percent
                    leaf percent {
                        type types-sros:percent;
                        default "0";
                        description "Minimum difference in percent between dark bandwidth and sampled data rate, to trigger IGP-TE update";
                    }

                    ///nokia-conf/configure/router/rsvp/dbw-accounting/up-threshold/bw
                    leaf bw {
                        type int32 {
                            range "0..1000000";
                        }
                        units "megabps";
                        description "Minimum difference in MRLB or MRB to trigger an update";
                    }

                } // container up-threshold

                ///nokia-conf/configure/router/rsvp/dbw-accounting/down-threshold
                container down-threshold {
                    description "Enter the down-threshold context";

                    ///nokia-conf/configure/router/rsvp/dbw-accounting/down-threshold/percent
                    leaf percent {
                        type types-sros:percent;
                        default "0";
                        description "Minimum difference in percent between dark bandwidth and sampled data rate, to trigger IGP-TE update";
                    }

                    ///nokia-conf/configure/router/rsvp/dbw-accounting/down-threshold/bw
                    leaf bw {
                        type int32 {
                            range "0..1000000";
                        }
                        units "megabps";
                        description "Minimum difference in MRLB or MRB to trigger an update";
                    }

                } // container down-threshold

            } // container dbw-accounting

            ///nokia-conf/configure/router/rsvp/diffserv-te
            container diffserv-te {
                presence "Enable the diffserv-te context";
                description "Enable the diffserv-te context";

                ///nokia-conf/configure/router/rsvp/diffserv-te/admission-control-model
                leaf admission-control-model {
                    type enumeration {
                        enum mam                            { value 1; }
                        enum rdm                            { value 2; }
                    }
                    mandatory true;
                    description "Parameters for the DiffServ TE node";
                }

                ///nokia-conf/configure/router/rsvp/diffserv-te/apply-groups
                leaf-list apply-groups {
                    type leafref {
                        path "../../../../groups/group/name";
                    }
                    max-elements 8;
                    ordered-by user;
                    description "Apply a configuration group at this level";
                }

                ///nokia-conf/configure/router/rsvp/diffserv-te/apply-groups-exclude
                leaf-list apply-groups-exclude {
                    type leafref {
                        path "../../../../groups/group/name";
                    }
                    max-elements 8;
                    ordered-by user;
                    description "Exclude a configuration group at this level";
                }

                ///nokia-conf/configure/router/rsvp/diffserv-te/class-type-bw
                container class-type-bw {
                    description "Enter the class-type-bw context";

                    ///nokia-conf/configure/router/rsvp/diffserv-te/class-type-bw/ct0
                    leaf ct0 {
                        type int32 {
                            range "0..100";
                        }
                        default "0";
                        description "RSVP interface bandwidth percentage for class type 0";
                    }

                    ///nokia-conf/configure/router/rsvp/diffserv-te/class-type-bw/ct1
                    leaf ct1 {
                        type int32 {
                            range "0..100";
                        }
                        default "0";
                        description "RSVP interface bandwidth percentage for class type 1";
                    }

                    ///nokia-conf/configure/router/rsvp/diffserv-te/class-type-bw/ct2
                    leaf ct2 {
                        type int32 {
                            range "0..100";
                        }
                        default "0";
                        description "RSVP interface bandwidth percentage for class type 2";
                    }

                    ///nokia-conf/configure/router/rsvp/diffserv-te/class-type-bw/ct3
                    leaf ct3 {
                        type int32 {
                            range "0..100";
                        }
                        default "0";
                        description "RSVP interface bandwidth percentage for class type 3";
                    }

                    ///nokia-conf/configure/router/rsvp/diffserv-te/class-type-bw/ct4
                    leaf ct4 {
                        type int32 {
                            range "0..100";
                        }
                        default "0";
                        description "RSVP interface bandwidth percentage for class type 4";
                    }

                    ///nokia-conf/configure/router/rsvp/diffserv-te/class-type-bw/ct5
                    leaf ct5 {
                        type int32 {
                            range "0..100";
                        }
                        default "0";
                        description "RSVP interface bandwidth percentage for class type 5";
                    }

                    ///nokia-conf/configure/router/rsvp/diffserv-te/class-type-bw/ct6
                    leaf ct6 {
                        type int32 {
                            range "0..100";
                        }
                        default "0";
                        description "RSVP interface bandwidth percentage for class type 6";
                    }

                    ///nokia-conf/configure/router/rsvp/diffserv-te/class-type-bw/ct7
                    leaf ct7 {
                        type int32 {
                            range "0..100";
                        }
                        default "0";
                        description "RSVP interface bandwidth percentage for class type 7";
                    }

                } // container class-type-bw

                ///nokia-conf/configure/router/rsvp/diffserv-te/fc
                list fc {
                    key "fc-name";
                    description "Enter the fc list instance";

                    ///nokia-conf/configure/router/rsvp/diffserv-te/fc/fc-name
                    leaf fc-name {
                        type types-sros:fc-name;
                        description "Forwarding class for this mapping";
                    }

                    ///nokia-conf/configure/router/rsvp/diffserv-te/fc/class-type
                    leaf class-type {
                        type types-mpls:class-type;
                        mandatory true;
                        description "Diff-Serv Class Type (CT) for an LSP";
                    }

                    ///nokia-conf/configure/router/rsvp/diffserv-te/fc/apply-groups
                    leaf-list apply-groups {
                        type leafref {
                            path "../../../../../groups/group/name";
                        }
                        max-elements 8;
                        ordered-by user;
                        description "Apply a configuration group at this level";
                    }

                    ///nokia-conf/configure/router/rsvp/diffserv-te/fc/apply-groups-exclude
                    leaf-list apply-groups-exclude {
                        type leafref {
                            path "../../../../../groups/group/name";
                        }
                        max-elements 8;
                        ordered-by user;
                        description "Exclude a configuration group at this level";
                    }

                } // list fc

                ///nokia-conf/configure/router/rsvp/diffserv-te/te-class
                list te-class {
                    key "te-class-number";
                    description "Enter the te-class list instance";

                    ///nokia-conf/configure/router/rsvp/diffserv-te/te-class/te-class-number
                    leaf te-class-number {
                        type uint32 {
                            range "0..7";
                        }
                        description "TE class number";
                    }

                    ///nokia-conf/configure/router/rsvp/diffserv-te/te-class/class-type
                    leaf class-type {
                        type types-mpls:class-type;
                        sros-ext:immutable;
                        mandatory true;
                        description "Class type (CT) associated with the TE class";
                    }

                    ///nokia-conf/configure/router/rsvp/diffserv-te/te-class/priority
                    leaf priority {
                        type types-mpls:priority;
                        sros-ext:immutable;
                        mandatory true;
                        description "TE class priority";
                    }

                    ///nokia-conf/configure/router/rsvp/diffserv-te/te-class/apply-groups
                    leaf-list apply-groups {
                        type leafref {
                            path "../../../../../groups/group/name";
                        }
                        max-elements 8;
                        ordered-by user;
                        description "Apply a configuration group at this level";
                    }

                    ///nokia-conf/configure/router/rsvp/diffserv-te/te-class/apply-groups-exclude
                    leaf-list apply-groups-exclude {
                        type leafref {
                            path "../../../../../groups/group/name";
                        }
                        max-elements 8;
                        ordered-by user;
                        description "Exclude a configuration group at this level";
                    }

                } // list te-class

            } // container diffserv-te

            ///nokia-conf/configure/router/rsvp/interface
            list interface {
                key "interface-name";
                description "Enter the interface list instance";

                ///nokia-conf/configure/router/rsvp/interface/interface-name
                leaf interface-name {
                    type leafref {
                        path "../../../interface/interface-name";
                    }
                    description "Index for router RSVP interface";
                }

                ///nokia-conf/configure/router/rsvp/interface/admin-state
                leaf admin-state {
                    type types-sros:admin-state;
                    default "enable";
                    description "Administrative state of RSVP on the IP interface";
                }

                ///nokia-conf/configure/router/rsvp/interface/authentication-keychain
                leaf authentication-keychain {
                    type leafref {
                        path "../../../../system/security/keychains/keychain/keychain-name";
                    }
                    description "TCP authentication keychain for the session";
                }

                ///nokia-conf/configure/router/rsvp/interface/authentication-key
                leaf authentication-key {
                    type types-sros:encrypted-leaf {
                        length "1..51";
                    }
                    description "Authentication or hash key string";
                }

                ///nokia-conf/configure/router/rsvp/interface/bfd-liveness
                leaf bfd-liveness {
                    type boolean;
                    default "false";
                    description "Enable BFD";
                }

                ///nokia-conf/configure/router/rsvp/interface/graceful-restart-helper-mode
                leaf graceful-restart-helper-mode {
                    type boolean;
                    default "false";
                    description "Enable graceful restart helper for the RSVP interface";
                }

                ///nokia-conf/configure/router/rsvp/interface/graceful-shutdown
                leaf graceful-shutdown {
                    type boolean;
                    default "false";
                    description "Initiate a graceful shutdown of RSVP interface";
                }

                ///nokia-conf/configure/router/rsvp/interface/hello-interval
                leaf hello-interval {
                    type uint32 {
                        range "0..60";
                    }
                    units "seconds";
                    default "3";
                    description "Time between RSVP Hello messages";
                }

                ///nokia-conf/configure/router/rsvp/interface/subscription
                leaf subscription {
                    type uint32 {
                        range "0..1000";
                    }
                    default "100";
                    description "Percentage of the link bandwidth to use for reservation";
                }

                ///nokia-conf/configure/router/rsvp/interface/dbw-multiplier
                leaf dbw-multiplier {
                    type int32 {
                        range "0..1000";
                    }
                    units "percent";
                    description "Configure the Dark Bandwidth multiplier.";
                }

                ///nokia-conf/configure/router/rsvp/interface/implicit-null-label
                leaf implicit-null-label {
                    type boolean;
                    sros-ext:auto-restart-to-modify;
                    description "Signal the implicit null label value for all LSPs";
                }

                ///nokia-conf/configure/router/rsvp/interface/apply-groups
                leaf-list apply-groups {
                    type leafref {
                        path "../../../../groups/group/name";
                    }
                    max-elements 8;
                    ordered-by user;
                    description "Apply a configuration group at this level";
                }

                ///nokia-conf/configure/router/rsvp/interface/apply-groups-exclude
                leaf-list apply-groups-exclude {
                    type leafref {
                        path "../../../../groups/group/name";
                    }
                    max-elements 8;
                    ordered-by user;
                    description "Exclude a configuration group at this level";
                }

                ///nokia-conf/configure/router/rsvp/interface/class-type-bw
                container class-type-bw {
                    presence "Enable the class-type-bw context";
                    description "Enable the class-type-bw context";

                    ///nokia-conf/configure/router/rsvp/interface/class-type-bw/ct0
                    leaf ct0 {
                        type int32 {
                            range "0..100";
                        }
                        description "Percentage of link bandwidth for class type (CT) 0";
                    }

                    ///nokia-conf/configure/router/rsvp/interface/class-type-bw/ct1
                    leaf ct1 {
                        type int32 {
                            range "0..100";
                        }
                        description "Percentage of link bandwidth for class type (CT) 1";
                    }

                    ///nokia-conf/configure/router/rsvp/interface/class-type-bw/ct2
                    leaf ct2 {
                        type int32 {
                            range "0..100";
                        }
                        description "Percentage of link bandwidth for class type (CT) 2";
                    }

                    ///nokia-conf/configure/router/rsvp/interface/class-type-bw/ct3
                    leaf ct3 {
                        type int32 {
                            range "0..100";
                        }
                        description "Percentage of link bandwidth for class type (CT) 3";
                    }

                    ///nokia-conf/configure/router/rsvp/interface/class-type-bw/ct4
                    leaf ct4 {
                        type int32 {
                            range "0..100";
                        }
                        description "Percentage of link bandwidth for class type (CT) 4";
                    }

                    ///nokia-conf/configure/router/rsvp/interface/class-type-bw/ct5
                    leaf ct5 {
                        type int32 {
                            range "0..100";
                        }
                        description "Percentage of link bandwidth for class type (CT) 5";
                    }

                    ///nokia-conf/configure/router/rsvp/interface/class-type-bw/ct6
                    leaf ct6 {
                        type int32 {
                            range "0..100";
                        }
                        description "Percentage of link bandwidth for class type (CT) 6";
                    }

                    ///nokia-conf/configure/router/rsvp/interface/class-type-bw/ct7
                    leaf ct7 {
                        type int32 {
                            range "0..100";
                        }
                        description "Percentage of link bandwidth for class type (CT) 7";
                    }

                } // container class-type-bw

                ///nokia-conf/configure/router/rsvp/interface/refresh-reduction
                container refresh-reduction {
                    presence "Enable the refresh-reduction context";
                    description "Enable the refresh-reduction context";

                    ///nokia-conf/configure/router/rsvp/interface/refresh-reduction/reliable-delivery
                    leaf reliable-delivery {
                        type boolean;
                        default "false";
                        description "Reliable delivery of RSVP messages over the RSVP interface";
                    }

                } // container refresh-reduction

                ///nokia-conf/configure/router/rsvp/interface/dbw-up-threshold
                container dbw-up-threshold {
                    presence "Enable the dbw-up-threshold context";
                    description "Enable the dbw-up-threshold context";

                    ///nokia-conf/configure/router/rsvp/interface/dbw-up-threshold/percent
                    leaf percent {
                        type int32 {
                            range "0..100";
                        }
                        units "percent";
                        description "Minimum difference in percent between dark bandwidth and sampled data rate, to trigger IGP-TE update";
                    }

                    ///nokia-conf/configure/router/rsvp/interface/dbw-up-threshold/bw
                    leaf bw {
                        type int32 {
                            range "0..1000000";
                        }
                        units "megabps";
                        description "Minimum difference in MRLB or MRB to trigger an update";
                    }

                } // container dbw-up-threshold

                ///nokia-conf/configure/router/rsvp/interface/dbw-down-threshold
                container dbw-down-threshold {
                    presence "Enable the dbw-down-threshold context";
                    description "Enable the dbw-down-threshold context";

                    ///nokia-conf/configure/router/rsvp/interface/dbw-down-threshold/percent
                    leaf percent {
                        type int32 {
                            range "0..100";
                        }
                        units "percent";
                        description "Minimum difference in percent between dark bandwidth and sampled data rate, to trigger IGP-TE update";
                    }

                    ///nokia-conf/configure/router/rsvp/interface/dbw-down-threshold/bw
                    leaf bw {
                        type int32 {
                            range "0..1000000";
                        }
                        units "megabps";
                        description "Minimum difference in MRLB or MRB to trigger an update";
                    }

                } // container dbw-down-threshold

                ///nokia-conf/configure/router/rsvp/interface/te-down-threshold
                container te-down-threshold {
                    presence "Enable the te-down-threshold context";
                    description "Enable the te-down-threshold context";

                    ///nokia-conf/configure/router/rsvp/interface/te-down-threshold/value
                    leaf-list value {
                        type types-rsvp:rsvp-te-threshold-level;
                        min-elements 1;
                        max-elements 16;
                        ordered-by user;
                        description "Threshold level per interface";
                    }

                    ///nokia-conf/configure/router/rsvp/interface/te-down-threshold/apply-groups
                    leaf-list apply-groups {
                        type leafref {
                            path "../../../../../groups/group/name";
                        }
                        max-elements 8;
                        ordered-by user;
                        description "Apply a configuration group at this level";
                    }

                    ///nokia-conf/configure/router/rsvp/interface/te-down-threshold/apply-groups-exclude
                    leaf-list apply-groups-exclude {
                        type leafref {
                            path "../../../../../groups/group/name";
                        }
                        max-elements 8;
                        ordered-by user;
                        description "Exclude a configuration group at this level";
                    }

                } // container te-down-threshold

                ///nokia-conf/configure/router/rsvp/interface/te-up-threshold
                container te-up-threshold {
                    presence "Enable the te-up-threshold context";
                    description "Enable the te-up-threshold context";

                    ///nokia-conf/configure/router/rsvp/interface/te-up-threshold/value
                    leaf-list value {
                        type types-rsvp:rsvp-te-threshold-level;
                        min-elements 1;
                        max-elements 16;
                        ordered-by user;
                        description "Threshold level per interface";
                    }

                    ///nokia-conf/configure/router/rsvp/interface/te-up-threshold/apply-groups
                    leaf-list apply-groups {
                        type leafref {
                            path "../../../../../groups/group/name";
                        }
                        max-elements 8;
                        ordered-by user;
                        description "Apply a configuration group at this level";
                    }

                    ///nokia-conf/configure/router/rsvp/interface/te-up-threshold/apply-groups-exclude
                    leaf-list apply-groups-exclude {
                        type leafref {
                            path "../../../../../groups/group/name";
                        }
                        max-elements 8;
                        ordered-by user;
                        description "Exclude a configuration group at this level";
                    }

                } // container te-up-threshold

            } // list interface

        } // container rsvp

    } // grouping conf-router-rsvp

}
