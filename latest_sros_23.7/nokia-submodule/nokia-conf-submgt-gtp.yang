submodule nokia-conf-submgt-gtp {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }

    include nokia-conf-groups;
    include nokia-conf-python;
    include nokia-conf-submgt-local-user-db;
    include nokia-conf-subscriber-mgmt;

    sros-ext:sros-major-release "rel23";
    organization "Nokia";
    contact
        "Nokia SR OS Support
         Web: <http://www.nokia.com>";
    description
        "Nokia YANG Data model to configure subscriber management gtp on SR OS based routers.

         Copyright 2016 Nokia. All rights reserved. Reproduction of this document
         is authorized on the condition that the foregoing copyright notice is included.

         This nokia-conf-submgt-gtp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-07-01";

    grouping conf-submgt-gtp {
        ///nokia-conf/configure/subscriber-mgmt/gtp
        container gtp {
            description "Enter the gtp context";

            ///nokia-conf/configure/subscriber-mgmt/gtp/max-held-uplink-sessions
            leaf max-held-uplink-sessions {
                type uint32 {
                    range "0..500000";
                }
                default "2000";
                description "Maximum GTP sessions held while UE is disconnected";
            }

            ///nokia-conf/configure/subscriber-mgmt/gtp/apply-groups
            leaf-list apply-groups {
                type leafref {
                    path "../../../groups/group/name";
                }
                max-elements 8;
                ordered-by user;
                description "Apply a configuration group at this level";
            }

            ///nokia-conf/configure/subscriber-mgmt/gtp/apply-groups-exclude
            leaf-list apply-groups-exclude {
                type leafref {
                    path "../../../groups/group/name";
                }
                max-elements 8;
                ordered-by user;
                description "Exclude a configuration group at this level";
            }

            ///nokia-conf/configure/subscriber-mgmt/gtp/serving-network
            container serving-network {
                presence "Enable the serving-network context";
                description "Enable the serving-network context";

                ///nokia-conf/configure/subscriber-mgmt/gtp/serving-network/mcc
                leaf mcc {
                    type string {
                        length "3";
                        pattern "\\d{3}" {
                            error-message "mcc must be digits";
                        }
                    }
                    mandatory true;
                    description "Mobile Country Code (MCC) portion of serving network";
                }

                ///nokia-conf/configure/subscriber-mgmt/gtp/serving-network/mnc
                leaf mnc {
                    type string {
                        length "2..3";
                        pattern "\\d{2,3}" {
                            error-message "mnc must be digits";
                        }
                    }
                    mandatory true;
                    description "Mobile Network Code (MNC) portion of serving network";
                }

            } // container serving-network

            ///nokia-conf/configure/subscriber-mgmt/gtp/apn-policy
            list apn-policy {
                key "name";
                max-elements 128;
                description "Enter the apn-policy list instance";

                ///nokia-conf/configure/subscriber-mgmt/gtp/apn-policy/name
                leaf name {
                    type types-sros:named-item;
                    description "APN policy name for a new incoming GTP connection";
                }

                ///nokia-conf/configure/subscriber-mgmt/gtp/apn-policy/apply-groups
                leaf-list apply-groups {
                    type leafref {
                        path "../../../../groups/group/name";
                    }
                    max-elements 8;
                    ordered-by user;
                    description "Apply a configuration group at this level";
                }

                ///nokia-conf/configure/subscriber-mgmt/gtp/apn-policy/apply-groups-exclude
                leaf-list apply-groups-exclude {
                    type leafref {
                        path "../../../../groups/group/name";
                    }
                    max-elements 8;
                    ordered-by user;
                    description "Exclude a configuration group at this level";
                }

                ///nokia-conf/configure/subscriber-mgmt/gtp/apn-policy/apn
                list apn {
                    key "apn-name";
                    max-elements 1024;
                    description "Enter the apn list instance";

                    ///nokia-conf/configure/subscriber-mgmt/gtp/apn-policy/apn/apn-name
                    leaf apn-name {
                        type string {
                            length "1..80";
                            pattern "([a-zA-Z0-9]+-+)*([a-zA-Z0-9]+\\.([a-zA-Z0-9]+-+)*)*[a-zA-Z0-9]+" {
                                error-message "wrong format of apn name";
                            }
                        }
                        description "GTP APN name";
                    }

                    ///nokia-conf/configure/subscriber-mgmt/gtp/apn-policy/apn/skip-gtp-ipv4-allocation
                    leaf skip-gtp-ipv4-allocation {
                        type boolean;
                        default "false";
                        description "defer IPv4 address allocation to DHCP";
                    }

                    ///nokia-conf/configure/subscriber-mgmt/gtp/apn-policy/apn/apply-groups
                    leaf-list apply-groups {
                        type leafref {
                            path "../../../../../groups/group/name";
                        }
                        max-elements 8;
                        ordered-by user;
                        description "Apply a configuration group at this level";
                    }

                    ///nokia-conf/configure/subscriber-mgmt/gtp/apn-policy/apn/apply-groups-exclude
                    leaf-list apply-groups-exclude {
                        type leafref {
                            path "../../../../../groups/group/name";
                        }
                        max-elements 8;
                        ordered-by user;
                        description "Exclude a configuration group at this level";
                    }

                    ///nokia-conf/configure/subscriber-mgmt/gtp/apn-policy/apn/auth-policy
                    choice auth-policy {
                        ///nokia-conf/configure/subscriber-mgmt/gtp/apn-policy/apn/auth-policy/diameter
                        case diameter {

                            ///nokia-conf/configure/subscriber-mgmt/gtp/apn-policy/apn/auth-policy/diameter/diameter-nasreq-policy
                            leaf diameter-nasreq-policy {
                                type leafref {
                                    path "../../../../diameter-nasreq-policy/name";
                                }
                                description "NASREQ authentication policy name";
                            }

                        }
                        ///nokia-conf/configure/subscriber-mgmt/gtp/apn-policy/apn/auth-policy/radius
                        case radius {

                            ///nokia-conf/configure/subscriber-mgmt/gtp/apn-policy/apn/auth-policy/radius/radius-auth-policy
                            leaf radius-auth-policy {
                                type leafref {
                                    path "../../../../radius-authentication-policy/name";
                                }
                                description "RADIUS authentication policy name";
                            }

                        }
                        ///nokia-conf/configure/subscriber-mgmt/gtp/apn-policy/apn/auth-policy/user-db
                        case user-db {

                            ///nokia-conf/configure/subscriber-mgmt/gtp/apn-policy/apn/auth-policy/user-db/user-db
                            leaf user-db {
                                type leafref {
                                    path "../../../../local-user-db/name";
                                }
                                description "Local user database name";
                            }

                        }
                    }
                    ///nokia-conf/configure/subscriber-mgmt/gtp/apn-policy/apn/ambr-qos-mapping
                    container ambr-qos-mapping {
                        description "Enable the ambr-qos-mapping context";

                        ///nokia-conf/configure/subscriber-mgmt/gtp/apn-policy/apn/ambr-qos-mapping/apply-groups
                        leaf-list apply-groups {
                            type leafref {
                                path "../../../../../../groups/group/name";
                            }
                            max-elements 8;
                            ordered-by user;
                            description "Apply a configuration group at this level";
                        }

                        ///nokia-conf/configure/subscriber-mgmt/gtp/apn-policy/apn/ambr-qos-mapping/apply-groups-exclude
                        leaf-list apply-groups-exclude {
                            type leafref {
                                path "../../../../../../groups/group/name";
                            }
                            max-elements 8;
                            ordered-by user;
                            description "Exclude a configuration group at this level";
                        }

                        ///nokia-conf/configure/subscriber-mgmt/gtp/apn-policy/apn/ambr-qos-mapping/downlink
                        container downlink {
                            presence "Enable the downlink context";
                            description "Enable the downlink context";

                            ///nokia-conf/configure/subscriber-mgmt/gtp/apn-policy/apn/ambr-qos-mapping/downlink/downlink
                            choice downlink {
                                mandatory true;
                                ///nokia-conf/configure/subscriber-mgmt/gtp/apn-policy/apn/ambr-qos-mapping/downlink/downlink/aggregate-rate
                                case aggregate-rate {

                                    ///nokia-conf/configure/subscriber-mgmt/gtp/apn-policy/apn/ambr-qos-mapping/downlink/downlink/aggregate-rate/aggregate-rate
                                    leaf aggregate-rate {
                                        type empty;
                                        description "Map the downlink APN-AMBR rate to an aggregate rate";
                                    }

                                }
                                ///nokia-conf/configure/subscriber-mgmt/gtp/apn-policy/apn/ambr-qos-mapping/downlink/downlink/arbiter
                                case arbiter {

                                    ///nokia-conf/configure/subscriber-mgmt/gtp/apn-policy/apn/ambr-qos-mapping/downlink/downlink/arbiter/arbiter
                                    leaf arbiter {
                                        type types-sros:named-item;
                                        description "Name of arbiter to be overridden";
                                    }

                                }
                                ///nokia-conf/configure/subscriber-mgmt/gtp/apn-policy/apn/ambr-qos-mapping/downlink/downlink/policer
                                case policer {

                                    ///nokia-conf/configure/subscriber-mgmt/gtp/apn-policy/apn/ambr-qos-mapping/downlink/downlink/policer/policer
                                    leaf policer {
                                        type types-qos:sap-egress-policer-id;
                                        description "ID of policer to be overridden";
                                    }

                                }
                                ///nokia-conf/configure/subscriber-mgmt/gtp/apn-policy/apn/ambr-qos-mapping/downlink/downlink/queue
                                case queue {

                                    ///nokia-conf/configure/subscriber-mgmt/gtp/apn-policy/apn/ambr-qos-mapping/downlink/downlink/queue/queue
                                    leaf queue {
                                        type types-qos:egress-queue-id;
                                        description "Map the downlink APN-AMBR rate to a queue PIR override";
                                    }

                                }
                                ///nokia-conf/configure/subscriber-mgmt/gtp/apn-policy/apn/ambr-qos-mapping/downlink/downlink/scheduler
                                case scheduler {

                                    ///nokia-conf/configure/subscriber-mgmt/gtp/apn-policy/apn/ambr-qos-mapping/downlink/downlink/scheduler/scheduler
                                    leaf scheduler {
                                        type types-sros:named-item;
                                        description "Name of the scheduler to be overridden";
                                    }

                                }
                            }
                        } // container downlink

                        ///nokia-conf/configure/subscriber-mgmt/gtp/apn-policy/apn/ambr-qos-mapping/uplink
                        container uplink {
                            presence "Enable the uplink context";
                            description "Enable the uplink context";

                            ///nokia-conf/configure/subscriber-mgmt/gtp/apn-policy/apn/ambr-qos-mapping/uplink/uplink
                            choice uplink {
                                mandatory true;
                                ///nokia-conf/configure/subscriber-mgmt/gtp/apn-policy/apn/ambr-qos-mapping/uplink/uplink/arbiter
                                case arbiter {

                                    ///nokia-conf/configure/subscriber-mgmt/gtp/apn-policy/apn/ambr-qos-mapping/uplink/uplink/arbiter/arbiter
                                    leaf arbiter {
                                        type types-sros:named-item;
                                        description "Name of arbiter to be overridden";
                                    }

                                }
                                ///nokia-conf/configure/subscriber-mgmt/gtp/apn-policy/apn/ambr-qos-mapping/uplink/uplink/policer
                                case policer {

                                    ///nokia-conf/configure/subscriber-mgmt/gtp/apn-policy/apn/ambr-qos-mapping/uplink/uplink/policer/policer
                                    leaf policer {
                                        type types-qos:ingress-policer-id;
                                        description "Map the uplink APN-AMBR rate to a policer PIR override";
                                    }

                                }
                                ///nokia-conf/configure/subscriber-mgmt/gtp/apn-policy/apn/ambr-qos-mapping/uplink/uplink/queue
                                case queue {

                                    ///nokia-conf/configure/subscriber-mgmt/gtp/apn-policy/apn/ambr-qos-mapping/uplink/uplink/queue/queue
                                    leaf queue {
                                        type types-qos:ingress-queue-id;
                                        description "Map the uplink APN-AMBR rate to a queue PIR override";
                                    }

                                }
                                ///nokia-conf/configure/subscriber-mgmt/gtp/apn-policy/apn/ambr-qos-mapping/uplink/uplink/scheduler
                                case scheduler {

                                    ///nokia-conf/configure/subscriber-mgmt/gtp/apn-policy/apn/ambr-qos-mapping/uplink/uplink/scheduler/scheduler
                                    leaf scheduler {
                                        type types-sros:named-item;
                                        description "Name of scheduler to be overridden";
                                    }

                                }
                            }
                        } // container uplink

                    } // container ambr-qos-mapping

                    ///nokia-conf/configure/subscriber-mgmt/gtp/apn-policy/apn/defaults
                    container defaults {
                        description "Enter the defaults context";

                        ///nokia-conf/configure/subscriber-mgmt/gtp/apn-policy/apn/defaults/group-interface
                        container group-interface {
                            presence "Enable the group-interface context";
                            description "Enable the group-interface context";

                            ///nokia-conf/configure/subscriber-mgmt/gtp/apn-policy/apn/defaults/group-interface/svc-name
                            leaf svc-name {
                                type types-services:service-name;
                                mandatory true;
                                description "Service name where the group interface resides";
                            }

                            ///nokia-conf/configure/subscriber-mgmt/gtp/apn-policy/apn/defaults/group-interface/name
                            leaf name {
                                type types-sros:interface-name;
                                mandatory true;
                                description "Group interface name";
                            }

                        } // container group-interface

                    } // container defaults

                } // list apn

            } // list apn-policy

            ///nokia-conf/configure/subscriber-mgmt/gtp/peer-profile
            list peer-profile {
                key "name";
                description "Enter the peer-profile list instance";

                ///nokia-conf/configure/subscriber-mgmt/gtp/peer-profile/name
                leaf name {
                    type types-sros:named-item;
                    description "Peer profile name";
                }

                ///nokia-conf/configure/subscriber-mgmt/gtp/peer-profile/description
                leaf description {
                    type types-sros:description;
                    description "Text description";
                }

                ///nokia-conf/configure/subscriber-mgmt/gtp/peer-profile/interface-type
                leaf interface-type {
                    type enumeration {
                        enum gn                             { value 1; }
                        enum s2a                            { value 2; }
                        enum s2b                            { value 3; }
                        enum s11                            { value 4; }
                    }
                    description "3GPP interface type for connections toward this peer";
                }

                ///nokia-conf/configure/subscriber-mgmt/gtp/peer-profile/ip-ttl
                leaf ip-ttl {
                    type uint8 {
                        range "1..255";
                    }
                    default "255";
                    description "IP header TTL value for GTP control messages";
                }

                ///nokia-conf/configure/subscriber-mgmt/gtp/peer-profile/python-policy
                leaf python-policy {
                    type leafref {
                        path "../../../../python/python-policy/name";
                    }
                    description "Python policy for MGW profile packets sent or received";
                }

                ///nokia-conf/configure/subscriber-mgmt/gtp/peer-profile/apply-groups
                leaf-list apply-groups {
                    type leafref {
                        path "../../../../groups/group/name";
                    }
                    max-elements 8;
                    ordered-by user;
                    description "Apply a configuration group at this level";
                }

                ///nokia-conf/configure/subscriber-mgmt/gtp/peer-profile/apply-groups-exclude
                leaf-list apply-groups-exclude {
                    type leafref {
                        path "../../../../groups/group/name";
                    }
                    max-elements 8;
                    ordered-by user;
                    description "Exclude a configuration group at this level";
                }

                ///nokia-conf/configure/subscriber-mgmt/gtp/peer-profile/keep-alive
                container keep-alive {
                    description "Enter the keep-alive context";

                    ///nokia-conf/configure/subscriber-mgmt/gtp/peer-profile/keep-alive/admin-state
                    leaf admin-state {
                        type types-sros:admin-state;
                        default "enable";
                        description "Administrative state of GTP-C echo request messages";
                    }

                    ///nokia-conf/configure/subscriber-mgmt/gtp/peer-profile/keep-alive/interval
                    leaf interval {
                        when "../admin-state = 'enable'" {
                            description "admin-state must be enabled";
                        }
                        type types-sros:time-duration {
                            range "60..180";
                        }
                        units "seconds";
                        default "60";
                        description "Frequency for sending keepalives";
                    }

                    ///nokia-conf/configure/subscriber-mgmt/gtp/peer-profile/keep-alive/retry-count
                    leaf retry-count {
                        when "../admin-state = 'enable'" {
                            description "admin-state must be enabled";
                        }
                        type uint32 {
                            range "1..15";
                        }
                        default "4";
                        description "Time between echo retries toward the same peer";
                    }

                    ///nokia-conf/configure/subscriber-mgmt/gtp/peer-profile/keep-alive/timeout
                    leaf timeout {
                        when "../admin-state = 'enable'" {
                            description "admin-state must be enabled";
                        }
                        type uint32 {
                            range "1..20";
                        }
                        units "seconds";
                        default "5";
                        description "Timeout after which echo request is deemed unanswered";
                    }

                } // container keep-alive

                ///nokia-conf/configure/subscriber-mgmt/gtp/peer-profile/message-retransmit
                container message-retransmit {
                    description "Enter the message-retransmit context";

                    ///nokia-conf/configure/subscriber-mgmt/gtp/peer-profile/message-retransmit/timeout
                    leaf timeout {
                        type uint32 {
                            range "1..30";
                        }
                        units "seconds";
                        default "5";
                        description "Timeout after which a message is considered unanswered";
                    }

                    ///nokia-conf/configure/subscriber-mgmt/gtp/peer-profile/message-retransmit/retry-count
                    leaf retry-count {
                        type uint32 {
                            range "1..8";
                        }
                        default "3";
                        description "Maximum unanswered retries before message deemed failed";
                    }

                } // container message-retransmit

                ///nokia-conf/configure/subscriber-mgmt/gtp/peer-profile/s11
                container s11 {
                    description "Enter the s11 context";

                    ///nokia-conf/configure/subscriber-mgmt/gtp/peer-profile/s11/ipv4-mtu
                    leaf ipv4-mtu {
                        type uint32 {
                            range "512..9000";
                        }
                        default "1400";
                        description "IPv4-MTU PCO sent in S11 GTP messages";
                    }

                    ///nokia-conf/configure/subscriber-mgmt/gtp/peer-profile/s11/end-marker-count
                    leaf end-marker-count {
                        type uint32 {
                            range "0..5";
                        }
                        default "1";
                        description "Number of GTP-U end marker packets that are sent";
                    }

                    ///nokia-conf/configure/subscriber-mgmt/gtp/peer-profile/s11/change-reporting-action
                    leaf change-reporting-action {
                        type union {
                            type uint32 {
                                range "0..255";
                            }
                            type enumeration {
                                enum cgi-sai                        { value 1; }
                                enum rai                            { value 2; }
                                enum tai                            { value 3; }
                                enum ecgi                           { value 4; }
                                enum cgi-sai-rai                    { value 5; }
                                enum tai-ecgi                       { value 6; }
                            }
                        }
                        description "Value of change reporting action IE sends to the peer";
                    }

                    ///nokia-conf/configure/subscriber-mgmt/gtp/peer-profile/s11/qos
                    container qos {
                        description "Enter the qos context";

                        ///nokia-conf/configure/subscriber-mgmt/gtp/peer-profile/s11/qos/arp
                        leaf arp {
                            type uint32 {
                                range "1..15";
                            }
                            default "1";
                            description "Allocation or retention priority";
                        }

                        ///nokia-conf/configure/subscriber-mgmt/gtp/peer-profile/s11/qos/qci
                        leaf qci {
                            type uint32 {
                                range "1..9";
                            }
                            default "8";
                            description "QoS Class Identifier (QCI) to send in GTP messages";
                        }

                        ///nokia-conf/configure/subscriber-mgmt/gtp/peer-profile/s11/qos/ambr
                        container ambr {
                            description "Enter the ambr context";

                            ///nokia-conf/configure/subscriber-mgmt/gtp/peer-profile/s11/qos/ambr/down-link
                            leaf down-link {
                                type int32 {
                                    range "0..10000000";
                                }
                                units "kilobps";
                                default "20000";
                                description "Downlink Aggregated Maximum Bit Rate (AMBR)";
                            }

                            ///nokia-conf/configure/subscriber-mgmt/gtp/peer-profile/s11/qos/ambr/up-link
                            leaf up-link {
                                type int32 {
                                    range "0..10000000";
                                }
                                units "kilobps";
                                default "10000";
                                description "Uplink Aggregated Maximum Bit Rate (AMBR)";
                            }

                        } // container ambr

                        ///nokia-conf/configure/subscriber-mgmt/gtp/peer-profile/s11/qos/down-link
                        container down-link {
                            description "Enter the down-link context";

                            ///nokia-conf/configure/subscriber-mgmt/gtp/peer-profile/s11/qos/down-link/gbr
                            leaf gbr {
                                type uint32 {
                                    range "0..100000";
                                }
                                units "kilobps";
                                default "0";
                                description "Guaranteed Bit Rate (GBR)";
                            }

                            ///nokia-conf/configure/subscriber-mgmt/gtp/peer-profile/s11/qos/down-link/mbr
                            leaf mbr {
                                type uint32 {
                                    range "0..100000";
                                }
                                units "kilobps";
                                default "0";
                                description "Maximum Bit Rate (MBR)";
                            }

                        } // container down-link

                        ///nokia-conf/configure/subscriber-mgmt/gtp/peer-profile/s11/qos/up-link
                        container up-link {
                            description "Enter the up-link context";

                            ///nokia-conf/configure/subscriber-mgmt/gtp/peer-profile/s11/qos/up-link/gbr
                            leaf gbr {
                                type uint32 {
                                    range "0..100000";
                                }
                                units "kilobps";
                                default "0";
                                description "Guaranteed Bit Rate (GBR)";
                            }

                            ///nokia-conf/configure/subscriber-mgmt/gtp/peer-profile/s11/qos/up-link/mbr
                            leaf mbr {
                                type uint32 {
                                    range "0..100000";
                                }
                                units "kilobps";
                                default "0";
                                description "Maximum Bit Rate (MBR)";
                            }

                        } // container up-link

                    } // container qos

                } // container s11

                ///nokia-conf/configure/subscriber-mgmt/gtp/peer-profile/uplink
                container uplink {
                    description "Enter the uplink context";

                    ///nokia-conf/configure/subscriber-mgmt/gtp/peer-profile/uplink/protocol-configuration-options
                    leaf protocol-configuration-options {
                        type enumeration {
                            enum pco                            { value 1; }
                            enum apco                           { value 2; }
                        }
                        default "pco";
                        description "Information Element for Protocol Configuration Options";
                    }

                    ///nokia-conf/configure/subscriber-mgmt/gtp/peer-profile/uplink/rat-type
                    leaf rat-type {
                        type union {
                            type uint32 {
                                range "0..255";
                            }
                            type enumeration {
                                enum utran                          { value 1; }
                                enum geran                          { value 2; }
                                enum wlan                           { value 3; }
                                enum gan                            { value 4; }
                                enum hspa                           { value 5; }
                                enum eutran                         { value 6; }
                                enum virtual                        { value 7; }
                            }
                        }
                        default "wlan";
                        description "Default Radio Access Type (RAT) signaled in GTP setup";
                    }

                    ///nokia-conf/configure/subscriber-mgmt/gtp/peer-profile/uplink/report-wlan-location
                    leaf report-wlan-location {
                        type boolean;
                        default "false";
                        description "Report WLAN or cellular location of UE during setup";
                    }

                    ///nokia-conf/configure/subscriber-mgmt/gtp/peer-profile/uplink/session-hold-time
                    leaf session-hold-time {
                        type union {
                            type types-sros:time-duration {
                                range "0..3600";
                            }
                            type enumeration {
                                enum remaining-lease-time           { value -1; }
                            }
                        }
                        default "30";
                        description "Time to hold a GTP session after its UE is disconnected";
                    }

                    ///nokia-conf/configure/subscriber-mgmt/gtp/peer-profile/uplink/charging-characteristics
                    container charging-characteristics {
                        description "Enter the charging-characteristics context";

                        ///nokia-conf/configure/subscriber-mgmt/gtp/peer-profile/uplink/charging-characteristics/home
                        container home {
                            description "Enter the home context";

                            ///nokia-conf/configure/subscriber-mgmt/gtp/peer-profile/uplink/charging-characteristics/home/bit0
                            leaf bit0 {
                                type boolean;
                                default "false";
                                description "Set bit in charging characteristics information element";
                            }

                            ///nokia-conf/configure/subscriber-mgmt/gtp/peer-profile/uplink/charging-characteristics/home/bit1
                            leaf bit1 {
                                type boolean;
                                default "false";
                                description "Set bit in charging characteristics information element";
                            }

                            ///nokia-conf/configure/subscriber-mgmt/gtp/peer-profile/uplink/charging-characteristics/home/bit2
                            leaf bit2 {
                                type boolean;
                                default "false";
                                description "Set bit in charging characteristics information element";
                            }

                            ///nokia-conf/configure/subscriber-mgmt/gtp/peer-profile/uplink/charging-characteristics/home/bit3
                            leaf bit3 {
                                type boolean;
                                default "false";
                                description "Set bit in charging characteristics information element";
                            }

                            ///nokia-conf/configure/subscriber-mgmt/gtp/peer-profile/uplink/charging-characteristics/home/bit4
                            leaf bit4 {
                                type boolean;
                                default "false";
                                description "Set bit in charging characteristics information element";
                            }

                            ///nokia-conf/configure/subscriber-mgmt/gtp/peer-profile/uplink/charging-characteristics/home/bit5
                            leaf bit5 {
                                type boolean;
                                default "false";
                                description "Set bit in charging characteristics information element";
                            }

                            ///nokia-conf/configure/subscriber-mgmt/gtp/peer-profile/uplink/charging-characteristics/home/bit6
                            leaf bit6 {
                                type boolean;
                                default "false";
                                description "Set bit in charging characteristics information element";
                            }

                            ///nokia-conf/configure/subscriber-mgmt/gtp/peer-profile/uplink/charging-characteristics/home/bit7
                            leaf bit7 {
                                type boolean;
                                default "false";
                                description "Set bit in charging characteristics information element";
                            }

                            ///nokia-conf/configure/subscriber-mgmt/gtp/peer-profile/uplink/charging-characteristics/home/bit8
                            leaf bit8 {
                                type boolean;
                                default "false";
                                description "Set bit in charging characteristics information element";
                            }

                            ///nokia-conf/configure/subscriber-mgmt/gtp/peer-profile/uplink/charging-characteristics/home/bit9
                            leaf bit9 {
                                type boolean;
                                default "false";
                                description "Set bit in charging characteristics information element";
                            }

                            ///nokia-conf/configure/subscriber-mgmt/gtp/peer-profile/uplink/charging-characteristics/home/bit10
                            leaf bit10 {
                                type boolean;
                                default "false";
                                description "Set bit in charging characteristics information element";
                            }

                            ///nokia-conf/configure/subscriber-mgmt/gtp/peer-profile/uplink/charging-characteristics/home/bit11
                            leaf bit11 {
                                type boolean;
                                default "false";
                                description "Set bit in charging characteristics information element";
                            }

                            ///nokia-conf/configure/subscriber-mgmt/gtp/peer-profile/uplink/charging-characteristics/home/bit12
                            leaf bit12 {
                                type boolean;
                                default "false";
                                description "Set bit in charging characteristics information element";
                            }

                            ///nokia-conf/configure/subscriber-mgmt/gtp/peer-profile/uplink/charging-characteristics/home/bit13
                            leaf bit13 {
                                type boolean;
                                default "false";
                                description "Set bit in charging characteristics information element";
                            }

                            ///nokia-conf/configure/subscriber-mgmt/gtp/peer-profile/uplink/charging-characteristics/home/bit14
                            leaf bit14 {
                                type boolean;
                                default "false";
                                description "Set bit in charging characteristics information element";
                            }

                            ///nokia-conf/configure/subscriber-mgmt/gtp/peer-profile/uplink/charging-characteristics/home/bit15
                            leaf bit15 {
                                type boolean;
                                default "false";
                                description "Set bit in charging characteristics information element";
                            }

                        } // container home

                        ///nokia-conf/configure/subscriber-mgmt/gtp/peer-profile/uplink/charging-characteristics/roaming
                        container roaming {
                            description "Enter the roaming context";

                            ///nokia-conf/configure/subscriber-mgmt/gtp/peer-profile/uplink/charging-characteristics/roaming/bit0
                            leaf bit0 {
                                type boolean;
                                default "false";
                                description "Set bit in charging characteristics information element";
                            }

                            ///nokia-conf/configure/subscriber-mgmt/gtp/peer-profile/uplink/charging-characteristics/roaming/bit1
                            leaf bit1 {
                                type boolean;
                                default "false";
                                description "Set bit in charging characteristics information element";
                            }

                            ///nokia-conf/configure/subscriber-mgmt/gtp/peer-profile/uplink/charging-characteristics/roaming/bit2
                            leaf bit2 {
                                type boolean;
                                default "false";
                                description "Set bit in charging characteristics information element";
                            }

                            ///nokia-conf/configure/subscriber-mgmt/gtp/peer-profile/uplink/charging-characteristics/roaming/bit3
                            leaf bit3 {
                                type boolean;
                                default "false";
                                description "Set bit in charging characteristics information element";
                            }

                            ///nokia-conf/configure/subscriber-mgmt/gtp/peer-profile/uplink/charging-characteristics/roaming/bit4
                            leaf bit4 {
                                type boolean;
                                default "false";
                                description "Set bit in charging characteristics information element";
                            }

                            ///nokia-conf/configure/subscriber-mgmt/gtp/peer-profile/uplink/charging-characteristics/roaming/bit5
                            leaf bit5 {
                                type boolean;
                                default "false";
                                description "Set bit in charging characteristics information element";
                            }

                            ///nokia-conf/configure/subscriber-mgmt/gtp/peer-profile/uplink/charging-characteristics/roaming/bit6
                            leaf bit6 {
                                type boolean;
                                default "false";
                                description "Set bit in charging characteristics information element";
                            }

                            ///nokia-conf/configure/subscriber-mgmt/gtp/peer-profile/uplink/charging-characteristics/roaming/bit7
                            leaf bit7 {
                                type boolean;
                                default "false";
                                description "Set bit in charging characteristics information element";
                            }

                            ///nokia-conf/configure/subscriber-mgmt/gtp/peer-profile/uplink/charging-characteristics/roaming/bit8
                            leaf bit8 {
                                type boolean;
                                default "false";
                                description "Set bit in charging characteristics information element";
                            }

                            ///nokia-conf/configure/subscriber-mgmt/gtp/peer-profile/uplink/charging-characteristics/roaming/bit9
                            leaf bit9 {
                                type boolean;
                                default "false";
                                description "Set bit in charging characteristics information element";
                            }

                            ///nokia-conf/configure/subscriber-mgmt/gtp/peer-profile/uplink/charging-characteristics/roaming/bit10
                            leaf bit10 {
                                type boolean;
                                default "false";
                                description "Set bit in charging characteristics information element";
                            }

                            ///nokia-conf/configure/subscriber-mgmt/gtp/peer-profile/uplink/charging-characteristics/roaming/bit11
                            leaf bit11 {
                                type boolean;
                                default "false";
                                description "Set bit in charging characteristics information element";
                            }

                            ///nokia-conf/configure/subscriber-mgmt/gtp/peer-profile/uplink/charging-characteristics/roaming/bit12
                            leaf bit12 {
                                type boolean;
                                default "false";
                                description "Set bit in charging characteristics information element";
                            }

                            ///nokia-conf/configure/subscriber-mgmt/gtp/peer-profile/uplink/charging-characteristics/roaming/bit13
                            leaf bit13 {
                                type boolean;
                                default "false";
                                description "Set bit in charging characteristics information element";
                            }

                            ///nokia-conf/configure/subscriber-mgmt/gtp/peer-profile/uplink/charging-characteristics/roaming/bit14
                            leaf bit14 {
                                type boolean;
                                default "false";
                                description "Set bit in charging characteristics information element";
                            }

                            ///nokia-conf/configure/subscriber-mgmt/gtp/peer-profile/uplink/charging-characteristics/roaming/bit15
                            leaf bit15 {
                                type boolean;
                                default "false";
                                description "Set bit in charging characteristics information element";
                            }

                        } // container roaming

                    } // container charging-characteristics

                    ///nokia-conf/configure/subscriber-mgmt/gtp/peer-profile/uplink/ggsn
                    container ggsn {
                        description "Enter the ggsn context";

                        ///nokia-conf/configure/subscriber-mgmt/gtp/peer-profile/uplink/ggsn/qos
                        container qos {
                            description "Enter the qos context";

                            ///nokia-conf/configure/subscriber-mgmt/gtp/peer-profile/uplink/ggsn/qos/arp
                            leaf arp {
                                type uint32 {
                                    range "1..3";
                                }
                                default "1";
                                description "Allocation or retention priority";
                            }

                            ///nokia-conf/configure/subscriber-mgmt/gtp/peer-profile/uplink/ggsn/qos/ambr
                            container ambr {
                                presence "Enable the ambr context";
                                description "Enable the ambr context";

                                ///nokia-conf/configure/subscriber-mgmt/gtp/peer-profile/uplink/ggsn/qos/ambr/down-link
                                leaf down-link {
                                    type int32 {
                                        range "0..10000000";
                                    }
                                    units "kilobps";
                                    mandatory true;
                                    description "Downlink Aggregated Maximum Bit Rate (AMBR)";
                                }

                                ///nokia-conf/configure/subscriber-mgmt/gtp/peer-profile/uplink/ggsn/qos/ambr/up-link
                                leaf up-link {
                                    type int32 {
                                        range "0..10000000";
                                    }
                                    units "kilobps";
                                    mandatory true;
                                    description "Uplink Aggregated Maximum Bit Rate (AMBR)";
                                }

                            } // container ambr

                            ///nokia-conf/configure/subscriber-mgmt/gtp/peer-profile/uplink/ggsn/qos/down-link
                            container down-link {
                                description "Enter the down-link context";

                                ///nokia-conf/configure/subscriber-mgmt/gtp/peer-profile/uplink/ggsn/qos/down-link/gbr
                                leaf gbr {
                                    type uint32 {
                                        range "0..100000";
                                    }
                                    units "kilobps";
                                    default "2000";
                                    description "Guaranteed Bit Rate (GBR)";
                                }

                                ///nokia-conf/configure/subscriber-mgmt/gtp/peer-profile/uplink/ggsn/qos/down-link/mbr
                                leaf mbr {
                                    type uint32 {
                                        range "0..100000";
                                    }
                                    units "kilobps";
                                    default "2000";
                                    description "Maximum Bit Rate (MBR)";
                                }

                            } // container down-link

                            ///nokia-conf/configure/subscriber-mgmt/gtp/peer-profile/uplink/ggsn/qos/up-link
                            container up-link {
                                description "Enter the up-link context";

                                ///nokia-conf/configure/subscriber-mgmt/gtp/peer-profile/uplink/ggsn/qos/up-link/gbr
                                leaf gbr {
                                    type uint32 {
                                        range "0..100000";
                                    }
                                    units "kilobps";
                                    default "5000";
                                    description "Guaranteed Bit Rate (GBR)";
                                }

                                ///nokia-conf/configure/subscriber-mgmt/gtp/peer-profile/uplink/ggsn/qos/up-link/mbr
                                leaf mbr {
                                    type uint32 {
                                        range "0..100000";
                                    }
                                    units "kilobps";
                                    default "5000";
                                    description "Maximum Bit Rate (MBR)";
                                }

                            } // container up-link

                        } // container qos

                    } // container ggsn

                    ///nokia-conf/configure/subscriber-mgmt/gtp/peer-profile/uplink/pgw
                    container pgw {
                        description "Enter the pgw context";

                        ///nokia-conf/configure/subscriber-mgmt/gtp/peer-profile/uplink/pgw/qos
                        container qos {
                            description "Enter the qos context";

                            ///nokia-conf/configure/subscriber-mgmt/gtp/peer-profile/uplink/pgw/qos/arp
                            leaf arp {
                                type uint32 {
                                    range "1..15";
                                }
                                default "1";
                                description "Allocation or retention priority";
                            }

                            ///nokia-conf/configure/subscriber-mgmt/gtp/peer-profile/uplink/pgw/qos/qci
                            leaf qci {
                                type uint32 {
                                    range "1..9";
                                }
                                default "8";
                                description "QoS Class Identifier (QCI) to send in GTP messages";
                            }

                            ///nokia-conf/configure/subscriber-mgmt/gtp/peer-profile/uplink/pgw/qos/ambr
                            container ambr {
                                description "Enter the ambr context";

                                ///nokia-conf/configure/subscriber-mgmt/gtp/peer-profile/uplink/pgw/qos/ambr/down-link
                                leaf down-link {
                                    type int32 {
                                        range "0..10000000";
                                    }
                                    units "kilobps";
                                    default "20000";
                                    description "Downlink Aggregated Maximum Bit Rate (AMBR)";
                                }

                                ///nokia-conf/configure/subscriber-mgmt/gtp/peer-profile/uplink/pgw/qos/ambr/up-link
                                leaf up-link {
                                    type int32 {
                                        range "0..10000000";
                                    }
                                    units "kilobps";
                                    default "10000";
                                    description "Uplink Aggregated Maximum Bit Rate (AMBR)";
                                }

                            } // container ambr

                            ///nokia-conf/configure/subscriber-mgmt/gtp/peer-profile/uplink/pgw/qos/down-link
                            container down-link {
                                description "Enter the down-link context";

                                ///nokia-conf/configure/subscriber-mgmt/gtp/peer-profile/uplink/pgw/qos/down-link/gbr
                                leaf gbr {
                                    type uint32 {
                                        range "0..100000";
                                    }
                                    units "kilobps";
                                    default "0";
                                    description "Guaranteed Bit Rate (GBR)";
                                }

                                ///nokia-conf/configure/subscriber-mgmt/gtp/peer-profile/uplink/pgw/qos/down-link/mbr
                                leaf mbr {
                                    type uint32 {
                                        range "0..100000";
                                    }
                                    units "kilobps";
                                    default "0";
                                    description "Maximum Bit Rate (MBR)";
                                }

                            } // container down-link

                            ///nokia-conf/configure/subscriber-mgmt/gtp/peer-profile/uplink/pgw/qos/up-link
                            container up-link {
                                description "Enter the up-link context";

                                ///nokia-conf/configure/subscriber-mgmt/gtp/peer-profile/uplink/pgw/qos/up-link/gbr
                                leaf gbr {
                                    type uint32 {
                                        range "0..100000";
                                    }
                                    units "kilobps";
                                    default "0";
                                    description "Guaranteed Bit Rate (GBR)";
                                }

                                ///nokia-conf/configure/subscriber-mgmt/gtp/peer-profile/uplink/pgw/qos/up-link/mbr
                                leaf mbr {
                                    type uint32 {
                                        range "0..100000";
                                    }
                                    units "kilobps";
                                    default "0";
                                    description "Maximum Bit Rate (MBR)";
                                }

                            } // container up-link

                        } // container qos

                    } // container pgw

                } // container uplink

            } // list peer-profile

        } // container gtp

    } // grouping conf-submgt-gtp

}
