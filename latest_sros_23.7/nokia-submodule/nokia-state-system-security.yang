submodule nokia-state-system-security {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-router             { prefix "types-router"; }
    import nokia-types-services           { prefix "types-services"; }
    import nokia-types-sros               { prefix "types-sros"; }

    include nokia-state-system-security-aaa;
    include nokia-state-system-security-cpm;
    include nokia-state-system-security-management-access-filter;
    include nokia-state-system-security-pki;
    include nokia-state-system-security-ssh;
    include nokia-state-system-security-tls;
    include nokia-state-system-security-user-parameters;

    sros-ext:sros-major-release "rel23";
    organization "Nokia";
    contact
        "Nokia SR OS Support
         Web: <http://www.nokia.com>";
    description
        "Nokia YANG Data model with operational state for system security parameters. on SR OS based routers.

         Copyright 2016 Nokia. All rights reserved. Reproduction of this document
         is authorized on the condition that the foregoing copyright notice is included.

         This nokia-state-system-security YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-12";

    grouping state-system-security {
        ///nokia-state/state/system/security
        container security {
            description "Enable the security context";

            ///nokia-state/state/system/security/telnet-server-oper-state
            leaf telnet-server-oper-state {
                type types-sros:oper-state;
                description "Indicates the operational status of the telnet server.";
            }

            ///nokia-state/state/system/security/ftp-server-oper-state
            leaf ftp-server-oper-state {
                type types-sros:oper-state;
                description "Indicates the operational status of the FTP server.";
            }

            ///nokia-state/state/system/security/telnet6-server-oper-state
            leaf telnet6-server-oper-state {
                type types-sros:oper-state;
                description "Indicates the operational status of the IPv6 telnet server.";
            }

            ///nokia-state/state/system/security/cpu-protection
            container cpu-protection {
                description "Enable the cpu-protection context";

                ///nokia-state/state/system/security/cpu-protection/violators
                container violators {
                    description "Enter the violators context";

                    ///nokia-state/state/system/security/cpu-protection/violators/interfaces
                    container interfaces {
                        description "Enter the interfaces context";

                        ///nokia-state/state/system/security/cpu-protection/violators/interfaces/overall-rate
                        container overall-rate {
                            description "Enter the overall-rate context";

                            ///nokia-state/state/system/security/cpu-protection/violators/interfaces/overall-rate/interface
                            list interface {
                                key "vrtr-id if-index";
                                description "Enter the interface list instance";

                                ///nokia-state/state/system/security/cpu-protection/violators/interfaces/overall-rate/interface/vrtr-id
                                leaf vrtr-id {
                                    type int32;
                                    description "The virtual router index.";
                                }

                                ///nokia-state/state/system/security/cpu-protection/violators/interfaces/overall-rate/interface/if-index
                                leaf if-index {
                                    type int32;
                                    description "The interface index.";
                                }

                                ///nokia-state/state/system/security/cpu-protection/violators/interfaces/overall-rate/interface/service-name
                                leaf service-name {
                                    type types-services:service-name;
                                    description
                                        "The name of the service containing the interface.
                                         This is only applicable for a service interface.";
                                }

                                ///nokia-state/state/system/security/cpu-protection/violators/interfaces/overall-rate/interface/interface-type
                                leaf interface-type {
                                    type types-router:interface-type;
                                    description "The type of interface.";
                                }

                                ///nokia-state/state/system/security/cpu-protection/violators/interfaces/overall-rate/interface/interface-name
                                leaf interface-name {
                                    type types-sros:interface-name;
                                    description "The name of the interface.";
                                }

                                ///nokia-state/state/system/security/cpu-protection/violators/interfaces/overall-rate/interface/periods
                                leaf periods {
                                    type yang:counter32;
                                    description
                                        "The number of times the rate limit violation was detected.
                                         the sampling interval length is equal to 1 second.";
                                }

                                ///nokia-state/state/system/security/cpu-protection/violators/interfaces/overall-rate/interface/first-time
                                leaf first-time {
                                    type yang:date-and-time;
                                    description "Indicates when the violation occurred for the first time.";
                                }

                                ///nokia-state/state/system/security/cpu-protection/violators/interfaces/overall-rate/interface/last-time
                                leaf last-time {
                                    type yang:date-and-time;
                                    description "Indicates when the violation occurred for the last time.";
                                }

                            } // list interface

                        } // container overall-rate

                        ///nokia-state/state/system/security/cpu-protection/violators/interfaces/out-of-profile-rate
                        container out-of-profile-rate {
                            description "Enter the out-of-profile-rate context";

                            ///nokia-state/state/system/security/cpu-protection/violators/interfaces/out-of-profile-rate/interface
                            list interface {
                                key "vrtr-id if-index";
                                description "Enter the interface list instance";

                                ///nokia-state/state/system/security/cpu-protection/violators/interfaces/out-of-profile-rate/interface/vrtr-id
                                leaf vrtr-id {
                                    type int32;
                                    description "The virtual router index.";
                                }

                                ///nokia-state/state/system/security/cpu-protection/violators/interfaces/out-of-profile-rate/interface/if-index
                                leaf if-index {
                                    type int32;
                                    description "The interface index.";
                                }

                                ///nokia-state/state/system/security/cpu-protection/violators/interfaces/out-of-profile-rate/interface/service-name
                                leaf service-name {
                                    type types-services:service-name;
                                    description
                                        "The name of the service containing the interface.
                                         This is only applicable for a service interface.";
                                }

                                ///nokia-state/state/system/security/cpu-protection/violators/interfaces/out-of-profile-rate/interface/interface-type
                                leaf interface-type {
                                    type types-router:interface-type;
                                    description "The type of interface.";
                                }

                                ///nokia-state/state/system/security/cpu-protection/violators/interfaces/out-of-profile-rate/interface/interface-name
                                leaf interface-name {
                                    type types-sros:interface-name;
                                    description "The name of the interface.";
                                }

                                ///nokia-state/state/system/security/cpu-protection/violators/interfaces/out-of-profile-rate/interface/periods
                                leaf periods {
                                    type yang:counter32;
                                    description
                                        "The number of times the rate limit violation was detected.
                                         the sampling interval length is equal to 1 second.";
                                }

                                ///nokia-state/state/system/security/cpu-protection/violators/interfaces/out-of-profile-rate/interface/first-time
                                leaf first-time {
                                    type yang:date-and-time;
                                    description "Indicates when the violation occurred for the first time.";
                                }

                                ///nokia-state/state/system/security/cpu-protection/violators/interfaces/out-of-profile-rate/interface/last-time
                                leaf last-time {
                                    type yang:date-and-time;
                                    description "Indicates when the violation occurred for the last time.";
                                }

                            } // list interface

                        } // container out-of-profile-rate

                    } // container interfaces

                    ///nokia-state/state/system/security/cpu-protection/violators/saps
                    container saps {
                        description "Enter the saps context";

                        ///nokia-state/state/system/security/cpu-protection/violators/saps/overall-rate
                        container overall-rate {
                            description "Enter the overall-rate context";

                            ///nokia-state/state/system/security/cpu-protection/violators/saps/overall-rate/sap
                            list sap {
                                key "service-id sap-id";
                                description "Enter the sap list instance";

                                ///nokia-state/state/system/security/cpu-protection/violators/saps/overall-rate/sap/service-id
                                leaf service-id {
                                    type types-services:external-service-id;
                                    description "The service index.";
                                }

                                ///nokia-state/state/system/security/cpu-protection/violators/saps/overall-rate/sap/sap-id
                                leaf sap-id {
                                    type types-sros:sap;
                                    description "The SAP identifier.";
                                }

                                ///nokia-state/state/system/security/cpu-protection/violators/saps/overall-rate/sap/sap-type
                                leaf sap-type {
                                    type types-services:service-type;
                                    description "The type of the service containing the SAP or the spoke SDP.";
                                }

                                ///nokia-state/state/system/security/cpu-protection/violators/saps/overall-rate/sap/service-name
                                leaf service-name {
                                    type types-services:service-name;
                                    description "The name of the service containing the SAP or the spoke SDP.";
                                }

                                ///nokia-state/state/system/security/cpu-protection/violators/saps/overall-rate/sap/interface-type
                                leaf interface-type {
                                    type types-router:interface-type;
                                    description "The type of interface.This is only applicable for layer 3 SAPs or spoke SDPs.";
                                }

                                ///nokia-state/state/system/security/cpu-protection/violators/saps/overall-rate/sap/interface-name
                                leaf interface-name {
                                    type types-sros:interface-name;
                                    description "The name of the interface.This is only applicable for layer 3 SAPs or spoke SDPs.";
                                }

                                ///nokia-state/state/system/security/cpu-protection/violators/saps/overall-rate/sap/periods
                                leaf periods {
                                    type yang:counter32;
                                    description
                                        "The number of times the rate limit violation was detected.
                                         the sampling interval length is equal to 1 second.";
                                }

                                ///nokia-state/state/system/security/cpu-protection/violators/saps/overall-rate/sap/first-time
                                leaf first-time {
                                    type yang:date-and-time;
                                    description "Indicates when the violation occurred for the first time.";
                                }

                                ///nokia-state/state/system/security/cpu-protection/violators/saps/overall-rate/sap/last-time
                                leaf last-time {
                                    type yang:date-and-time;
                                    description "Indicates when the violation occurred for the last time.";
                                }

                            } // list sap

                        } // container overall-rate

                        ///nokia-state/state/system/security/cpu-protection/violators/saps/out-of-profile-rate
                        container out-of-profile-rate {
                            description "Enter the out-of-profile-rate context";

                            ///nokia-state/state/system/security/cpu-protection/violators/saps/out-of-profile-rate/sap
                            list sap {
                                key "service-id sap-id";
                                description "Enter the sap list instance";

                                ///nokia-state/state/system/security/cpu-protection/violators/saps/out-of-profile-rate/sap/service-id
                                leaf service-id {
                                    type types-services:external-service-id;
                                    description "The service index.";
                                }

                                ///nokia-state/state/system/security/cpu-protection/violators/saps/out-of-profile-rate/sap/sap-id
                                leaf sap-id {
                                    type types-sros:sap;
                                    description "The SAP identifier.";
                                }

                                ///nokia-state/state/system/security/cpu-protection/violators/saps/out-of-profile-rate/sap/sap-type
                                leaf sap-type {
                                    type types-services:service-type;
                                    description "The type of the service containing the SAP or the spoke SDP.";
                                }

                                ///nokia-state/state/system/security/cpu-protection/violators/saps/out-of-profile-rate/sap/service-name
                                leaf service-name {
                                    type types-services:service-name;
                                    description "The name of the service containing the SAP or the spoke SDP.";
                                }

                                ///nokia-state/state/system/security/cpu-protection/violators/saps/out-of-profile-rate/sap/interface-type
                                leaf interface-type {
                                    type types-router:interface-type;
                                    description "The type of interface.This is only applicable for layer 3 SAPs or spoke SDPs.";
                                }

                                ///nokia-state/state/system/security/cpu-protection/violators/saps/out-of-profile-rate/sap/interface-name
                                leaf interface-name {
                                    type types-sros:interface-name;
                                    description "The name of the interface.This is only applicable for layer 3 SAPs or spoke SDPs.";
                                }

                                ///nokia-state/state/system/security/cpu-protection/violators/saps/out-of-profile-rate/sap/periods
                                leaf periods {
                                    type yang:counter32;
                                    description
                                        "The number of times the rate limit violation was detected.
                                         the sampling interval length is equal to 1 second.";
                                }

                                ///nokia-state/state/system/security/cpu-protection/violators/saps/out-of-profile-rate/sap/first-time
                                leaf first-time {
                                    type yang:date-and-time;
                                    description "Indicates when the violation occurred for the first time.";
                                }

                                ///nokia-state/state/system/security/cpu-protection/violators/saps/out-of-profile-rate/sap/last-time
                                leaf last-time {
                                    type yang:date-and-time;
                                    description "Indicates when the violation occurred for the last time.";
                                }

                            } // list sap

                        } // container out-of-profile-rate

                        ///nokia-state/state/system/security/cpu-protection/violators/saps/eth-cfm-rate
                        container eth-cfm-rate {
                            description "Enter the eth-cfm-rate context";

                            ///nokia-state/state/system/security/cpu-protection/violators/saps/eth-cfm-rate/aggregate-flow
                            list aggregate-flow {
                                key "service-id sap-id level opcode";
                                description "Enter the aggregate-flow list instance";

                                ///nokia-state/state/system/security/cpu-protection/violators/saps/eth-cfm-rate/aggregate-flow/service-id
                                leaf service-id {
                                    type types-services:external-service-id;
                                    description "The service index.";
                                }

                                ///nokia-state/state/system/security/cpu-protection/violators/saps/eth-cfm-rate/aggregate-flow/sap-id
                                leaf sap-id {
                                    type types-sros:sap;
                                    description "The SAP identifier.";
                                }

                                ///nokia-state/state/system/security/cpu-protection/violators/saps/eth-cfm-rate/aggregate-flow/level
                                leaf level {
                                    type types-eth-cfm:mp-level;
                                    description "The Ethernet CFM domain level.";
                                }

                                ///nokia-state/state/system/security/cpu-protection/violators/saps/eth-cfm-rate/aggregate-flow/opcode
                                leaf opcode {
                                    type uint32 {
                                        range "0..255";
                                    }
                                    description "The Ethernet CFM opcode.";
                                }

                                ///nokia-state/state/system/security/cpu-protection/violators/saps/eth-cfm-rate/aggregate-flow/sap-type
                                leaf sap-type {
                                    type types-services:service-type;
                                    description "The type of the service containing the SAP or the spoke SDP.";
                                }

                                ///nokia-state/state/system/security/cpu-protection/violators/saps/eth-cfm-rate/aggregate-flow/service-name
                                leaf service-name {
                                    type types-services:service-name;
                                    description "The name of the service containing the SAP or the spoke SDP.";
                                }

                                ///nokia-state/state/system/security/cpu-protection/violators/saps/eth-cfm-rate/aggregate-flow/interface-type
                                leaf interface-type {
                                    type types-router:interface-type;
                                    description "The type of interface.This is only applicable for layer 3 SAPs or spoke SDPs.";
                                }

                                ///nokia-state/state/system/security/cpu-protection/violators/saps/eth-cfm-rate/aggregate-flow/interface-name
                                leaf interface-name {
                                    type types-sros:interface-name;
                                    description "The name of the interface.This is only applicable for layer 3 SAPs or spoke SDPs.";
                                }

                                ///nokia-state/state/system/security/cpu-protection/violators/saps/eth-cfm-rate/aggregate-flow/periods
                                leaf periods {
                                    type yang:counter32;
                                    description
                                        "The number of times the rate limit violation was detected.
                                         the sampling interval length is equal to 1 second.";
                                }

                                ///nokia-state/state/system/security/cpu-protection/violators/saps/eth-cfm-rate/aggregate-flow/first-time
                                leaf first-time {
                                    type yang:date-and-time;
                                    description "Indicates when the violation occurred for the first time.";
                                }

                                ///nokia-state/state/system/security/cpu-protection/violators/saps/eth-cfm-rate/aggregate-flow/last-time
                                leaf last-time {
                                    type yang:date-and-time;
                                    description "Indicates when the violation occurred for the last time.";
                                }

                            } // list aggregate-flow

                            ///nokia-state/state/system/security/cpu-protection/violators/saps/eth-cfm-rate/mac-flow
                            list mac-flow {
                                key "service-id sap-id mac-address level opcode";
                                description "Enter the mac-flow list instance";

                                ///nokia-state/state/system/security/cpu-protection/violators/saps/eth-cfm-rate/mac-flow/service-id
                                leaf service-id {
                                    type types-services:external-service-id;
                                    description "The service index.";
                                }

                                ///nokia-state/state/system/security/cpu-protection/violators/saps/eth-cfm-rate/mac-flow/sap-id
                                leaf sap-id {
                                    type types-sros:sap;
                                    description "The SAP identifier.";
                                }

                                ///nokia-state/state/system/security/cpu-protection/violators/saps/eth-cfm-rate/mac-flow/mac-address
                                leaf mac-address {
                                    type yang:mac-address;
                                    description "The source MAC address.";
                                }

                                ///nokia-state/state/system/security/cpu-protection/violators/saps/eth-cfm-rate/mac-flow/level
                                leaf level {
                                    type types-eth-cfm:mp-level;
                                    description "The Ethernet CFM domain level.";
                                }

                                ///nokia-state/state/system/security/cpu-protection/violators/saps/eth-cfm-rate/mac-flow/opcode
                                leaf opcode {
                                    type uint32 {
                                        range "0..255";
                                    }
                                    description "The Ethernet CFM opcode.";
                                }

                                ///nokia-state/state/system/security/cpu-protection/violators/saps/eth-cfm-rate/mac-flow/sap-type
                                leaf sap-type {
                                    type types-services:service-type;
                                    description "The type of the service containing the SAP or the spoke SDP.";
                                }

                                ///nokia-state/state/system/security/cpu-protection/violators/saps/eth-cfm-rate/mac-flow/service-name
                                leaf service-name {
                                    type types-services:service-name;
                                    description "The name of the service containing the SAP or the spoke SDP.";
                                }

                                ///nokia-state/state/system/security/cpu-protection/violators/saps/eth-cfm-rate/mac-flow/interface-type
                                leaf interface-type {
                                    type types-router:interface-type;
                                    description "The type of interface.This is only applicable for layer 3 SAPs or spoke SDPs.";
                                }

                                ///nokia-state/state/system/security/cpu-protection/violators/saps/eth-cfm-rate/mac-flow/interface-name
                                leaf interface-name {
                                    type types-sros:interface-name;
                                    description "The name of the interface.This is only applicable for layer 3 SAPs or spoke SDPs.";
                                }

                                ///nokia-state/state/system/security/cpu-protection/violators/saps/eth-cfm-rate/mac-flow/periods
                                leaf periods {
                                    type yang:counter32;
                                    description
                                        "The number of times the rate limit violation was detected.
                                         the sampling interval length is equal to 1 second.";
                                }

                                ///nokia-state/state/system/security/cpu-protection/violators/saps/eth-cfm-rate/mac-flow/first-time
                                leaf first-time {
                                    type yang:date-and-time;
                                    description "Indicates when the violation occurred for the first time.";
                                }

                                ///nokia-state/state/system/security/cpu-protection/violators/saps/eth-cfm-rate/mac-flow/last-time
                                leaf last-time {
                                    type yang:date-and-time;
                                    description "Indicates when the violation occurred for the last time.";
                                }

                            } // list mac-flow

                        } // container eth-cfm-rate

                    } // container saps

                    ///nokia-state/state/system/security/cpu-protection/violators/sdps
                    container sdps {
                        description "Enter the sdps context";

                        ///nokia-state/state/system/security/cpu-protection/violators/sdps/overall-rate
                        container overall-rate {
                            description "Enter the overall-rate context";

                            ///nokia-state/state/system/security/cpu-protection/violators/sdps/overall-rate/spoke-sdp
                            list spoke-sdp {
                                key "service-id sdp-bind-id";
                                description "Enter the spoke-sdp list instance";

                                ///nokia-state/state/system/security/cpu-protection/violators/sdps/overall-rate/spoke-sdp/service-id
                                leaf service-id {
                                    type types-services:external-service-id;
                                    description "The service index.";
                                }

                                ///nokia-state/state/system/security/cpu-protection/violators/sdps/overall-rate/spoke-sdp/sdp-bind-id
                                leaf sdp-bind-id {
                                    type types-services:sdp-bind-id;
                                    description "The spoke SDP identifier.";
                                }

                                ///nokia-state/state/system/security/cpu-protection/violators/sdps/overall-rate/spoke-sdp/sap-type
                                leaf sap-type {
                                    type types-services:service-type;
                                    description "The type of the service containing the SAP or the spoke SDP.";
                                }

                                ///nokia-state/state/system/security/cpu-protection/violators/sdps/overall-rate/spoke-sdp/service-name
                                leaf service-name {
                                    type types-services:service-name;
                                    description "The name of the service containing the SAP or the spoke SDP.";
                                }

                                ///nokia-state/state/system/security/cpu-protection/violators/sdps/overall-rate/spoke-sdp/interface-type
                                leaf interface-type {
                                    type types-router:interface-type;
                                    description "The type of interface.This is only applicable for layer 3 SAPs or spoke SDPs.";
                                }

                                ///nokia-state/state/system/security/cpu-protection/violators/sdps/overall-rate/spoke-sdp/interface-name
                                leaf interface-name {
                                    type types-sros:interface-name;
                                    description "The name of the interface.This is only applicable for layer 3 SAPs or spoke SDPs.";
                                }

                                ///nokia-state/state/system/security/cpu-protection/violators/sdps/overall-rate/spoke-sdp/periods
                                leaf periods {
                                    type yang:counter32;
                                    description
                                        "The number of times the rate limit violation was detected.
                                         the sampling interval length is equal to 1 second.";
                                }

                                ///nokia-state/state/system/security/cpu-protection/violators/sdps/overall-rate/spoke-sdp/first-time
                                leaf first-time {
                                    type yang:date-and-time;
                                    description "Indicates when the violation occurred for the first time.";
                                }

                                ///nokia-state/state/system/security/cpu-protection/violators/sdps/overall-rate/spoke-sdp/last-time
                                leaf last-time {
                                    type yang:date-and-time;
                                    description "Indicates when the violation occurred for the last time.";
                                }

                            } // list spoke-sdp

                        } // container overall-rate

                        ///nokia-state/state/system/security/cpu-protection/violators/sdps/out-of-profile-rate
                        container out-of-profile-rate {
                            description "Enter the out-of-profile-rate context";

                            ///nokia-state/state/system/security/cpu-protection/violators/sdps/out-of-profile-rate/spoke-sdp
                            list spoke-sdp {
                                key "service-id sdp-bind-id";
                                description "Enter the spoke-sdp list instance";

                                ///nokia-state/state/system/security/cpu-protection/violators/sdps/out-of-profile-rate/spoke-sdp/service-id
                                leaf service-id {
                                    type types-services:external-service-id;
                                    description "The service index.";
                                }

                                ///nokia-state/state/system/security/cpu-protection/violators/sdps/out-of-profile-rate/spoke-sdp/sdp-bind-id
                                leaf sdp-bind-id {
                                    type types-services:sdp-bind-id;
                                    description "The spoke SDP identifier.";
                                }

                                ///nokia-state/state/system/security/cpu-protection/violators/sdps/out-of-profile-rate/spoke-sdp/sap-type
                                leaf sap-type {
                                    type types-services:service-type;
                                    description "The type of the service containing the SAP or the spoke SDP.";
                                }

                                ///nokia-state/state/system/security/cpu-protection/violators/sdps/out-of-profile-rate/spoke-sdp/service-name
                                leaf service-name {
                                    type types-services:service-name;
                                    description "The name of the service containing the SAP or the spoke SDP.";
                                }

                                ///nokia-state/state/system/security/cpu-protection/violators/sdps/out-of-profile-rate/spoke-sdp/interface-type
                                leaf interface-type {
                                    type types-router:interface-type;
                                    description "The type of interface.This is only applicable for layer 3 SAPs or spoke SDPs.";
                                }

                                ///nokia-state/state/system/security/cpu-protection/violators/sdps/out-of-profile-rate/spoke-sdp/interface-name
                                leaf interface-name {
                                    type types-sros:interface-name;
                                    description "The name of the interface.This is only applicable for layer 3 SAPs or spoke SDPs.";
                                }

                                ///nokia-state/state/system/security/cpu-protection/violators/sdps/out-of-profile-rate/spoke-sdp/periods
                                leaf periods {
                                    type yang:counter32;
                                    description
                                        "The number of times the rate limit violation was detected.
                                         the sampling interval length is equal to 1 second.";
                                }

                                ///nokia-state/state/system/security/cpu-protection/violators/sdps/out-of-profile-rate/spoke-sdp/first-time
                                leaf first-time {
                                    type yang:date-and-time;
                                    description "Indicates when the violation occurred for the first time.";
                                }

                                ///nokia-state/state/system/security/cpu-protection/violators/sdps/out-of-profile-rate/spoke-sdp/last-time
                                leaf last-time {
                                    type yang:date-and-time;
                                    description "Indicates when the violation occurred for the last time.";
                                }

                            } // list spoke-sdp

                        } // container out-of-profile-rate

                        ///nokia-state/state/system/security/cpu-protection/violators/sdps/eth-cfm-rate
                        container eth-cfm-rate {
                            description "Enter the eth-cfm-rate context";

                            ///nokia-state/state/system/security/cpu-protection/violators/sdps/eth-cfm-rate/aggregate-flow
                            list aggregate-flow {
                                key "service-id sdp-bind-id level opcode";
                                description "Enter the aggregate-flow list instance";

                                ///nokia-state/state/system/security/cpu-protection/violators/sdps/eth-cfm-rate/aggregate-flow/service-id
                                leaf service-id {
                                    type types-services:external-service-id;
                                    description "The service index.";
                                }

                                ///nokia-state/state/system/security/cpu-protection/violators/sdps/eth-cfm-rate/aggregate-flow/sdp-bind-id
                                leaf sdp-bind-id {
                                    type types-services:sdp-bind-id;
                                    description "The spoke SDP identifier.";
                                }

                                ///nokia-state/state/system/security/cpu-protection/violators/sdps/eth-cfm-rate/aggregate-flow/level
                                leaf level {
                                    type types-eth-cfm:mp-level;
                                    description "The Ethernet CFM domain level.";
                                }

                                ///nokia-state/state/system/security/cpu-protection/violators/sdps/eth-cfm-rate/aggregate-flow/opcode
                                leaf opcode {
                                    type uint32 {
                                        range "0..255";
                                    }
                                    description "The Ethernet CFM opcode.";
                                }

                                ///nokia-state/state/system/security/cpu-protection/violators/sdps/eth-cfm-rate/aggregate-flow/sap-type
                                leaf sap-type {
                                    type types-services:service-type;
                                    description "The type of the service containing the SAP or the spoke SDP.";
                                }

                                ///nokia-state/state/system/security/cpu-protection/violators/sdps/eth-cfm-rate/aggregate-flow/service-name
                                leaf service-name {
                                    type types-services:service-name;
                                    description "The name of the service containing the SAP or the spoke SDP.";
                                }

                                ///nokia-state/state/system/security/cpu-protection/violators/sdps/eth-cfm-rate/aggregate-flow/interface-type
                                leaf interface-type {
                                    type types-router:interface-type;
                                    description "The type of interface.This is only applicable for layer 3 SAPs or spoke SDPs.";
                                }

                                ///nokia-state/state/system/security/cpu-protection/violators/sdps/eth-cfm-rate/aggregate-flow/interface-name
                                leaf interface-name {
                                    type types-sros:interface-name;
                                    description "The name of the interface.This is only applicable for layer 3 SAPs or spoke SDPs.";
                                }

                                ///nokia-state/state/system/security/cpu-protection/violators/sdps/eth-cfm-rate/aggregate-flow/periods
                                leaf periods {
                                    type yang:counter32;
                                    description
                                        "The number of times the rate limit violation was detected.
                                         the sampling interval length is equal to 1 second.";
                                }

                                ///nokia-state/state/system/security/cpu-protection/violators/sdps/eth-cfm-rate/aggregate-flow/first-time
                                leaf first-time {
                                    type yang:date-and-time;
                                    description "Indicates when the violation occurred for the first time.";
                                }

                                ///nokia-state/state/system/security/cpu-protection/violators/sdps/eth-cfm-rate/aggregate-flow/last-time
                                leaf last-time {
                                    type yang:date-and-time;
                                    description "Indicates when the violation occurred for the last time.";
                                }

                            } // list aggregate-flow

                            ///nokia-state/state/system/security/cpu-protection/violators/sdps/eth-cfm-rate/mac-flow
                            list mac-flow {
                                key "service-id sdp-bind-id mac-address level opcode";
                                description "Enter the mac-flow list instance";

                                ///nokia-state/state/system/security/cpu-protection/violators/sdps/eth-cfm-rate/mac-flow/service-id
                                leaf service-id {
                                    type types-services:external-service-id;
                                    description "The service index.";
                                }

                                ///nokia-state/state/system/security/cpu-protection/violators/sdps/eth-cfm-rate/mac-flow/sdp-bind-id
                                leaf sdp-bind-id {
                                    type types-services:sdp-bind-id;
                                    description "The spoke SDP identifier.";
                                }

                                ///nokia-state/state/system/security/cpu-protection/violators/sdps/eth-cfm-rate/mac-flow/mac-address
                                leaf mac-address {
                                    type yang:mac-address;
                                    description "The source MAC address.";
                                }

                                ///nokia-state/state/system/security/cpu-protection/violators/sdps/eth-cfm-rate/mac-flow/level
                                leaf level {
                                    type types-eth-cfm:mp-level;
                                    description "The Ethernet CFM domain level.";
                                }

                                ///nokia-state/state/system/security/cpu-protection/violators/sdps/eth-cfm-rate/mac-flow/opcode
                                leaf opcode {
                                    type uint32 {
                                        range "0..255";
                                    }
                                    description "The Ethernet CFM opcode.";
                                }

                                ///nokia-state/state/system/security/cpu-protection/violators/sdps/eth-cfm-rate/mac-flow/sap-type
                                leaf sap-type {
                                    type types-services:service-type;
                                    description "The type of the service containing the SAP or the spoke SDP.";
                                }

                                ///nokia-state/state/system/security/cpu-protection/violators/sdps/eth-cfm-rate/mac-flow/service-name
                                leaf service-name {
                                    type types-services:service-name;
                                    description "The name of the service containing the SAP or the spoke SDP.";
                                }

                                ///nokia-state/state/system/security/cpu-protection/violators/sdps/eth-cfm-rate/mac-flow/interface-type
                                leaf interface-type {
                                    type types-router:interface-type;
                                    description "The type of interface.This is only applicable for layer 3 SAPs or spoke SDPs.";
                                }

                                ///nokia-state/state/system/security/cpu-protection/violators/sdps/eth-cfm-rate/mac-flow/interface-name
                                leaf interface-name {
                                    type types-sros:interface-name;
                                    description "The name of the interface.This is only applicable for layer 3 SAPs or spoke SDPs.";
                                }

                                ///nokia-state/state/system/security/cpu-protection/violators/sdps/eth-cfm-rate/mac-flow/periods
                                leaf periods {
                                    type yang:counter32;
                                    description
                                        "The number of times the rate limit violation was detected.
                                         the sampling interval length is equal to 1 second.";
                                }

                                ///nokia-state/state/system/security/cpu-protection/violators/sdps/eth-cfm-rate/mac-flow/first-time
                                leaf first-time {
                                    type yang:date-and-time;
                                    description "Indicates when the violation occurred for the first time.";
                                }

                                ///nokia-state/state/system/security/cpu-protection/violators/sdps/eth-cfm-rate/mac-flow/last-time
                                leaf last-time {
                                    type yang:date-and-time;
                                    description "Indicates when the violation occurred for the last time.";
                                }

                            } // list mac-flow

                        } // container eth-cfm-rate

                    } // container sdps

                    ///nokia-state/state/system/security/cpu-protection/violators/ports
                    container ports {
                        description "Enter the ports context";

                        ///nokia-state/state/system/security/cpu-protection/violators/ports/port
                        list port {
                            key "port-id";
                            description "Enter the port list instance";

                            ///nokia-state/state/system/security/cpu-protection/violators/ports/port/port-id
                            leaf port-id {
                                type types-sros:port;
                                description "The identifier that uniquely identifies the port.";
                            }

                            ///nokia-state/state/system/security/cpu-protection/violators/ports/port/link-specific-rate
                            container link-specific-rate {
                                description "Enter the link-specific-rate context";

                                ///nokia-state/state/system/security/cpu-protection/violators/ports/port/link-specific-rate/periods
                                leaf periods {
                                    type yang:counter32;
                                    description
                                        "The number of times the rate limit violation was detected.
                                         the sampling interval length is equal to 1 second.";
                                }

                                ///nokia-state/state/system/security/cpu-protection/violators/ports/port/link-specific-rate/first-time
                                leaf first-time {
                                    type yang:date-and-time;
                                    description "Indicates when the violation occurred for the first time.";
                                }

                                ///nokia-state/state/system/security/cpu-protection/violators/ports/port/link-specific-rate/last-time
                                leaf last-time {
                                    type yang:date-and-time;
                                    description "Indicates when the violation occurred for the last time.";
                                }

                            } // container link-specific-rate

                            ///nokia-state/state/system/security/cpu-protection/violators/ports/port/overall-rate
                            container overall-rate {
                                description "Enter the overall-rate context";

                                ///nokia-state/state/system/security/cpu-protection/violators/ports/port/overall-rate/periods
                                leaf periods {
                                    type yang:counter32;
                                    description
                                        "The number of times the rate limit violation was detected.
                                         the sampling interval length is equal to 1 second.";
                                }

                                ///nokia-state/state/system/security/cpu-protection/violators/ports/port/overall-rate/first-time
                                leaf first-time {
                                    type yang:date-and-time;
                                    description "Indicates when the violation occurred for the first time.";
                                }

                                ///nokia-state/state/system/security/cpu-protection/violators/ports/port/overall-rate/last-time
                                leaf last-time {
                                    type yang:date-and-time;
                                    description "Indicates when the violation occurred for the last time.";
                                }

                            } // container overall-rate

                        } // list port

                    } // container ports

                    ///nokia-state/state/system/security/cpu-protection/violators/mac-sources
                    container mac-sources {
                        description "Enter the mac-sources context";

                        ///nokia-state/state/system/security/cpu-protection/violators/mac-sources/sap-sources
                        container sap-sources {
                            description "Enter the sap-sources context";

                            ///nokia-state/state/system/security/cpu-protection/violators/mac-sources/sap-sources/mac-source
                            list mac-source {
                                key "service-id sap-id mac-address";
                                description "Enter the mac-source list instance";

                                ///nokia-state/state/system/security/cpu-protection/violators/mac-sources/sap-sources/mac-source/service-id
                                leaf service-id {
                                    type types-services:external-service-id;
                                    description "The service index.";
                                }

                                ///nokia-state/state/system/security/cpu-protection/violators/mac-sources/sap-sources/mac-source/sap-id
                                leaf sap-id {
                                    type types-sros:sap;
                                    description "The SAP identifier.";
                                }

                                ///nokia-state/state/system/security/cpu-protection/violators/mac-sources/sap-sources/mac-source/mac-address
                                leaf mac-address {
                                    type yang:mac-address;
                                    description "MAC address.";
                                }

                                ///nokia-state/state/system/security/cpu-protection/violators/mac-sources/sap-sources/mac-source/sap-type
                                leaf sap-type {
                                    type types-services:service-type;
                                    description "The type of the service containing the SAP or the spoke SDP.";
                                }

                                ///nokia-state/state/system/security/cpu-protection/violators/mac-sources/sap-sources/mac-source/service-name
                                leaf service-name {
                                    type types-services:service-name;
                                    description "The name of the service containing the SAP or the spoke SDP.";
                                }

                                ///nokia-state/state/system/security/cpu-protection/violators/mac-sources/sap-sources/mac-source/interface-type
                                leaf interface-type {
                                    type types-router:interface-type;
                                    description "The type of interface.This is only applicable for layer 3 SAPs or spoke SDPs.";
                                }

                                ///nokia-state/state/system/security/cpu-protection/violators/mac-sources/sap-sources/mac-source/interface-name
                                leaf interface-name {
                                    type types-sros:interface-name;
                                    description "The name of the interface.This is only applicable for layer 3 SAPs or spoke SDPs.";
                                }

                                ///nokia-state/state/system/security/cpu-protection/violators/mac-sources/sap-sources/mac-source/periods
                                leaf periods {
                                    type yang:counter32;
                                    description
                                        "The number of times the rate limit violation was detected.
                                         the sampling interval length is equal to 1 second.";
                                }

                                ///nokia-state/state/system/security/cpu-protection/violators/mac-sources/sap-sources/mac-source/first-time
                                leaf first-time {
                                    type yang:date-and-time;
                                    description "Indicates when the violation occurred for the first time.";
                                }

                                ///nokia-state/state/system/security/cpu-protection/violators/mac-sources/sap-sources/mac-source/last-time
                                leaf last-time {
                                    type yang:date-and-time;
                                    description "Indicates when the violation occurred for the last time.";
                                }

                            } // list mac-source

                        } // container sap-sources

                    } // container mac-sources

                } // container violators

            } // container cpu-protection

            ///nokia-state/state/system/security/dot1x
            container dot1x {
                description "Enter the dot1x context";

                ///nokia-state/state/system/security/dot1x/radius-policy
                list radius-policy {
                    key "policy-name";
                    description "Enter the radius-policy list instance";

                    ///nokia-state/state/system/security/dot1x/radius-policy/policy-name
                    leaf policy-name {
                        type types-sros:named-item;
                        description "RADIUS server policy name for 802.1X authentication";
                    }

                    ///nokia-state/state/system/security/dot1x/radius-policy/server
                    list server {
                        key "server-index";
                        description "Enter the server list instance";

                        ///nokia-state/state/system/security/dot1x/radius-policy/server/server-index
                        leaf server-index {
                            type uint32 {
                                range "1..5";
                            }
                            description "RADIUS server index";
                        }

                        ///nokia-state/state/system/security/dot1x/radius-policy/server/oper-state
                        leaf oper-state {
                            type types-sros:oper-state;
                            description "Indicates the current status of the RADIUS server";
                        }

                    } // list server

                } // list radius-policy

            } // container dot1x

            ///nokia-state/state/system/security/keychains
            container keychains {
                description "Enter the keychains context";

                ///nokia-state/state/system/security/keychains/keychain
                list keychain {
                    key "keychain-name";
                    description "Enter the keychain list instance";

                    ///nokia-state/state/system/security/keychains/keychain/keychain-name
                    leaf keychain-name {
                        type types-sros:named-item;
                        description "Keychain name";
                    }

                    ///nokia-state/state/system/security/keychains/keychain/oper-state
                    leaf oper-state {
                        type types-sros:oper-state;
                        description "Indicates the operational state of the keychain.";
                    }

                    ///nokia-state/state/system/security/keychains/keychain/expired
                    leaf expired {
                        type boolean;
                        description "Indicates if the keychain is expired.";
                    }

                } // list keychain

            } // container keychains

            ///nokia-state/state/system/security/source-address
            container source-address {
                description "Enter the source-address context";

                ///nokia-state/state/system/security/source-address/ipv4
                list ipv4 {
                    key "application";
                    description "Enter the ipv4 list instance";

                    ///nokia-state/state/system/security/source-address/ipv4/application
                    leaf application {
                        type enumeration {
                            enum telnet                         { value 1; }
                            enum ftp                            { value 2; }
                            enum ssh                            { value 3; }
                            enum radius                         { value 4; }
                            enum tacplus                        { value 5; }
                            enum snmptrap                       { value 6; }
                            enum syslog                         { value 7; }
                            enum ping                           { value 8; }
                            enum traceroute                     { value 9; }
                            enum dns                            { value 10; }
                            enum sntp                           { value 11; }
                            enum ntp                            { value 12; }
                            enum cflowd                         { value 13; }
                            enum ptp                            { value 23; }
                            enum mcreporter                     { value 24; }
                            enum sflow                          { value 27; }
                            enum icmp-error                     { value 29; }
                            enum ldap                           { value 31; }
                        }
                        description "Application that uses the source IP address";
                    }

                    ///nokia-state/state/system/security/source-address/ipv4/oper-state
                    leaf oper-state {
                        type types-sros:up-down-status;
                        description "Indicates the operational status of the source IP entry.";
                    }

                } // list ipv4

                ///nokia-state/state/system/security/source-address/ipv6
                list ipv6 {
                    key "application";
                    description "Enter the ipv6 list instance";

                    ///nokia-state/state/system/security/source-address/ipv6/application
                    leaf application {
                        type enumeration {
                            enum telnet                         { value 14; }
                            enum ftp                            { value 15; }
                            enum radius                         { value 16; }
                            enum tacplus                        { value 17; }
                            enum snmptrap                       { value 18; }
                            enum syslog                         { value 19; }
                            enum ping                           { value 20; }
                            enum traceroute                     { value 21; }
                            enum dns                            { value 22; }
                            enum cflowd                         { value 25; }
                            enum ntp                            { value 26; }
                            enum sflow                          { value 28; }
                            enum icmp6-error                    { value 30; }
                            enum ldap                           { value 32; }
                            enum ssh                            { value 33; }
                            enum ptp                            { value 34; }
                        }
                        description "Application which uses the source IPv6 address";
                    }

                    ///nokia-state/state/system/security/source-address/ipv6/oper-state
                    leaf oper-state {
                        type types-sros:up-down-status;
                        description "Indicates the operational status of the soure IPv6 entry.";
                    }

                } // list ipv6

            } // container source-address

            ///nokia-state/state/system/security/management
            container management {
                description "Enter the management context";

                ///nokia-state/state/system/security/management/global
                container global {
                    description "Enter the global context";

                    ///nokia-state/state/system/security/management/global/telnet
                    container telnet {
                        description "Enter the telnet context";

                        ///nokia-state/state/system/security/management/global/telnet/admin-state
                        leaf admin-state {
                            status obsolete;
                            type types-sros:admin-state;
                            description "The administrative state for global server";
                        }

                        ///nokia-state/state/system/security/management/global/telnet/oper-state
                        leaf oper-state {
                            type types-sros:oper-state;
                            description "Indicates the current oper state of global server";
                        }

                    } // container telnet

                    ///nokia-state/state/system/security/management/global/telnet6
                    container telnet6 {
                        description "Enter the telnet6 context";

                        ///nokia-state/state/system/security/management/global/telnet6/admin-state
                        leaf admin-state {
                            status obsolete;
                            type types-sros:admin-state;
                            description "The administrative state for global server";
                        }

                        ///nokia-state/state/system/security/management/global/telnet6/oper-state
                        leaf oper-state {
                            type types-sros:oper-state;
                            description "Indicates the current oper state of global server";
                        }

                    } // container telnet6

                    ///nokia-state/state/system/security/management/global/ftp
                    container ftp {
                        description "Enter the ftp context";

                        ///nokia-state/state/system/security/management/global/ftp/admin-state
                        leaf admin-state {
                            status obsolete;
                            type types-sros:admin-state;
                            description "The administrative state for global server";
                        }

                        ///nokia-state/state/system/security/management/global/ftp/oper-state
                        leaf oper-state {
                            type types-sros:oper-state;
                            description "Indicates the current oper state of global server";
                        }

                    } // container ftp

                    ///nokia-state/state/system/security/management/global/ssh
                    container ssh {
                        description "Enter the ssh context";

                        ///nokia-state/state/system/security/management/global/ssh/admin-state
                        leaf admin-state {
                            status obsolete;
                            type types-sros:admin-state;
                            description "The administrative state for global server";
                        }

                        ///nokia-state/state/system/security/management/global/ssh/oper-state
                        leaf oper-state {
                            type types-sros:oper-state;
                            description "Indicates the current oper state of global server";
                        }

                    } // container ssh

                    ///nokia-state/state/system/security/management/global/netconf
                    container netconf {
                        description "Enter the netconf context";

                        ///nokia-state/state/system/security/management/global/netconf/admin-state
                        leaf admin-state {
                            status obsolete;
                            type types-sros:admin-state;
                            description "The administrative state for global server";
                        }

                        ///nokia-state/state/system/security/management/global/netconf/oper-state
                        leaf oper-state {
                            type types-sros:oper-state;
                            description "Indicates the current oper state of global server";
                        }

                    } // container netconf

                    ///nokia-state/state/system/security/management/global/grpc
                    container grpc {
                        description "Enter the grpc context";

                        ///nokia-state/state/system/security/management/global/grpc/admin-state
                        leaf admin-state {
                            status obsolete;
                            type types-sros:admin-state;
                            description "The administrative state for global server";
                        }

                        ///nokia-state/state/system/security/management/global/grpc/oper-state
                        leaf oper-state {
                            type types-sros:oper-state;
                            description "Indicates the current oper state of global server";
                        }

                    } // container grpc

                } // container global

                ///nokia-state/state/system/security/management/router-instance
                list router-instance {
                    key "router";
                    description "Enter the router-instance list instance";

                    ///nokia-state/state/system/security/management/router-instance/router
                    leaf router {
                        type types-sros:router-instance;
                        description "Server router instance";
                    }

                    ///nokia-state/state/system/security/management/router-instance/allow-telnet
                    leaf allow-telnet {
                        type boolean;
                        description "Allow/disallow access to telnet server.";
                    }

                    ///nokia-state/state/system/security/management/router-instance/allow-telnet6
                    leaf allow-telnet6 {
                        type boolean;
                        description "Allow/disallow access to telnet IPv6 server.";
                    }

                    ///nokia-state/state/system/security/management/router-instance/allow-ftp
                    leaf allow-ftp {
                        type boolean;
                        description "Allow/disallow access to ftp server.";
                    }

                    ///nokia-state/state/system/security/management/router-instance/allow-ssh
                    leaf allow-ssh {
                        type boolean;
                        description "Allow/disallow access to ssh server.";
                    }

                    ///nokia-state/state/system/security/management/router-instance/allow-netconf
                    leaf allow-netconf {
                        type boolean;
                        description "Allow/disallow access to netconf server.";
                    }

                    ///nokia-state/state/system/security/management/router-instance/allow-grpc
                    leaf allow-grpc {
                        type boolean;
                        description "Allow/disallow access to grpc server.";
                    }

                } // list router-instance

            } // container management

            uses state-system-security-aaa;
            uses state-system-security-cpm-cpm-filter;
            uses state-system-security-cpm-cpm-queue;
            uses state-system-security-management-access-filter;
            uses state-system-security-pki;
            uses state-system-security-ssh;
            uses state-system-security-tls;
            uses state-system-security-user-parameters-user-params;
        } // container security

    } // grouping state-system-security

}
