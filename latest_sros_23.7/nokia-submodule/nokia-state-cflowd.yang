submodule nokia-state-cflowd {

    yang-version "1.1";

    belongs-to nokia-state { prefix "state"; }

    import ietf-yang-types                { prefix "yang"; }
    import nokia-sros-yang-extensions     { prefix "sros-ext"; }
    import nokia-types-cflowd             { prefix "types-cflowd"; }
    import nokia-types-qos                { prefix "types-qos"; }
    import nokia-types-sros               { prefix "types-sros"; }

    sros-ext:sros-major-release "rel23";
    organization "Nokia";
    contact
        "Nokia SR OS Support
         Web: <http://www.nokia.com>";
    description
        "Nokia YANG Data model with operational state for Cflowd configuration on SR OS based routers.

         Copyright 2016 Nokia. All rights reserved. Reproduction of this document
         is authorized on the condition that the foregoing copyright notice is included.

         This nokia-state-cflowd YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-31";

    grouping state-cflowd {
        ///nokia-state/state/cflowd
        container cflowd {
            description "Enable the cflowd context";

            ///nokia-state/state/cflowd/max-collectors
            leaf max-collectors {
                type int32 {
                    range "0..8";
                }
                description
                    "Specifies the maximum number of row entries that can be created in the
                     collector table.

                     Current implementation does not allow to configure this field.";
            }

            ///nokia-state/state/cflowd/oper-state
            leaf oper-state {
                type types-sros:oper-state;
                description "Indicates current operational status of the Cflowd data analysis.";
            }

            ///nokia-state/state/cflowd/active-flows
            leaf active-flows {
                type yang:gauge32;
                description "Indicates current number of active flows being collected.";
            }

            ///nokia-state/state/cflowd/aggregation
            leaf aggregation {
                type yang:gauge32;
                description
                    "Indicates aggregation scheme(s) currently used to aggregate multiple individual
                     flows into an aggregated flow for export to one or more remote host
                     collectors.

                     If no aggregation scheme is specified, {}, no data will be exported.
                     If the 'raw (5)' scheme is specified, flow data is exported without
                     aggregation in version 5 format.  All other aggregation types use
                     version 8 format to export the flow data to the remote host
                     collector.";
            }

            ///nokia-state/state/cflowd/total-packets-received
            leaf total-packets-received {
                type yang:counter64;
                description "Indicates the total number of packets received for Cflowd.";
            }

            ///nokia-state/state/cflowd/total-packets-dropped
            leaf total-packets-dropped {
                type yang:counter64;
                description "Indicates the total number of packets dropped for Cflowd.";
            }

            ///nokia-state/state/cflowd/raw-flows-created
            leaf raw-flows-created {
                type yang:counter64;
                description "Indicates the total number of raw flows created by system.";
            }

            ///nokia-state/state/cflowd/aggregate-flows-created
            leaf aggregate-flows-created {
                type yang:counter64;
                description "Indicates the total number of aggregate flows created by system.";
            }

            ///nokia-state/state/cflowd/raw-flows-matched
            leaf raw-flows-matched {
                type yang:counter64;
                description "Indicates the number of raw packets matched to an existing raw flow.";
            }

            ///nokia-state/state/cflowd/aggregate-flows-matched
            leaf aggregate-flows-matched {
                type yang:counter64;
                description "Indicates the number of packets matched to an existing aggregate flow.";
            }

            ///nokia-state/state/cflowd/raw-flows-flushed
            leaf raw-flows-flushed {
                type yang:counter64;
                description "Indicates the number of raw flows flushed.";
            }

            ///nokia-state/state/cflowd/aggregate-flows-flushed
            leaf aggregate-flows-flushed {
                type yang:counter64;
                description "Indicates the number of aggregate flows flushed.";
            }

            ///nokia-state/state/cflowd/overflow-events
            leaf overflow-events {
                type yang:counter64;
                description
                    "Indicates the number of times the flow cache has entered
                     the overflow state.";
            }

            ///nokia-state/state/cflowd/dropped-flows
            leaf dropped-flows {
                type yang:counter64;
                description
                    "Indicates the number of times a flow was dropped.
                     Data from dropped flows are not reported to any collector.";
            }

            ///nokia-state/state/cflowd/version
            list version {
                key "version-index";
                description "Enter the version list instance";

                ///nokia-state/state/cflowd/version/version-index
                leaf version-index {
                    type types-cflowd:collector-version;
                    description "The cflowd collector version.";
                }

                ///nokia-state/state/cflowd/version/status
                leaf status {
                    type boolean;
                    description "Whether or not a collector of the specified version is in use.";
                }

                ///nokia-state/state/cflowd/version/sent-packets
                leaf sent-packets {
                    type yang:counter64;
                    units "packets";
                    description "The number of packets transmitted for the specified version";
                }

                ///nokia-state/state/cflowd/version/open-packets
                leaf open-packets {
                    type yang:counter64;
                    units "packets";
                    description "The number of open packets pending for the specified version";
                }

                ///nokia-state/state/cflowd/version/errored-packets
                leaf errored-packets {
                    type yang:counter64;
                    units "packets";
                    description "The number of errored packets for the specified version";
                }

            } // list version

            ///nokia-state/state/cflowd/collector
            list collector {
                key "ip-address port";
                description "Enter the collector list instance";

                ///nokia-state/state/cflowd/collector/ip-address
                leaf ip-address {
                    type types-sros:ip-unicast-address;
                    description "IP address of the remote cflowd collector host";
                }

                ///nokia-state/state/cflowd/collector/port
                leaf port {
                    type types-qos:tcp-udp-match-port {
                        range "1..65535";
                    }
                    description "UDP port number of the remote cflowd collector host";
                }

                ///nokia-state/state/cflowd/collector/oper-state
                leaf oper-state {
                    type types-sros:oper-state;
                    description "Indicates the current operational status of this remote collector host.";
                }

                ///nokia-state/state/cflowd/collector/records-sent
                leaf records-sent {
                    type yang:counter64;
                    description
                        "Indicates the number of Cflowd records that have been transmitted
                         to this remote collector host.";
                }

                ///nokia-state/state/cflowd/collector/last-packet-sent
                leaf last-packet-sent {
                    type types-sros:date-time;
                    description
                        "Indicates the time, when the last Cflowd packet was sent to this
                         remote collector host.";
                }

                ///nokia-state/state/cflowd/collector/packets-sent
                leaf packets-sent {
                    type yang:counter64;
                    description
                        "Indicates the number of Cflowd packets that have been transmitted
                         to this remote collector host.";
                }

                ///nokia-state/state/cflowd/collector/template-statistics
                list template-statistics {
                    key "template-flow-index";
                    description "Enter the template-statistics list instance";

                    ///nokia-state/state/cflowd/collector/template-statistics/template-flow-index
                    leaf template-flow-index {
                        type enumeration {
                            enum ipv4                           { value 1; }
                            enum mpls                           { value 2; }
                            enum ipv6                           { value 3; }
                            enum l2                             { value 4; }
                        }
                        description "The template flow type.";
                    }

                    ///nokia-state/state/cflowd/collector/template-statistics/last-transmit-time
                    leaf last-transmit-time {
                        type yang:date-and-time;
                        description "The time, since system startup, when the specified template was last transmitted.";
                    }

                    ///nokia-state/state/cflowd/collector/template-statistics/sent-packets
                    leaf sent-packets {
                        type uint64;
                        units "packets";
                        description "The number of packets transmitted for the specified template.";
                    }

                    ///nokia-state/state/cflowd/collector/template-statistics/open-packets
                    leaf open-packets {
                        type uint64;
                        units "packets";
                        description "The number of open packets pending for the specified template.";
                    }

                    ///nokia-state/state/cflowd/collector/template-statistics/errored-packets
                    leaf errored-packets {
                        type uint64;
                        units "packets";
                        description "The number of errored packets for the specified template";
                    }

                } // list template-statistics

            } // list collector

        } // container cflowd

    } // grouping state-cflowd

}
