submodule nokia-state-submgt-service-chaining {

    yang-version "1.1";

    belongs-to nokia-state { prefix "state"; }

    import ietf-yang-types                { prefix "yang"; }
    import nokia-sros-yang-extensions     { prefix "sros-ext"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for service chaining on SR OS based routers.

         Copyright 2016 Nokia. All rights reserved. Reproduction of this document
         is authorized on the condition that the foregoing copyright notice is included.

         This nokia-state-submgt-service-chaining YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-21";

    grouping state-submgt-service-chaining-isa-service-chaining {
        container isa-service-chaining {
            description "Enter the isa-service-chaining context";

            list evpn {
                key "id";
                description "Enter the evpn list instance";

                leaf id {
                    type types-services:service-name;
                    description "EVPN service ID";
                }

                list ip-mapping {
                    key "ip-address";
                    description "Enter the ip-mapping list instance";

                    leaf ip-address {
                        type types-sros:ip-address;
                        description "IP address of the IP mapping";
                    }

                    leaf oper-state {
                        type types-sros:oper-state;
                        description "Operational state of the IP mapping";
                    }

                    leaf mac-address {
                        type yang:mac-address;
                        description "MAC address of the IP mapping";
                    }

                    leaf vni {
                        type uint32;
                        description "VXLAN Network Identifier of the IP mapping";
                    }

                    leaf vtep {
                        type types-sros:ip-address;
                        description "VXLAN Tunnel Endpoint of the IP mapping";
                    }

                } // list ip-mapping

                list esi-mapping {
                    key "esi";
                    description "Enter the esi-mapping list instance";

                    leaf esi {
                        type types-services:ethernet-segment-id;
                        description "Ethernet Segment Identifier of the ESI mapping";
                    }

                    leaf oper-state {
                        type types-sros:oper-state;
                        description "Operational state of the ESI mapping";
                    }

                    leaf vni {
                        type uint32;
                        description "VXLAN Network Identifier of the ESI mapping";
                    }

                    leaf vtep {
                        type types-sros:ip-address;
                        description "VXLAN Tunnel Endpoint of the ESI mapping";
                    }

                } // list esi-mapping

            } // list evpn

        } // container isa-service-chaining

    } // grouping state-submgt-service-chaining-isa-service-chaining

}
