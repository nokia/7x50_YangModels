submodule nokia-state-eth-cfm {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-lldp               { prefix "types-lldp"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for eth-cfm on SR OS based routers.

         Copyright 2016 Nokia. All rights reserved. Reproduction of this document
         is authorized on the condition that the foregoing copyright notice is included.

         This nokia-state-eth-cfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-29";

    grouping state-eth-cfm {
        ///nokia-state/state/eth-cfm
        container eth-cfm {
            description "Enable the eth-cfm context";

            ///nokia-state/state/eth-cfm/system-state
            container system-state {
                description "Enter the system-state context";

                ///nokia-state/state/eth-cfm/system-state/ccm-grace-period
                leaf ccm-grace-period {
                    type enumeration {
                        enum active                         { value 1; }
                        enum inactive                       { value 2; }
                    }
                    description "Indicates whether or not the node is actively executing a grace period.";
                }

            } // container system-state

            ///nokia-state/state/eth-cfm/default-domain
            container default-domain {
                description "Enable the default-domain context";

                ///nokia-state/state/eth-cfm/default-domain/system-settings
                container system-settings {
                    description "Enter the system-settings context";

                    ///nokia-state/state/eth-cfm/default-domain/system-settings/level
                    leaf level {
                        type types-eth-cfm:mp-level;
                        description "The level for the bridge and VLAN of the default domain";
                    }

                    ///nokia-state/state/eth-cfm/default-domain/system-settings/mhf-creation
                    leaf mhf-creation {
                        type types-eth-cfm:mhf-creation-type;
                        description
                            "A value indicating if the Management entity can create MHFs
                             (MIP Half Function) for the default domain.";
                    }

                    ///nokia-state/state/eth-cfm/default-domain/system-settings/id-permission
                    leaf id-permission {
                        type types-eth-cfm:permission-type;
                        description "Sender ID TLV permissions for the default domain.";
                    }

                    ///nokia-state/state/eth-cfm/default-domain/system-settings/mip-ltr-priority
                    leaf mip-ltr-priority {
                        type types-eth-cfm:frame-priority;
                        description
                            "Default priority value to be used for link-trace responses
                             by MIPs in the default domain.";
                    }

                } // container system-settings

            } // container default-domain

            ///nokia-state/state/eth-cfm/domain
            list domain {
                key "md-admin-name";
                description "Enter the domain list instance";

                ///nokia-state/state/eth-cfm/domain/md-admin-name
                leaf md-admin-name {
                    type types-eth-cfm:admin-name;
                    description "Unique domain name";
                }

                ///nokia-state/state/eth-cfm/domain/domain-index
                leaf domain-index {
                    type uint32 {
                        range "1..4294967295";
                    }
                    description "The index of this domain entry.";
                }

                ///nokia-state/state/eth-cfm/domain/creation-origin
                leaf creation-origin {
                    type types-sros:creation-origin;
                    description "The mechanism which created this eth-cfm domain entry.";
                }

                ///nokia-state/state/eth-cfm/domain/next-ma-index
                leaf next-ma-index {
                    type uint32 {
                        range "0..max";
                    }
                    description "The next available association index, or a zero to indicate that none exist.";
                }

                ///nokia-state/state/eth-cfm/domain/association
                list association {
                    key "ma-admin-name";
                    description "Enter the association list instance";

                    ///nokia-state/state/eth-cfm/domain/association/ma-admin-name
                    leaf ma-admin-name {
                        type types-eth-cfm:admin-name;
                        description "Domain association name";
                    }

                    ///nokia-state/state/eth-cfm/domain/association/association-index
                    leaf association-index {
                        type uint32 {
                            range "1..4294967295";
                        }
                        description "The index of this assosiation entry.";
                    }

                    ///nokia-state/state/eth-cfm/domain/association/statistics
                    container statistics {
                        description "Enter the statistics context";

                        ///nokia-state/state/eth-cfm/domain/association/statistics/total-mep-count
                        leaf total-mep-count {
                            type yang:counter32;
                            description
                                "The number of unique MEPs configured (both local and remote)
                                 that are associated with this MA.";
                        }

                    } // container statistics

                    ///nokia-state/state/eth-cfm/domain/association/mep
                    list mep {
                        key "mep-id";
                        description "Enter the mep list instance";

                        ///nokia-state/state/eth-cfm/domain/association/mep/mep-id
                        leaf mep-id {
                            type types-eth-cfm:mep-id-type;
                            description
                                "A local maintenance association end point identifier unique
                                 over a given maintanance association.";
                        }

                        ///nokia-state/state/eth-cfm/domain/association/mep/loopback-results
                        container loopback-results {
                            description "Enter the loopback-results context";

                            ///nokia-state/state/eth-cfm/domain/association/mep/loopback-results/unicast-latest-run
                            container unicast-latest-run {
                                description "Enter the unicast-latest-run context";

                                ///nokia-state/state/eth-cfm/domain/association/mep/loopback-results/unicast-latest-run/test-status
                                leaf test-status {
                                    type enumeration {
                                        enum completed                      { value 1; }
                                        enum terminated-incomplete          { value 2; }
                                        enum in-progress                    { value 3; }
                                    }
                                    description
                                        "The status of the last test that was requested.
                                         If the test-status is failed-to-start the statistics from a prior latest-run
                                         are deleted";
                                }

                                ///nokia-state/state/eth-cfm/domain/association/mep/loopback-results/unicast-latest-run/start-time
                                leaf start-time {
                                    type yang:date-and-time;
                                    description "UTC date and time when the test started.";
                                }

                                ///nokia-state/state/eth-cfm/domain/association/mep/loopback-results/unicast-latest-run/end-time
                                leaf end-time {
                                    type yang:date-and-time;
                                    description "UTC date and time when a test ended.";
                                }

                                ///nokia-state/state/eth-cfm/domain/association/mep/loopback-results/unicast-latest-run/remote-mep-id
                                leaf remote-mep-id {
                                    type uint32;
                                    description "Indicates the remote mepid used for the last test.";
                                }

                                ///nokia-state/state/eth-cfm/domain/association/mep/loopback-results/unicast-latest-run/destination-mac-address
                                leaf destination-mac-address {
                                    type yang:mac-address;
                                    description "Indicates the destination mac address used for the last test.";
                                }

                                ///nokia-state/state/eth-cfm/domain/association/mep/loopback-results/unicast-latest-run/statistics
                                container statistics {
                                    description "Enter the statistics context";

                                    ///nokia-state/state/eth-cfm/domain/association/mep/loopback-results/unicast-latest-run/statistics/sent-packets
                                    leaf sent-packets {
                                        type uint32;
                                        description "Indicates the number of packets sent during the last test.";
                                    }

                                    ///nokia-state/state/eth-cfm/domain/association/mep/loopback-results/unicast-latest-run/statistics/received-in-order
                                    leaf received-in-order {
                                        type yang:counter32;
                                        description "Total number of valid, in-order Loopback Replies received.";
                                    }

                                    ///nokia-state/state/eth-cfm/domain/association/mep/loopback-results/unicast-latest-run/statistics/received-out-of-order
                                    leaf received-out-of-order {
                                        type yang:counter32;
                                        description "The total number of valid, out-of-order Loopback Replies received.";
                                    }

                                    ///nokia-state/state/eth-cfm/domain/association/mep/loopback-results/unicast-latest-run/statistics/received-bad-msdu
                                    leaf received-bad-msdu {
                                        type yang:counter32;
                                        description
                                            "The total number of LBRs received whose
                                             mac_service_data_unit did not match (except for the OpCode)
                                             that of the corresponding LBM (20.2.3).";
                                    }

                                    ///nokia-state/state/eth-cfm/domain/association/mep/loopback-results/unicast-latest-run/statistics/packet-loss
                                    leaf packet-loss {
                                        type decimal64 {
                                            range "0.00..100.00";
                                            fraction-digits 2;
                                        }
                                        units "percent";
                                        description "Percentage of packet loss during testing.";
                                    }

                                } // container statistics

                            } // container unicast-latest-run

                            ///nokia-state/state/eth-cfm/domain/association/mep/loopback-results/multicast-latest-run
                            container multicast-latest-run {
                                description "Enter the multicast-latest-run context";

                                ///nokia-state/state/eth-cfm/domain/association/mep/loopback-results/multicast-latest-run/test-status
                                leaf test-status {
                                    type enumeration {
                                        enum completed                      { value 1; }
                                        enum terminated-incomplete          { value 2; }
                                        enum in-progress                    { value 3; }
                                    }
                                    description
                                        "The status of the last test that was requested.
                                         If the test-status is failed-to-start the statistics from a prior latest-run
                                         are deleted";
                                }

                                ///nokia-state/state/eth-cfm/domain/association/mep/loopback-results/multicast-latest-run/start-time
                                leaf start-time {
                                    type yang:date-and-time;
                                    description "UTC date and time when the test started.";
                                }

                                ///nokia-state/state/eth-cfm/domain/association/mep/loopback-results/multicast-latest-run/end-time
                                leaf end-time {
                                    type yang:date-and-time;
                                    description "UTC date and time when a test ended.";
                                }

                                ///nokia-state/state/eth-cfm/domain/association/mep/loopback-results/multicast-latest-run/statistics
                                container statistics {
                                    description "Enter the statistics context";

                                    ///nokia-state/state/eth-cfm/domain/association/mep/loopback-results/multicast-latest-run/statistics/sent-packets
                                    leaf sent-packets {
                                        type uint32;
                                        description "Indicates the number of packets sent during the last multicast test.";
                                    }

                                    ///nokia-state/state/eth-cfm/domain/association/mep/loopback-results/multicast-latest-run/statistics/received-packets
                                    leaf received-packets {
                                        type yang:counter32;
                                        description "Total number of valid multicast Loopback Replies received.";
                                    }

                                } // container statistics

                                ///nokia-state/state/eth-cfm/domain/association/mep/loopback-results/multicast-latest-run/remote-mep-mac
                                list remote-mep-mac {
                                    key "remote-mac-address";
                                    description "Enter the remote-mep-mac list instance";

                                    ///nokia-state/state/eth-cfm/domain/association/mep/loopback-results/multicast-latest-run/remote-mep-mac/remote-mac-address
                                    leaf remote-mac-address {
                                        type yang:mac-address;
                                        description "Specifies the MAC address of the remote MEP responding to the multicast loopback message.";
                                    }

                                    ///nokia-state/state/eth-cfm/domain/association/mep/loopback-results/multicast-latest-run/remote-mep-mac/sequence-number
                                    list sequence-number {
                                        key "id received-index";
                                        description "Enter the sequence-number list instance";

                                        ///nokia-state/state/eth-cfm/domain/association/mep/loopback-results/multicast-latest-run/remote-mep-mac/sequence-number/id
                                        leaf id {
                                            type uint32;
                                            description "Specifies the sequence number contained within the reply message.";
                                        }

                                        ///nokia-state/state/eth-cfm/domain/association/mep/loopback-results/multicast-latest-run/remote-mep-mac/sequence-number/received-index
                                        leaf received-index {
                                            type uint32;
                                            description
                                                "Indicates the order in which the reply was received for the corresponding
                                                 remote MAC address. It is locally assigned and can be used to detect out
                                                 of order responses.";
                                        }

                                    } // list sequence-number

                                } // list remote-mep-mac

                            } // container multicast-latest-run

                        } // container loopback-results

                        ///nokia-state/state/eth-cfm/domain/association/mep/linktrace-results
                        container linktrace-results {
                            description "Enter the linktrace-results context";

                            ///nokia-state/state/eth-cfm/domain/association/mep/linktrace-results/latest-run
                            container latest-run {
                                description "Enter the latest-run context";

                                ///nokia-state/state/eth-cfm/domain/association/mep/linktrace-results/latest-run/test-status
                                leaf test-status {
                                    type enumeration {
                                        enum completed                      { value 1; }
                                        enum terminated-incomplete          { value 2; }
                                        enum in-progress                    { value 3; }
                                    }
                                    description
                                        "The status of the last test that was requested.
                                         If the test-status is failed-to-start the statistics from a prior latest-run
                                         are deleted";
                                }

                                ///nokia-state/state/eth-cfm/domain/association/mep/linktrace-results/latest-run/start-time
                                leaf start-time {
                                    type yang:date-and-time;
                                    description "UTC date and time when the test started.";
                                }

                                ///nokia-state/state/eth-cfm/domain/association/mep/linktrace-results/latest-run/end-time
                                leaf end-time {
                                    type yang:date-and-time;
                                    description "UTC date and time when a test ended.";
                                }

                                ///nokia-state/state/eth-cfm/domain/association/mep/linktrace-results/latest-run/remote-mep-id
                                leaf remote-mep-id {
                                    type uint32;
                                    description "Indicates the remote mepid used for the last test.";
                                }

                                ///nokia-state/state/eth-cfm/domain/association/mep/linktrace-results/latest-run/destination-mac-address
                                leaf destination-mac-address {
                                    type yang:mac-address;
                                    description "Indicates the destination mac address used for the last test.";
                                }

                                ///nokia-state/state/eth-cfm/domain/association/mep/linktrace-results/latest-run/sequence-number
                                list sequence-number {
                                    key "id receive-order";
                                    description "Enter the sequence-number list instance";

                                    ///nokia-state/state/eth-cfm/domain/association/mep/linktrace-results/latest-run/sequence-number/id
                                    leaf id {
                                        type uint32 {
                                            range "0..4294967295";
                                        }
                                        description
                                            "Transaction identifier/Sequence number returned by a previous
                                             transmit linktrace message command, indicating which LTM's
                                             response is going to be returned.";
                                    }

                                    ///nokia-state/state/eth-cfm/domain/association/mep/linktrace-results/latest-run/sequence-number/receive-order
                                    leaf receive-order {
                                        type uint32 {
                                            range "1..4294967295";
                                        }
                                        description
                                            "An index to distinguish among multiple LTRs with the same LTR
                                             Transaction Identifier field value.  dot1agCfmLtrReceiveOrder
                                             are assigned sequentially from 1, in the order that the
                                             Linktrace Initiator received the LTRs.";
                                    }

                                    ///nokia-state/state/eth-cfm/domain/association/mep/linktrace-results/latest-run/sequence-number/ingress-mac
                                    leaf ingress-mac {
                                        type yang:mac-address;
                                        description
                                            "MAC address returned in the ingress MAC address field.
                                             If the ingress-action leaf contains the value
                                             ing-no-tlv(0), then the contents of this leaf are meaningless.";
                                    }

                                    ///nokia-state/state/eth-cfm/domain/association/mep/linktrace-results/latest-run/sequence-number/egress-mac
                                    leaf egress-mac {
                                        type yang:mac-address;
                                        description
                                            "MAC address returned in the egress MAC address field.
                                             If the egress-action leaf contains the value
                                             egr-no-tlv(0), then the contents of this leaf are meaningless.";
                                    }

                                    ///nokia-state/state/eth-cfm/domain/association/mep/linktrace-results/latest-run/sequence-number/relay
                                    leaf relay {
                                        type enumeration {
                                            enum rly-hit                        { value 1; }
                                            enum rly-fdb                        { value 2; }
                                            enum rly-mpdb                       { value 3; }
                                        }
                                        description "Value returned in the Relay Action field.";
                                    }

                                    ///nokia-state/state/eth-cfm/domain/association/mep/linktrace-results/latest-run/sequence-number/action
                                    leaf action {
                                        type enumeration {
                                            enum terminate                      { value 1; }
                                            enum forward                        { value 2; }
                                            enum none                           { value 3; }
                                        }
                                        description
                                            "Value indicating how the forwarded LTM was processed by the
                                             responding MP.";
                                    }

                                    ///nokia-state/state/eth-cfm/domain/association/mep/linktrace-results/latest-run/sequence-number/chassis-id-subtype
                                    leaf chassis-id-subtype {
                                        type union {
                                            type uint32 {
                                                range "8..255";
                                            }
                                            type types-lldp:chassis-id-subtype;
                                        }
                                        description
                                            "This object specifies the format of the Chassis ID returned
                                             in the Sender ID TLV of the LTR, if any. This value is
                                             meaningless if the chassis-id has a length of 0.";
                                    }

                                    ///nokia-state/state/eth-cfm/domain/association/mep/linktrace-results/latest-run/sequence-number/chassis-id
                                    leaf chassis-id {
                                        type string;
                                        description
                                            "The Chassis ID returned in the Sender ID TLV of the LTR, if
                                             any. The format of this object is determined by the
                                             value of the chassis-id-subtype object.";
                                    }

                                    ///nokia-state/state/eth-cfm/domain/association/mep/linktrace-results/latest-run/sequence-number/management-address-domain
                                    leaf management-address-domain {
                                        type string;
                                        description
                                            "The domain that identifies the type and format of
                                             the related management-address leaf, used to access
                                             the system transmitting the LTR. The value is received
                                             in the LTR Sender ID TLV from that system.

                                             Typical values will be one of (not all inclusive) list:

                                             snmpUDPDomain          (from SNMPv2-TM, RFC3417)
                                             snmpIeee802Domain      (from SNMP-IEEE802-TM-MIB, RFC4789)

                                             The value 'zeroDotZero' (from RFC2578) indicates 'no management
                                             address was present in the LTR', in which case the related
                                             management-address leaf must not contain a value.";
                                    }

                                    ///nokia-state/state/eth-cfm/domain/association/mep/linktrace-results/latest-run/sequence-number/management-address
                                    leaf management-address {
                                        type string;
                                        description
                                            "The TAddress that can be used to access the SNMP
                                             agent of the system transmitting the CCM, received in the CCM
                                             Sender ID TLV from that system.

                                             If the related management-address-domain leaf contains
                                             the value 'zeroDotZero', this object must have a
                                             zero-length OCTET STRING as a value.";
                                    }

                                } // list sequence-number

                            } // container latest-run

                        } // container linktrace-results

                    } // list mep

                } // list association

            } // list domain

            ///nokia-state/state/eth-cfm/resource-limits
            container resource-limits {
                description "Enter the resource-limits context";

                ///nokia-state/state/eth-cfm/resource-limits/domain
                container domain {
                    description "Enter the domain context";

                    ///nokia-state/state/eth-cfm/resource-limits/domain/current-usage
                    leaf current-usage {
                        type yang:counter32;
                        description "Indicates the current resource usage of the ETH-CFM component.";
                    }

                    ///nokia-state/state/eth-cfm/resource-limits/domain/system-limit
                    leaf system-limit {
                        type yang:counter32;
                        description "Indicates the maximum resource usage limit of the ETH-CFM component.";
                    }

                } // container domain

                ///nokia-state/state/eth-cfm/resource-limits/association
                container association {
                    description "Enter the association context";

                    ///nokia-state/state/eth-cfm/resource-limits/association/current-usage
                    leaf current-usage {
                        type yang:counter32;
                        description "Indicates the current resource usage of the ETH-CFM component.";
                    }

                    ///nokia-state/state/eth-cfm/resource-limits/association/system-limit
                    leaf system-limit {
                        type yang:counter32;
                        description "Indicates the maximum resource usage limit of the ETH-CFM component.";
                    }

                    ///nokia-state/state/eth-cfm/resource-limits/association/extended-association
                    container extended-association {
                        description "Enter the extended-association context";

                        ///nokia-state/state/eth-cfm/resource-limits/association/extended-association/current-usage
                        leaf current-usage {
                            type yang:counter32;
                            description "Indicates the current resource usage of the ETH-CFM component.";
                        }

                        ///nokia-state/state/eth-cfm/resource-limits/association/extended-association/system-limit
                        leaf system-limit {
                            type yang:counter32;
                            description "Indicates the maximum resource usage limit of the ETH-CFM component.";
                        }

                    } // container extended-association

                } // container association

                ///nokia-state/state/eth-cfm/resource-limits/mep
                container mep {
                    description "Enter the mep context";

                    ///nokia-state/state/eth-cfm/resource-limits/mep/current-usage
                    leaf current-usage {
                        type yang:counter32;
                        description "Indicates the current resource usage of the ETH-CFM component.";
                    }

                    ///nokia-state/state/eth-cfm/resource-limits/mep/system-limit
                    leaf system-limit {
                        type yang:counter32;
                        description "Indicates the maximum resource usage limit of the ETH-CFM component.";
                    }

                    ///nokia-state/state/eth-cfm/resource-limits/mep/one-second
                    container one-second {
                        description "Enter the one-second context";

                        ///nokia-state/state/eth-cfm/resource-limits/mep/one-second/current-usage
                        leaf current-usage {
                            type yang:counter32;
                            description "Indicates the current resource usage of the ETH-CFM component.";
                        }

                        ///nokia-state/state/eth-cfm/resource-limits/mep/one-second/system-limit
                        leaf system-limit {
                            type yang:counter32;
                            description "Indicates the maximum resource usage limit of the ETH-CFM component.";
                        }

                    } // container one-second

                    ///nokia-state/state/eth-cfm/resource-limits/mep/sub-second
                    container sub-second {
                        description "Enter the sub-second context";

                        ///nokia-state/state/eth-cfm/resource-limits/mep/sub-second/current-usage
                        leaf current-usage {
                            type yang:counter32;
                            description "Indicates the current resource usage of the ETH-CFM component.";
                        }

                        ///nokia-state/state/eth-cfm/resource-limits/mep/sub-second/system-limit
                        leaf system-limit {
                            type yang:counter32;
                            description "Indicates the maximum resource usage limit of the ETH-CFM component.";
                        }

                    } // container sub-second

                    ///nokia-state/state/eth-cfm/resource-limits/mep/remote-mep
                    container remote-mep {
                        description "Enter the remote-mep context";

                        ///nokia-state/state/eth-cfm/resource-limits/mep/remote-mep/current-usage
                        leaf current-usage {
                            type yang:counter32;
                            description "Indicates the current resource usage of the ETH-CFM component.";
                        }

                        ///nokia-state/state/eth-cfm/resource-limits/mep/remote-mep/system-limit
                        leaf system-limit {
                            type yang:counter32;
                            description "Indicates the maximum resource usage limit of the ETH-CFM component.";
                        }

                    } // container remote-mep

                } // container mep

                ///nokia-state/state/eth-cfm/resource-limits/primary-vlan-management-point
                container primary-vlan-management-point {
                    description "Enter the primary-vlan-management-point context";

                    ///nokia-state/state/eth-cfm/resource-limits/primary-vlan-management-point/ingress
                    container ingress {
                        description "Enter the ingress context";

                        ///nokia-state/state/eth-cfm/resource-limits/primary-vlan-management-point/ingress/current-usage
                        leaf current-usage {
                            type yang:counter32;
                            description "Indicates the current resource usage of the ETH-CFM component.";
                        }

                        ///nokia-state/state/eth-cfm/resource-limits/primary-vlan-management-point/ingress/system-limit
                        leaf system-limit {
                            type yang:counter32;
                            description "Indicates the maximum resource usage limit of the ETH-CFM component.";
                        }

                    } // container ingress

                    ///nokia-state/state/eth-cfm/resource-limits/primary-vlan-management-point/egress
                    container egress {
                        description "Enter the egress context";

                        ///nokia-state/state/eth-cfm/resource-limits/primary-vlan-management-point/egress/current-usage
                        leaf current-usage {
                            type yang:counter32;
                            description "Indicates the current resource usage of the ETH-CFM component.";
                        }

                        ///nokia-state/state/eth-cfm/resource-limits/primary-vlan-management-point/egress/system-limit
                        leaf system-limit {
                            type yang:counter32;
                            description "Indicates the maximum resource usage limit of the ETH-CFM component.";
                        }

                    } // container egress

                } // container primary-vlan-management-point

                ///nokia-state/state/eth-cfm/resource-limits/ais
                container ais {
                    description "Enter the ais context";

                    ///nokia-state/state/eth-cfm/resource-limits/ais/current-usage
                    leaf current-usage {
                        type yang:counter32;
                        description "Indicates the current resource usage of the ETH-CFM component.";
                    }

                    ///nokia-state/state/eth-cfm/resource-limits/ais/system-limit
                    leaf system-limit {
                        type yang:counter32;
                        description "Indicates the maximum resource usage limit of the ETH-CFM component.";
                    }

                } // container ais

                ///nokia-state/state/eth-cfm/resource-limits/csf
                container csf {
                    description "Enter the csf context";

                    ///nokia-state/state/eth-cfm/resource-limits/csf/current-usage
                    leaf current-usage {
                        type yang:counter32;
                        description "Indicates the current resource usage of the ETH-CFM component.";
                    }

                    ///nokia-state/state/eth-cfm/resource-limits/csf/system-limit
                    leaf system-limit {
                        type yang:counter32;
                        description "Indicates the maximum resource usage limit of the ETH-CFM component.";
                    }

                } // container csf

                ///nokia-state/state/eth-cfm/resource-limits/lmm-statistics-collectors
                container lmm-statistics-collectors {
                    description "Enter the lmm-statistics-collectors context";

                    ///nokia-state/state/eth-cfm/resource-limits/lmm-statistics-collectors/current-usage
                    leaf current-usage {
                        type yang:counter32;
                        description "Indicates the current resource usage of the ETH-CFM component.";
                    }

                    ///nokia-state/state/eth-cfm/resource-limits/lmm-statistics-collectors/system-limit
                    leaf system-limit {
                        type yang:counter32;
                        description "Indicates the maximum resource usage limit of the ETH-CFM component.";
                    }

                } // container lmm-statistics-collectors

                ///nokia-state/state/eth-cfm/resource-limits/lbm-concurrent-test
                container lbm-concurrent-test {
                    description "Enter the lbm-concurrent-test context";

                    ///nokia-state/state/eth-cfm/resource-limits/lbm-concurrent-test/current-usage
                    leaf current-usage {
                        type yang:counter32;
                        description "Indicates the current resource usage of the ETH-CFM component.";
                    }

                    ///nokia-state/state/eth-cfm/resource-limits/lbm-concurrent-test/system-limit
                    leaf system-limit {
                        type yang:counter32;
                        description "Indicates the maximum resource usage limit of the ETH-CFM component.";
                    }

                    ///nokia-state/state/eth-cfm/resource-limits/lbm-concurrent-test/multicast-concurrent-test
                    container multicast-concurrent-test {
                        description "Enter the multicast-concurrent-test context";

                        ///nokia-state/state/eth-cfm/resource-limits/lbm-concurrent-test/multicast-concurrent-test/current-usage
                        leaf current-usage {
                            type yang:counter32;
                            description "Indicates the current resource usage of the ETH-CFM component.";
                        }

                        ///nokia-state/state/eth-cfm/resource-limits/lbm-concurrent-test/multicast-concurrent-test/system-limit
                        leaf system-limit {
                            type yang:counter32;
                            description "Indicates the maximum resource usage limit of the ETH-CFM component.";
                        }

                    } // container multicast-concurrent-test

                } // container lbm-concurrent-test

                ///nokia-state/state/eth-cfm/resource-limits/ltm-concurrent-test
                container ltm-concurrent-test {
                    description "Enter the ltm-concurrent-test context";

                    ///nokia-state/state/eth-cfm/resource-limits/ltm-concurrent-test/current-usage
                    leaf current-usage {
                        type yang:counter32;
                        description "Indicates the current resource usage of the ETH-CFM component.";
                    }

                    ///nokia-state/state/eth-cfm/resource-limits/ltm-concurrent-test/system-limit
                    leaf system-limit {
                        type yang:counter32;
                        description "Indicates the maximum resource usage limit of the ETH-CFM component.";
                    }

                } // container ltm-concurrent-test

                ///nokia-state/state/eth-cfm/resource-limits/mip
                container mip {
                    description "Enter the mip context";

                    ///nokia-state/state/eth-cfm/resource-limits/mip/current-usage
                    leaf current-usage {
                        type yang:counter32;
                        description "Indicates the current resource usage of the ETH-CFM component.";
                    }

                    ///nokia-state/state/eth-cfm/resource-limits/mip/system-limit
                    leaf system-limit {
                        type yang:counter32;
                        description "Indicates the maximum resource usage limit of the ETH-CFM component.";
                    }

                } // container mip

            } // container resource-limits

            ///nokia-state/state/eth-cfm/learned-remote-mac
            list learned-remote-mac {
                key "md-admin-name ma-admin-name local-mep-id remote-mep-id";
                description "Enter the learned-remote-mac list instance";

                ///nokia-state/state/eth-cfm/learned-remote-mac/md-admin-name
                leaf md-admin-name {
                    type leafref {
                        path "../../domain/md-admin-name";
                    }
                    description "A unique administratively assigned name used to identify a domain.";
                }

                ///nokia-state/state/eth-cfm/learned-remote-mac/ma-admin-name
                leaf ma-admin-name {
                    type leafref {
                        path "../../domain/association/ma-admin-name";
                    }
                    description "A unique administratively assigned name used to identify an association.";
                }

                ///nokia-state/state/eth-cfm/learned-remote-mac/local-mep-id
                leaf local-mep-id {
                    type types-eth-cfm:mep-id-type;
                    description
                        "Specifies a local Maintenance Association (MA) End Point identifier unique
                         over a given maintanance association.";
                }

                ///nokia-state/state/eth-cfm/learned-remote-mac/remote-mep-id
                leaf remote-mep-id {
                    type types-eth-cfm:mep-id-type;
                    description
                        "Specifies a remote Maintenance Association (MA) End Point identifier unique
                         over a given maintanance association.";
                }

                ///nokia-state/state/eth-cfm/learned-remote-mac/remote-mac-address
                leaf remote-mac-address {
                    type yang:mac-address;
                    description
                        "The the source MAC address used by the remote MEP in the most recently
                         received CCM PDU.";
                }

                ///nokia-state/state/eth-cfm/learned-remote-mac/stale-flag
                leaf stale-flag {
                    type boolean;
                    description
                        "Flag that indicates if the learned MAC entry for this remote MEP
                         matches the entry found in the list on the local MEP.

                         The value 'false' indicates that the MAC address matches the entry
                         found in both the lists for the same local and remote MEP values and
                         therefore is not considered stale.

                         The value 'true' indicates either the entries do not match, or there
                         is no equivalent entry for the remote MEP in the list on the local
                         MEP, so the learned remote MAC address in this table is considered stale.";
                }

                ///nokia-state/state/eth-cfm/learned-remote-mac/changed-flag
                leaf changed-flag {
                    type boolean;
                    description
                        "Indicates if the learned MAC entry for this remote MEP has been
                         modified in the last CCM interval of the local MEP.

                         The value 'true' indicates that the local MEP received a CCM from the
                         remote MEP with a MAC address that does not match the address in
                         learned-remote-mac from the last CCM interval of the local MEP. The
                         new address will be stored in learned-remote-mac.

                         The value 'false' indicates a new entry or an entry where
                         learned-remote-mac has not changed in over one CCM
                         interval.

                         This object can be used to detect if a remote MEP MAC address has
                         recently changed. This may help detect configuration changes of
                         remote MEP MAC addresses, or possibly duplicate remote MEPs configured
                         in the network.";
                }

            } // list learned-remote-mac

            ///nokia-state/state/eth-cfm/statistics
            container statistics {
                description "Enter the statistics context";

                ///nokia-state/state/eth-cfm/statistics/receive-count
                leaf receive-count {
                    type yang:counter32;
                    description "Indicates the number of received ETH-CFM packets on the node.";
                }

                ///nokia-state/state/eth-cfm/statistics/transmit-count
                leaf transmit-count {
                    type yang:counter32;
                    description "Indicates the number of transmitted ETH-CFM packets on the node.";
                }

                ///nokia-state/state/eth-cfm/statistics/congestion-drops
                leaf congestion-drops {
                    type yang:counter32;
                    description
                        "Indicates the number of dropped ETH-CFM packets on the node. A packet is
                         dropped because of resource contention.";
                }

                ///nokia-state/state/eth-cfm/statistics/error-discards
                leaf error-discards {
                    type yang:counter32;
                    description
                        "Indicates the number of discarded ETH-CFM packets on the node. A packet
                         may be discarded for several reasons including, but not limited to,
                         malformed PDU, invalid TLVs, MEP admin down, etc.";
                }

                ///nokia-state/state/eth-cfm/statistics/ais-transmit-active
                leaf ais-transmit-active {
                    type yang:counter32;
                    description
                        "Indicates the number of sessions where fault (AIS or other) is
                         actively being transmitted.";
                }

                ///nokia-state/state/eth-cfm/statistics/ais-transmit-fail
                leaf ais-transmit-fail {
                    type yang:counter32;
                    description
                        "Indicates the number of sessions where fault (AIS or other) can't
                         be transmitted due to lack of resources.";
                }

                ///nokia-state/state/eth-cfm/statistics/opcode
                list opcode {
                    key "opcode-name";
                    description "Enter the opcode list instance";

                    ///nokia-state/state/eth-cfm/statistics/opcode/opcode-name
                    leaf opcode-name {
                        type types-eth-cfm:statistics-opcode-name;
                        description "Integer that defines which CFM PDU Opcode the statictics refer to.";
                    }

                    ///nokia-state/state/eth-cfm/statistics/opcode/transmitted
                    leaf transmitted {
                        type yang:counter32;
                        description "The total number of PDUs transmitted from the node with the specified Opcode.";
                    }

                    ///nokia-state/state/eth-cfm/statistics/opcode/received
                    leaf received {
                        type yang:counter32;
                        description "The total number of PDUs received on the node with the specified Opcode.";
                    }

                } // list opcode

            } // container statistics

            ///nokia-state/state/eth-cfm/cfm-stack-table
            container cfm-stack-table {
                description "Enter the cfm-stack-table context";

                ///nokia-state/state/eth-cfm/cfm-stack-table/sap
                container sap {
                    description "Enter the sap context";

                    ///nokia-state/state/eth-cfm/cfm-stack-table/sap/sap
                    list sap {
                        key "sap-id level direction";
                        description "Enter the sap list instance";

                        ///nokia-state/state/eth-cfm/cfm-stack-table/sap/sap/sap-id
                        leaf sap-id {
                            type types-sros:sap;
                            description "SAP identifier.";
                        }

                        ///nokia-state/state/eth-cfm/cfm-stack-table/sap/sap/level
                        leaf level {
                            type types-eth-cfm:mp-level;
                            description "The level for the bridge and VLAN of the default domain.";
                        }

                        ///nokia-state/state/eth-cfm/cfm-stack-table/sap/sap/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/sap/sap/md-admin-name
                        leaf md-admin-name {
                            type types-eth-cfm:admin-name;
                            description "A unique administratively assigned name used to identify a domain.";
                        }

                        ///nokia-state/state/eth-cfm/cfm-stack-table/sap/sap/ma-admin-name
                        leaf ma-admin-name {
                            type types-eth-cfm:admin-name;
                            description "A unique administratively assigned name used to identify an association.";
                        }

                        ///nokia-state/state/eth-cfm/cfm-stack-table/sap/sap/mep-id
                        leaf mep-id {
                            type types-eth-cfm:mep-id-type;
                            description
                                "Indicates a local Maintenance association End Point identifier unique
                                 over a given maintanance association.";
                        }

                        ///nokia-state/state/eth-cfm/cfm-stack-table/sap/sap/is-mip
                        leaf is-mip {
                            type boolean;
                            description "Indicates if the Maintenance Point is a MIP.";
                        }

                        ///nokia-state/state/eth-cfm/cfm-stack-table/sap/sap/mac-address
                        leaf mac-address {
                            type yang:mac-address;
                            description "MAC address of the Maintenance Endpoint.";
                        }

                        ///nokia-state/state/eth-cfm/cfm-stack-table/sap/sap/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list sap

                } // container sap

                ///nokia-state/state/eth-cfm/cfm-stack-table/eth-ring
                container eth-ring {
                    description "Enter the eth-ring context";

                    ///nokia-state/state/eth-cfm/cfm-stack-table/eth-ring/port-and-raps-tag
                    list port-and-raps-tag {
                        key "port-and-raps-tag-id level direction";
                        description "Enter the port-and-raps-tag list instance";

                        ///nokia-state/state/eth-cfm/cfm-stack-table/eth-ring/port-and-raps-tag/port-and-raps-tag-id
                        leaf port-and-raps-tag-id {
                            type types-sros:port-and-encap;
                            description "Port-id and raps-tag associated with the eth-ring path.";
                        }

                        ///nokia-state/state/eth-cfm/cfm-stack-table/eth-ring/port-and-raps-tag/level
                        leaf level {
                            type types-eth-cfm:mp-level;
                            description "The level for the bridge and VLAN of the default domain.";
                        }

                        ///nokia-state/state/eth-cfm/cfm-stack-table/eth-ring/port-and-raps-tag/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/eth-ring/port-and-raps-tag/md-admin-name
                        leaf md-admin-name {
                            type types-eth-cfm:admin-name;
                            description "A unique administratively assigned name used to identify a domain.";
                        }

                        ///nokia-state/state/eth-cfm/cfm-stack-table/eth-ring/port-and-raps-tag/ma-admin-name
                        leaf ma-admin-name {
                            type types-eth-cfm:admin-name;
                            description "A unique administratively assigned name used to identify an association.";
                        }

                        ///nokia-state/state/eth-cfm/cfm-stack-table/eth-ring/port-and-raps-tag/mep-id
                        leaf mep-id {
                            type types-eth-cfm:mep-id-type;
                            description
                                "Indicates a local Maintenance association End Point identifier unique
                                 over a given maintanance association.";
                        }

                        ///nokia-state/state/eth-cfm/cfm-stack-table/eth-ring/port-and-raps-tag/is-mip
                        leaf is-mip {
                            type boolean;
                            description "Indicates if the Maintenance Point is a MIP.";
                        }

                        ///nokia-state/state/eth-cfm/cfm-stack-table/eth-ring/port-and-raps-tag/mac-address
                        leaf mac-address {
                            type yang:mac-address;
                            description "MAC address of the Maintenance Endpoint.";
                        }

                        ///nokia-state/state/eth-cfm/cfm-stack-table/eth-ring/port-and-raps-tag/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list port-and-raps-tag

                } // container eth-ring

                ///nokia-state/state/eth-cfm/cfm-stack-table/facility
                container facility {
                    description "Enter the facility context";

                    ///nokia-state/state/eth-cfm/cfm-stack-table/facility/port
                    list port {
                        key "port-id vlan level direction";
                        description "Enter the port list instance";

                        ///nokia-state/state/eth-cfm/cfm-stack-table/facility/port/port-id
                        leaf port-id {
                            type types-sros:port;
                            description "Port identifier.";
                        }

                        ///nokia-state/state/eth-cfm/cfm-stack-table/facility/port/vlan
                        leaf vlan {
                            type types-eth-cfm:vlan-id-or-none;
                            description "The VLAN ID that uniquely identifies a specific VLAN.";
                        }

                        ///nokia-state/state/eth-cfm/cfm-stack-table/facility/port/level
                        leaf level {
                            type types-eth-cfm:mp-level;
                            description "The level for the bridge and VLAN of the default domain.";
                        }

                        ///nokia-state/state/eth-cfm/cfm-stack-table/facility/port/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/facility/port/md-admin-name
                        leaf md-admin-name {
                            type types-eth-cfm:admin-name;
                            description "A unique administratively assigned name used to identify a domain.";
                        }

                        ///nokia-state/state/eth-cfm/cfm-stack-table/facility/port/ma-admin-name
                        leaf ma-admin-name {
                            type types-eth-cfm:admin-name;
                            description "A unique administratively assigned name used to identify an association.";
                        }

                        ///nokia-state/state/eth-cfm/cfm-stack-table/facility/port/mep-id
                        leaf mep-id {
                            type types-eth-cfm:mep-id-type;
                            description
                                "Indicates a local Maintenance association End Point identifier unique
                                 over a given maintanance association.";
                        }

                        ///nokia-state/state/eth-cfm/cfm-stack-table/facility/port/is-mip
                        leaf is-mip {
                            type boolean;
                            description "Indicates if the Maintenance Point is a MIP.";
                        }

                        ///nokia-state/state/eth-cfm/cfm-stack-table/facility/port/mac-address
                        leaf mac-address {
                            type yang:mac-address;
                            description "MAC address of the Maintenance Endpoint.";
                        }

                        ///nokia-state/state/eth-cfm/cfm-stack-table/facility/port/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list port

                    ///nokia-state/state/eth-cfm/cfm-stack-table/facility/interface
                    list interface {
                        key "interface-name level direction";
                        description "Enter the interface list instance";

                        ///nokia-state/state/eth-cfm/cfm-stack-table/facility/interface/interface-name
                        leaf interface-name {
                            type types-sros:interface-name;
                            description "Router interface name.";
                        }

                        ///nokia-state/state/eth-cfm/cfm-stack-table/facility/interface/level
                        leaf level {
                            type types-eth-cfm:mp-level;
                            description "The level for the bridge and VLAN of the default domain.";
                        }

                        ///nokia-state/state/eth-cfm/cfm-stack-table/facility/interface/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/facility/interface/md-admin-name
                        leaf md-admin-name {
                            type types-eth-cfm:admin-name;
                            description "A unique administratively assigned name used to identify a domain.";
                        }

                        ///nokia-state/state/eth-cfm/cfm-stack-table/facility/interface/ma-admin-name
                        leaf ma-admin-name {
                            type types-eth-cfm:admin-name;
                            description "A unique administratively assigned name used to identify an association.";
                        }

                        ///nokia-state/state/eth-cfm/cfm-stack-table/facility/interface/mep-id
                        leaf mep-id {
                            type types-eth-cfm:mep-id-type;
                            description
                                "Indicates a local Maintenance association End Point identifier unique
                                 over a given maintanance association.";
                        }

                        ///nokia-state/state/eth-cfm/cfm-stack-table/facility/interface/is-mip
                        leaf is-mip {
                            type boolean;
                            description "Indicates if the Maintenance Point is a MIP.";
                        }

                        ///nokia-state/state/eth-cfm/cfm-stack-table/facility/interface/mac-address
                        leaf mac-address {
                            type yang:mac-address;
                            description "MAC address of the Maintenance Endpoint.";
                        }

                        ///nokia-state/state/eth-cfm/cfm-stack-table/facility/interface/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list interface

                } // container facility

                ///nokia-state/state/eth-cfm/cfm-stack-table/sdp
                container sdp {
                    description "Enter the sdp context";

                    ///nokia-state/state/eth-cfm/cfm-stack-table/sdp/sdp-bind
                    list sdp-bind {
                        key "sdp-bind-id level direction";
                        description "Enter the sdp-bind list instance";

                        ///nokia-state/state/eth-cfm/cfm-stack-table/sdp/sdp-bind/sdp-bind-id
                        leaf sdp-bind-id {
                            type types-services:sdp-bind-id;
                            description
                                "SDP Binding identifier as <sdp-id>:<vc-id>.
                                 sdp-id - [1..32767]
                                 vc-id - [1..4294967295].";
                        }

                        ///nokia-state/state/eth-cfm/cfm-stack-table/sdp/sdp-bind/level
                        leaf level {
                            type types-eth-cfm:mp-level;
                            description "The level for the bridge and VLAN of the default domain.";
                        }

                        ///nokia-state/state/eth-cfm/cfm-stack-table/sdp/sdp-bind/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/sdp/sdp-bind/md-admin-name
                        leaf md-admin-name {
                            type types-eth-cfm:admin-name;
                            description "A unique administratively assigned name used to identify a domain.";
                        }

                        ///nokia-state/state/eth-cfm/cfm-stack-table/sdp/sdp-bind/ma-admin-name
                        leaf ma-admin-name {
                            type types-eth-cfm:admin-name;
                            description "A unique administratively assigned name used to identify an association.";
                        }

                        ///nokia-state/state/eth-cfm/cfm-stack-table/sdp/sdp-bind/mep-id
                        leaf mep-id {
                            type types-eth-cfm:mep-id-type;
                            description
                                "Indicates a local Maintenance association End Point identifier unique
                                 over a given maintanance association.";
                        }

                        ///nokia-state/state/eth-cfm/cfm-stack-table/sdp/sdp-bind/is-mip
                        leaf is-mip {
                            type boolean;
                            description "Indicates if the Maintenance Point is a MIP.";
                        }

                        ///nokia-state/state/eth-cfm/cfm-stack-table/sdp/sdp-bind/mac-address
                        leaf mac-address {
                            type yang:mac-address;
                            description "MAC address of the Maintenance Endpoint.";
                        }

                        ///nokia-state/state/eth-cfm/cfm-stack-table/sdp/sdp-bind/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list sdp-bind

                } // container sdp

                ///nokia-state/state/eth-cfm/cfm-stack-table/virtual
                container virtual {
                    description "Enter the virtual context";

                    ///nokia-state/state/eth-cfm/cfm-stack-table/virtual/service
                    list service {
                        key "service-name level direction";
                        description "Enter the service list instance";

                        ///nokia-state/state/eth-cfm/cfm-stack-table/virtual/service/service-name
                        leaf service-name {
                            type types-services:service-name;
                            description "Name of service.";
                        }

                        ///nokia-state/state/eth-cfm/cfm-stack-table/virtual/service/level
                        leaf level {
                            type types-eth-cfm:mp-level;
                            description "The level for the bridge and VLAN of the default domain.";
                        }

                        ///nokia-state/state/eth-cfm/cfm-stack-table/virtual/service/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/virtual/service/md-admin-name
                        leaf md-admin-name {
                            type types-eth-cfm:admin-name;
                            description "A unique administratively assigned name used to identify a domain.";
                        }

                        ///nokia-state/state/eth-cfm/cfm-stack-table/virtual/service/ma-admin-name
                        leaf ma-admin-name {
                            type types-eth-cfm:admin-name;
                            description "A unique administratively assigned name used to identify an association.";
                        }

                        ///nokia-state/state/eth-cfm/cfm-stack-table/virtual/service/mep-id
                        leaf mep-id {
                            type types-eth-cfm:mep-id-type;
                            description
                                "Indicates a local Maintenance association End Point identifier unique
                                 over a given maintanance association.";
                        }

                        ///nokia-state/state/eth-cfm/cfm-stack-table/virtual/service/is-mip
                        leaf is-mip {
                            type boolean;
                            description "Indicates if the Maintenance Point is a MIP.";
                        }

                        ///nokia-state/state/eth-cfm/cfm-stack-table/virtual/service/mac-address
                        leaf mac-address {
                            type yang:mac-address;
                            description "MAC address of the Maintenance Endpoint.";
                        }

                        ///nokia-state/state/eth-cfm/cfm-stack-table/virtual/service/mep-defect-flags
                        leaf mep-defect-flags {
                            type bits {
                                bit rdi-ccm                        { position 0; }
                                bit mac-status                     { position 1; }
                                bit remote-ccm                     { position 2; }
                                bit error-ccm                      { position 3; }
                                bit xconnect-ccm                   { position 4; }
                                bit ais-rx                         { position 5; }
                                bit csf-ais-rx                     { position 6; }
                                bit csf-rdi-rx                     { position 7; }
                                bit csf-los-rx                     { position 8; }
                                bit grace-rx                       { position 9; }
                            }
                            description "Indicates the defects of the MEP.";
                        }

                    } // list service

                } // container virtual

                ///nokia-state/state/eth-cfm/cfm-stack-table/sap-primary-vlan
                container sap-primary-vlan {
                    description "Enter the sap-primary-vlan context";

                    ///nokia-state/state/eth-cfm/cfm-stack-table/sap-primary-vlan/sap
                    list sap {
                        key "sap-id primary-vlan level direction";
                        description "Enter the sap list instance";

                        ///nokia-state/state/eth-cfm/cfm-stack-table/sap-primary-vlan/sap/sap-id
                        leaf sap-id {
                            type types-sros:sap;
                            description "SAP identifier.";
                        }

                        ///nokia-state/state/eth-cfm/cfm-stack-table/sap-primary-vlan/sap/primary-vlan
                        leaf primary-vlan {
                            type uint32;
                            description "Primary Vlan ID.";
                        }

                        ///nokia-state/state/eth-cfm/cfm-stack-table/sap-primary-vlan/sap/level
                        leaf level {
                            type types-eth-cfm:mp-level;
                            description "The level for the bridge and VLAN of the default domain.";
                        }

                        ///nokia-state/state/eth-cfm/cfm-stack-table/sap-primary-vlan/sap/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/sap-primary-vlan/sap/md-admin-name
                        leaf md-admin-name {
                            type types-eth-cfm:admin-name;
                            description "A unique administratively assigned name used to identify a domain.";
                        }

                        ///nokia-state/state/eth-cfm/cfm-stack-table/sap-primary-vlan/sap/ma-admin-name
                        leaf ma-admin-name {
                            type types-eth-cfm:admin-name;
                            description "A unique administratively assigned name used to identify an association.";
                        }

                        ///nokia-state/state/eth-cfm/cfm-stack-table/sap-primary-vlan/sap/mep-id
                        leaf mep-id {
                            type types-eth-cfm:mep-id-type;
                            description
                                "Indicates a local Maintenance association End Point identifier unique
                                 over a given maintanance association.";
                        }

                        ///nokia-state/state/eth-cfm/cfm-stack-table/sap-primary-vlan/sap/is-mip
                        leaf is-mip {
                            type boolean;
                            description "Indicates if the Maintenance Point is a MIP.";
                        }

                        ///nokia-state/state/eth-cfm/cfm-stack-table/sap-primary-vlan/sap/mac-address
                        leaf mac-address {
                            type yang:mac-address;
                            description "MAC address of the Maintenance Endpoint.";
                        }

                    } // list sap

                } // container sap-primary-vlan

                ///nokia-state/state/eth-cfm/cfm-stack-table/sdp-primary-vlan
                container sdp-primary-vlan {
                    description "Enter the sdp-primary-vlan context";

                    ///nokia-state/state/eth-cfm/cfm-stack-table/sdp-primary-vlan/sdp-bind
                    list sdp-bind {
                        key "sdp-bind-id primary-vlan level direction";
                        description "Enter the sdp-bind list instance";

                        ///nokia-state/state/eth-cfm/cfm-stack-table/sdp-primary-vlan/sdp-bind/sdp-bind-id
                        leaf sdp-bind-id {
                            type types-services:sdp-bind-id;
                            description
                                "SDP Binding identifier as <sdp-id>:<vc-id>.
                                 sdp-id - [1..32767]
                                 vc-id - [1..4294967295].";
                        }

                        ///nokia-state/state/eth-cfm/cfm-stack-table/sdp-primary-vlan/sdp-bind/primary-vlan
                        leaf primary-vlan {
                            type uint32;
                            description "Primary Vlan ID.";
                        }

                        ///nokia-state/state/eth-cfm/cfm-stack-table/sdp-primary-vlan/sdp-bind/level
                        leaf level {
                            type types-eth-cfm:mp-level;
                            description "The level for the bridge and VLAN of the default domain.";
                        }

                        ///nokia-state/state/eth-cfm/cfm-stack-table/sdp-primary-vlan/sdp-bind/direction
                        leaf direction {
                            type types-eth-cfm:mp-direction;
                            description
                                "The direction the MEP/MIP faces on the Bridge port.

                                 If 'down' the Management Point (MP) sends CFM PDUs away from the
                                 MAC Relay Entity. If 'up' the MP sends CFM PDUs towards the MAC Relay Entity.";
                        }

                        ///nokia-state/state/eth-cfm/cfm-stack-table/sdp-primary-vlan/sdp-bind/md-admin-name
                        leaf md-admin-name {
                            type types-eth-cfm:admin-name;
                            description "A unique administratively assigned name used to identify a domain.";
                        }

                        ///nokia-state/state/eth-cfm/cfm-stack-table/sdp-primary-vlan/sdp-bind/ma-admin-name
                        leaf ma-admin-name {
                            type types-eth-cfm:admin-name;
                            description "A unique administratively assigned name used to identify an association.";
                        }

                        ///nokia-state/state/eth-cfm/cfm-stack-table/sdp-primary-vlan/sdp-bind/mep-id
                        leaf mep-id {
                            type types-eth-cfm:mep-id-type;
                            description
                                "Indicates a local Maintenance association End Point identifier unique
                                 over a given maintanance association.";
                        }

                        ///nokia-state/state/eth-cfm/cfm-stack-table/sdp-primary-vlan/sdp-bind/is-mip
                        leaf is-mip {
                            type boolean;
                            description "Indicates if the Maintenance Point is a MIP.";
                        }

                        ///nokia-state/state/eth-cfm/cfm-stack-table/sdp-primary-vlan/sdp-bind/mac-address
                        leaf mac-address {
                            type yang:mac-address;
                            description "MAC address of the Maintenance Endpoint.";
                        }

                    } // list sdp-bind

                } // container sdp-primary-vlan

            } // container cfm-stack-table

        } // container eth-cfm

    } // grouping state-eth-cfm

}
