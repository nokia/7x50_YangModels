submodule nokia-conf-submgt-local-user-db {

    yang-version "1.1";

    belongs-to nokia-conf { prefix "conf"; }

    import nokia-sros-yang-extensions     { prefix "sros-ext"; }
    import nokia-types-services           { prefix "types-services"; }
    import nokia-types-sros               { prefix "types-sros"; }
    import nokia-types-subscriber-mgmt    { prefix "types-submgt"; }

    include nokia-conf-groups;

    sros-ext:sros-major-release "rel23";
    organization "Nokia";
    contact
        "Nokia SR OS Support
         Web: <http://www.nokia.com>";
    description
        "Nokia YANG Data model to configure subscriber management local user database on SR OS based routers.

         Copyright 2016 Nokia. All rights reserved. Reproduction of this document
         is authorized on the condition that the foregoing copyright notice is included.

         This nokia-conf-submgt-local-user-db YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-01-30";

    grouping conf-submgt-local-user-db {
        ///nokia-conf/configure/subscriber-mgmt/local-user-db
        list local-user-db {
            key "name";
            max-elements 127;
            description "Enter the local-user-db list instance";

            ///nokia-conf/configure/subscriber-mgmt/local-user-db/name
            leaf name {
                type types-sros:named-item;
                description "Local user database name";
            }

            ///nokia-conf/configure/subscriber-mgmt/local-user-db/admin-state
            leaf admin-state {
                type types-sros:admin-state;
                default "disable";
                description "Administrative state of the local user database";
            }

            ///nokia-conf/configure/subscriber-mgmt/local-user-db/description
            leaf description {
                type types-sros:description;
                description "Text description";
            }

            ///nokia-conf/configure/subscriber-mgmt/local-user-db/apply-groups
            leaf-list apply-groups {
                type leafref {
                    path "../../../groups/group/name";
                }
                max-elements 8;
                ordered-by user;
                description "Apply a configuration group at this level";
            }

            ///nokia-conf/configure/subscriber-mgmt/local-user-db/apply-groups-exclude
            leaf-list apply-groups-exclude {
                type leafref {
                    path "../../../groups/group/name";
                }
                max-elements 8;
                ordered-by user;
                description "Exclude a configuration group at this level";
            }

            ///nokia-conf/configure/subscriber-mgmt/local-user-db/ipoe
            container ipoe {
                description "Enter the ipoe context";

                ///nokia-conf/configure/subscriber-mgmt/local-user-db/ipoe/match-list
                leaf-list match-list {
                    type enumeration {
                        enum circuit-id                     { value 1; }
                        enum mac                            { value 2; }
                        enum remote-id                      { value 3; }
                        enum sap-id                         { value 4; }
                        enum service-id                     { value 5; }
                        enum string                         { value 6; }
                        enum system-id                      { value 7; }
                        enum option60                       { value 8; }
                        enum encap-tag-range                { value 9; }
                        enum dual-stack-remote-id           { value 10; }
                        enum derived-id                     { value 11; }
                        enum ip                             { value 12; }
                        enum encap-tag-separate-range       { value 13; }
                    }
                    max-elements 4;
                    ordered-by user;
                    sros-ext:auto-restart-to-modify;
                    description "IPoE host match type";
                }

                ///nokia-conf/configure/subscriber-mgmt/local-user-db/ipoe/mask
                list mask {
                    key "type";
                    description "Enter the mask list instance";

                    ///nokia-conf/configure/subscriber-mgmt/local-user-db/ipoe/mask/type
                    leaf type {
                        type enumeration {
                            enum circuit-id                     { value 1; }
                            enum remote-id                      { value 3; }
                            enum sap-id                         { value 4; }
                            enum string                         { value 6; }
                            enum system-id                      { value 7; }
                            enum option60                       { value 8; }
                        }
                        description "Matching type to identify a host";
                    }

                    ///nokia-conf/configure/subscriber-mgmt/local-user-db/ipoe/mask/apply-groups
                    leaf-list apply-groups {
                        type leafref {
                            path "../../../../../groups/group/name";
                        }
                        max-elements 8;
                        ordered-by user;
                        description "Apply a configuration group at this level";
                    }

                    ///nokia-conf/configure/subscriber-mgmt/local-user-db/ipoe/mask/apply-groups-exclude
                    leaf-list apply-groups-exclude {
                        type leafref {
                            path "../../../../../groups/group/name";
                        }
                        max-elements 8;
                        ordered-by user;
                        description "Exclude a configuration group at this level";
                    }

                    ///nokia-conf/configure/subscriber-mgmt/local-user-db/ipoe/mask/prefix
                    container prefix {
                        presence "Enable the prefix context";
                        description "Enable the prefix context";

                        ///nokia-conf/configure/subscriber-mgmt/local-user-db/ipoe/mask/prefix/prefix
                        choice prefix {
                            mandatory true;
                            ///nokia-conf/configure/subscriber-mgmt/local-user-db/ipoe/mask/prefix/prefix/length
                            case length {

                                ///nokia-conf/configure/subscriber-mgmt/local-user-db/ipoe/mask/prefix/prefix/length/length
                                leaf length {
                                    type uint32 {
                                        range "1..127";
                                    }
                                    description "PPP mask prefix length";
                                }

                            }
                            ///nokia-conf/configure/subscriber-mgmt/local-user-db/ipoe/mask/prefix/prefix/string
                            case string {

                                ///nokia-conf/configure/subscriber-mgmt/local-user-db/ipoe/mask/prefix/prefix/string/string
                                leaf string {
                                    type string {
                                        length "1..127";
                                    }
                                    description "Prefix string";
                                }

                            }
                        }
                    } // container prefix

                    ///nokia-conf/configure/subscriber-mgmt/local-user-db/ipoe/mask/suffix
                    container suffix {
                        presence "Enable the suffix context";
                        description "Enable the suffix context";

                        ///nokia-conf/configure/subscriber-mgmt/local-user-db/ipoe/mask/suffix/suffix
                        choice suffix {
                            mandatory true;
                            ///nokia-conf/configure/subscriber-mgmt/local-user-db/ipoe/mask/suffix/suffix/length
                            case length {

                                ///nokia-conf/configure/subscriber-mgmt/local-user-db/ipoe/mask/suffix/suffix/length/length
                                leaf length {
                                    type uint32 {
                                        range "1..127";
                                    }
                                    description "PPP mask suffix length";
                                }

                            }
                            ///nokia-conf/configure/subscriber-mgmt/local-user-db/ipoe/mask/suffix/suffix/string
                            case string {

                                ///nokia-conf/configure/subscriber-mgmt/local-user-db/ipoe/mask/suffix/suffix/string/string
                                leaf string {
                                    type string {
                                        length "1..127";
                                        pattern "[^*].*";
                                    }
                                    description "Suffix string";
                                }

                            }
                        }
                    } // container suffix

                } // list mask

                ///nokia-conf/configure/subscriber-mgmt/local-user-db/ipoe/host
                list host {
                    key "host-name";
                    description "Enter the host list instance";

                    ///nokia-conf/configure/subscriber-mgmt/local-user-db/ipoe/host/host-name
                    leaf host-name {
                        type types-sros:named-item;
                        description "Host name";
                    }

                    ///nokia-conf/configure/subscriber-mgmt/local-user-db/ipoe/host/admin-state
                    leaf admin-state {
                        type types-sros:admin-state;
                        default "disable";
                        description "Administrative state of the host";
                    }

                    ///nokia-conf/configure/subscriber-mgmt/local-user-db/ipoe/host/retail-service-id
                    leaf retail-service-id {
                        type types-services:service-id-maf;
                        description "Configure the retail service-id";
                    }

                    ///nokia-conf/configure/subscriber-mgmt/local-user-db/ipoe/host/rip-policy
                    leaf rip-policy {
                        type types-sros:named-item;
                        description "RIP policy";
                    }

                    ///nokia-conf/configure/subscriber-mgmt/local-user-db/ipoe/host/apply-groups
                    leaf-list apply-groups {
                        type leafref {
                            path "../../../../../groups/group/name";
                        }
                        max-elements 8;
                        ordered-by user;
                        description "Apply a configuration group at this level";
                    }

                    ///nokia-conf/configure/subscriber-mgmt/local-user-db/ipoe/host/apply-groups-exclude
                    leaf-list apply-groups-exclude {
                        type leafref {
                            path "../../../../../groups/group/name";
                        }
                        max-elements 8;
                        ordered-by user;
                        description "Exclude a configuration group at this level";
                    }

                    ///nokia-conf/configure/subscriber-mgmt/local-user-db/ipoe/host/host-identification
                    container host-identification {
                        description "Enter the host-identification context";

                        ///nokia-conf/configure/subscriber-mgmt/local-user-db/ipoe/host/host-identification/derived-id
                        leaf derived-id {
                            type types-sros:display-string;
                            sros-ext:auto-restart-to-modify;
                            description "Derived ID string";
                        }

                        ///nokia-conf/configure/subscriber-mgmt/local-user-db/ipoe/host/host-identification/mac
                        leaf mac {
                            type types-sros:mac-unicast-address-no-zero;
                            sros-ext:auto-restart-to-modify;
                            description "MAC address";
                        }

                        ///nokia-conf/configure/subscriber-mgmt/local-user-db/ipoe/host/host-identification/sap-id
                        leaf sap-id {
                            type types-sros:display-string;
                            sros-ext:auto-restart-to-modify;
                            description "SAP ID";
                        }

                        ///nokia-conf/configure/subscriber-mgmt/local-user-db/ipoe/host/host-identification/ip-prefix
                        leaf ip-prefix {
                            type types-sros:ip-prefix-with-host-bits;
                            sros-ext:auto-restart-to-modify;
                            description "IP interface name";
                        }

                        ///nokia-conf/configure/subscriber-mgmt/local-user-db/ipoe/host/host-identification/string
                        leaf string {
                            type types-sros:display-string;
                            sros-ext:auto-restart-to-modify;
                            description "VSO string";
                        }

                        ///nokia-conf/configure/subscriber-mgmt/local-user-db/ipoe/host/host-identification/service-id
                        leaf service-id {
                            type types-services:service-id-maf;
                            sros-ext:auto-restart-to-modify;
                            description "Service ID";
                        }

                        ///nokia-conf/configure/subscriber-mgmt/local-user-db/ipoe/host/host-identification/system-id
                        leaf system-id {
                            type types-sros:display-string;
                            sros-ext:auto-restart-to-modify;
                            description "System ID";
                        }

                        ///nokia-conf/configure/subscriber-mgmt/local-user-db/ipoe/host/host-identification/circuit-id
                        container circuit-id {
                            description "Enter the circuit-id context";

                            ///nokia-conf/configure/subscriber-mgmt/local-user-db/ipoe/host/host-identification/circuit-id/format
                            choice format {
                                ///nokia-conf/configure/subscriber-mgmt/local-user-db/ipoe/host/host-identification/circuit-id/format/ascii-string
                                case ascii-string {

                                    ///nokia-conf/configure/subscriber-mgmt/local-user-db/ipoe/host/host-identification/circuit-id/format/ascii-string/ascii-string
                                    leaf ascii-string {
                                        type string {
                                            length "1..127";
                                        }
                                        sros-ext:auto-restart-to-modify;
                                        description "Circuit ID as ASCII string";
                                    }

                                }
                                ///nokia-conf/configure/subscriber-mgmt/local-user-db/ipoe/host/host-identification/circuit-id/format/hex-string
                                case hex-string {

                                    ///nokia-conf/configure/subscriber-mgmt/local-user-db/ipoe/host/host-identification/circuit-id/format/hex-string/hex-string
                                    leaf hex-string {
                                        type types-sros:hex-string {
                                            length "1..256";
                                        }
                                        sros-ext:auto-restart-to-modify;
                                        description "Circuit ID as hexadecimal string";
                                    }

                                }
                            }
                        } // container circuit-id

                        ///nokia-conf/configure/subscriber-mgmt/local-user-db/ipoe/host/host-identification/remote-id
                        container remote-id {
                            description "Enter the remote-id context";

                            ///nokia-conf/configure/subscriber-mgmt/local-user-db/ipoe/host/host-identification/remote-id/format
                            choice format {
                                ///nokia-conf/configure/subscriber-mgmt/local-user-db/ipoe/host/host-identification/remote-id/format/ascii-string
                                case ascii-string {

                                    ///nokia-conf/configure/subscriber-mgmt/local-user-db/ipoe/host/host-identification/remote-id/format/ascii-string/ascii-string
                                    leaf ascii-string {
                                        type string {
                                            length "1..255";
                                        }
                                        sros-ext:auto-restart-to-modify;
                                        description "Remote ID as ASCII string";
                                    }

                                }
                                ///nokia-conf/configure/subscriber-mgmt/local-user-db/ipoe/host/host-identification/remote-id/format/hex-string
                                case hex-string {

                                    ///nokia-conf/configure/subscriber-mgmt/local-user-db/ipoe/host/host-identification/remote-id/format/hex-string/hex-string
                                    leaf hex-string {
                                        type types-sros:hex-string {
                                            length "1..512";
                                        }
                                        sros-ext:auto-restart-to-modify;
                                        description "Remote ID as hexadecimal string";
                                    }

                                }
                            }
                        } // container remote-id

                        ///nokia-conf/configure/subscriber-mgmt/local-user-db/ipoe/host/host-identification/option60
                        container option60 {
                            description "Enter the option60 context";

                            ///nokia-conf/configure/subscriber-mgmt/local-user-db/ipoe/host/host-identification/option60/format
                            choice format {
                                ///nokia-conf/configure/subscriber-mgmt/local-user-db/ipoe/host/host-identification/option60/format/ascii-string
                                case ascii-string {

                                    ///nokia-conf/configure/subscriber-mgmt/local-user-db/ipoe/host/host-identification/option60/format/ascii-string/ascii-string
                                    leaf ascii-string {
                                        type types-sros:named-item;
                                        sros-ext:auto-restart-to-modify;
                                        description "Option 60 as ASCII string";
                                    }

                                }
                                ///nokia-conf/configure/subscriber-mgmt/local-user-db/ipoe/host/host-identification/option60/format/hex-string
                                case hex-string {

                                    ///nokia-conf/configure/subscriber-mgmt/local-user-db/ipoe/host/host-identification/option60/format/hex-string/hex-string
                                    leaf hex-string {
                                        type types-sros:hex-string {
                                            length "1..64";
                                        }
                                        sros-ext:auto-restart-to-modify;
                                        description "Option as a hexadecimal string";
                                    }

                                }
                            }
                        } // container option60

                        ///nokia-conf/configure/subscriber-mgmt/local-user-db/ipoe/host/host-identification/encap-tag-range
                        container encap-tag-range {
                            presence "Enable the encap-tag-range context";
                            description "Enable the encap-tag-range context";

                            ///nokia-conf/configure/subscriber-mgmt/local-user-db/ipoe/host/host-identification/encap-tag-range/from
                            leaf from {
                                type types-sros:atm-or-vlan-encap;
                                sros-ext:auto-restart-to-modify;
                                mandatory true;
                                description "Start tag";
                            }

                            ///nokia-conf/configure/subscriber-mgmt/local-user-db/ipoe/host/host-identification/encap-tag-range/to
                            leaf to {
                                type types-sros:atm-or-vlan-encap;
                                sros-ext:auto-restart-to-modify;
                                mandatory true;
                                description "End tag";
                            }

                        } // container encap-tag-range

                        ///nokia-conf/configure/subscriber-mgmt/local-user-db/ipoe/host/host-identification/encap-tag-separate-range
                        container encap-tag-separate-range {
                            description "Enter the encap-tag-separate-range context";

                            ///nokia-conf/configure/subscriber-mgmt/local-user-db/ipoe/host/host-identification/encap-tag-separate-range/outer
                            container outer {
                                description "Enter the outer context";

                                ///nokia-conf/configure/subscriber-mgmt/local-user-db/ipoe/host/host-identification/encap-tag-separate-range/outer/start
                                leaf start {
                                    type int32 {
                                        range "0..4094";
                                    }
                                    sros-ext:auto-restart-to-modify;
                                    description "Lower bound of the outer encapsulation tag range";
                                }

                                ///nokia-conf/configure/subscriber-mgmt/local-user-db/ipoe/host/host-identification/encap-tag-separate-range/outer/end
                                leaf end {
                                    type int32 {
                                        range "0..4094";
                                    }
                                    sros-ext:auto-restart-to-modify;
                                    description "Upper bound of the outer encapsulation tag range";
                                }

                            } // container outer

                            ///nokia-conf/configure/subscriber-mgmt/local-user-db/ipoe/host/host-identification/encap-tag-separate-range/inner
                            container inner {
                                description "Enter the inner context";

                                ///nokia-conf/configure/subscriber-mgmt/local-user-db/ipoe/host/host-identification/encap-tag-separate-range/inner/start
                                leaf start {
                                    type int32 {
                                        range "0..4094";
                                    }
                                    sros-ext:auto-restart-to-modify;
                                    description "Lower bound of the inner encapsulation tag range";
                                }

                                ///nokia-conf/configure/subscriber-mgmt/local-user-db/ipoe/host/host-identification/encap-tag-separate-range/inner/end
                                leaf end {
                                    type int32 {
                                        range "0..4094";
                                    }
                                    sros-ext:auto-restart-to-modify;
                                    description "Upper bound of the inner encapsulation tag range";
                                }

                            } // container inner

                        } // container encap-tag-separate-range

                    } // container host-identification

                    ///nokia-conf/configure/subscriber-mgmt/local-user-db/ipoe/host/authentication
                    container authentication {
                        description "Enter the authentication context";

                        ///nokia-conf/configure/subscriber-mgmt/local-user-db/ipoe/host/authentication/radius-auth-policy
                        leaf radius-auth-policy {
                            type types-sros:named-item;
                            description "Host authentication policy";
                        }

                        ///nokia-conf/configure/subscriber-mgmt/local-user-db/ipoe/host/authentication/gx-policy
                        leaf gx-policy {
                            type types-sros:named-item;
                            description "Diameter application policy";
                        }

                        ///nokia-conf/configure/subscriber-mgmt/local-user-db/ipoe/host/authentication/nasreq-auth-policy
                        leaf nasreq-auth-policy {
                            type types-sros:named-item;
                            description "Diameter NASREQ application policy for authentication";
                        }

                        ///nokia-conf/configure/subscriber-mgmt/local-user-db/ipoe/host/authentication/auth-domain-name
                        leaf auth-domain-name {
                            type types-sros:named-item;
                            description "Domain name appended to the username for the host";
                        }

                    } // container authentication

                    ///nokia-conf/configure/subscriber-mgmt/local-user-db/ipoe/host/radius-accounting-policy
                    container radius-accounting-policy {
                        description "Enter the radius-accounting-policy context";

                        ///nokia-conf/configure/subscriber-mgmt/local-user-db/ipoe/host/radius-accounting-policy/name
                        leaf name {
                            type types-sros:named-item;
                            description "RADIUS accounting policy name";
                        }

                        ///nokia-conf/configure/subscriber-mgmt/local-user-db/ipoe/host/radius-accounting-policy/duplicate
                        leaf duplicate {
                            type types-sros:named-item;
                            description "RADIUS accounting policy for generating duplicate accounting information";
                        }

                    } // container radius-accounting-policy

                    ///nokia-conf/configure/subscriber-mgmt/local-user-db/ipoe/host/gtp-interface
                    container gtp-interface {
                        presence "Enable the gtp-interface context";
                        description "Enable the gtp-interface context";

                        ///nokia-conf/configure/subscriber-mgmt/local-user-db/ipoe/host/gtp-interface/name
                        leaf name {
                            type types-sros:named-item;
                            mandatory true;
                            description "IP interface name";
                        }

                        ///nokia-conf/configure/subscriber-mgmt/local-user-db/ipoe/host/gtp-interface/service-id
                        leaf service-id {
                            type types-services:service-id-maf;
                            mandatory true;
                            description "Service ID";
                        }

                    } // container gtp-interface

                    ///nokia-conf/configure/subscriber-mgmt/local-user-db/ipoe/host/identification
                    container identification {
                        presence "Enable the identification context";
                        description "Enable the identification context";

                        ///nokia-conf/configure/subscriber-mgmt/local-user-db/ipoe/host/identification/option-number
                        leaf option-number {
                            type uint32 {
                                range "1..254";
                            }
                            sros-ext:immutable;
                            default "254";
                            description "Identification strings for the subscriber";
                        }

                        ///nokia-conf/configure/subscriber-mgmt/local-user-db/ipoe/host/identification/ancp-string
                        leaf ancp-string {
                            type string {
                                length "1..63";
                            }
                            description "ANCP string";
                        }

                        ///nokia-conf/configure/subscriber-mgmt/local-user-db/ipoe/host/identification/app-profile-string
                        leaf app-profile-string {
                            type string {
                                length "1..16";
                            }
                            description "Application profile string";
                        }

                        ///nokia-conf/configure/subscriber-mgmt/local-user-db/ipoe/host/identification/category-map-name
                        leaf category-map-name {
                            type types-sros:named-item;
                            description "Category map name";
                        }

                        ///nokia-conf/configure/subscriber-mgmt/local-user-db/ipoe/host/identification/int-dest-id
                        leaf int-dest-id {
                            type types-submgt:int-dest-id;
                            description "Intermediate destination ID";
                        }

                        ///nokia-conf/configure/subscriber-mgmt/local-user-db/ipoe/host/identification/sla-profile-string
                        leaf sla-profile-string {
                            type string {
                                length "1..32";
                            }
                            description "SLA profile string";
                        }

                        ///nokia-conf/configure/subscriber-mgmt/local-user-db/ipoe/host/identification/sub-profile-string
                        leaf sub-profile-string {
                            type string {
                                length "1..32";
                            }
                            description "Sub profile string";
                        }

                        ///nokia-conf/configure/subscriber-mgmt/local-user-db/ipoe/host/identification/subscriber-id
                        leaf subscriber-id {
                            type types-sros:named-item-64;
                            description "Subscriber ID";
                        }

                        ///nokia-conf/configure/subscriber-mgmt/local-user-db/ipoe/host/identification/spi-sharing-group-id
                        leaf spi-sharing-group-id {
                            type int32 {
                                range "0..65535";
                            }
                            description "SPI sharing group ID";
                        }

                    } // container identification

                    ///nokia-conf/configure/subscriber-mgmt/local-user-db/ipoe/host/match-radius-proxy-cache
                    container match-radius-proxy-cache {
                        description "Enter the match-radius-proxy-cache context";

                        ///nokia-conf/configure/subscriber-mgmt/local-user-db/ipoe/host/match-radius-proxy-cache/fail-action
                        leaf fail-action {
                            type enumeration {
                                enum continue                       { value 1; }
                                enum drop                           { value 2; }
                            }
                            default "drop";
                            description "Action when no match is found";
                        }

                        ///nokia-conf/configure/subscriber-mgmt/local-user-db/ipoe/host/match-radius-proxy-cache/mac-format
                        leaf mac-format {
                            type types-submgt:mac-specification;
                            default "aa:";
                            description "MAC address format";
                        }

                        ///nokia-conf/configure/subscriber-mgmt/local-user-db/ipoe/host/match-radius-proxy-cache/match
                        container match {
                            description "Enter the match context";

                            ///nokia-conf/configure/subscriber-mgmt/local-user-db/ipoe/host/match-radius-proxy-cache/match/format
                            choice format {
                                default "mac";
                                ///nokia-conf/configure/subscriber-mgmt/local-user-db/ipoe/host/match-radius-proxy-cache/match/format/mac
                                case mac {

                                    ///nokia-conf/configure/subscriber-mgmt/local-user-db/ipoe/host/match-radius-proxy-cache/match/format/mac/mac
                                    leaf mac {
                                        type boolean;
                                        default "true";
                                        description "Match MAC address of DHCP client";
                                    }

                                }
                                ///nokia-conf/configure/subscriber-mgmt/local-user-db/ipoe/host/match-radius-proxy-cache/match/format/circuit-id
                                case circuit-id {

                                    ///nokia-conf/configure/subscriber-mgmt/local-user-db/ipoe/host/match-radius-proxy-cache/match/format/circuit-id/circuit-id
                                    leaf circuit-id {
                                        type boolean;
                                        description "Match circuit ID in DHCP Option 82";
                                    }

                                }
                                ///nokia-conf/configure/subscriber-mgmt/local-user-db/ipoe/host/match-radius-proxy-cache/match/format/remote-id
                                case remote-id {

                                    ///nokia-conf/configure/subscriber-mgmt/local-user-db/ipoe/host/match-radius-proxy-cache/match/format/remote-id/remote-id
                                    leaf remote-id {
                                        type boolean;
                                        description "Match remote ID in DHCP Option 82";
                                    }

                                }
                                ///nokia-conf/configure/subscriber-mgmt/local-user-db/ipoe/host/match-radius-proxy-cache/match/format/option
                                case option {

                                    ///nokia-conf/configure/subscriber-mgmt/local-user-db/ipoe/host/match-radius-proxy-cache/match/format/option/ipv4-option
                                    leaf ipv4-option {
                                        type uint8 {
                                            range "1..254";
                                        }
                                        description "DHCP option number";
                                    }

                                    ///nokia-conf/configure/subscriber-mgmt/local-user-db/ipoe/host/match-radius-proxy-cache/match/format/option/ipv6-option
                                    leaf ipv6-option {
                                        type uint32 {
                                            range "1..65535";
                                        }
                                        description "DHCPv6 option number";
                                    }

                                }
                            }
                        } // container match

                        ///nokia-conf/configure/subscriber-mgmt/local-user-db/ipoe/host/match-radius-proxy-cache/server
                        container server {
                            presence "Enable the server context";
                            description "Enable the server context";

                            ///nokia-conf/configure/subscriber-mgmt/local-user-db/ipoe/host/match-radius-proxy-cache/server/service
                            leaf service {
                                type types-services:external-service-id;
                                description "Service ID";
                            }

                            ///nokia-conf/configure/subscriber-mgmt/local-user-db/ipoe/host/match-radius-proxy-cache/server/name
                            leaf name {
                                type types-sros:named-item;
                                mandatory true;
                                description "Local user database server name";
                            }

                        } // container server

                    } // container match-radius-proxy-cache

                    ///nokia-conf/configure/subscriber-mgmt/local-user-db/ipoe/host/msap-defaults
                    container msap-defaults {
                        description "Enter the msap-defaults context";

                        ///nokia-conf/configure/subscriber-mgmt/local-user-db/ipoe/host/msap-defaults/policy
                        leaf policy {
                            type types-sros:named-item;
                            description "MSAP policy";
                        }

                        ///nokia-conf/configure/subscriber-mgmt/local-user-db/ipoe/host/msap-defaults/service
                        leaf service {
                            type types-services:service-id-maf;
                            description "Service ID";
                        }

                        ///nokia-conf/configure/subscriber-mgmt/local-user-db/ipoe/host/msap-defaults/group-interface
                        container group-interface {
                            presence "Enable the group-interface context";
                            description "Enable the group-interface context";

                            ///nokia-conf/configure/subscriber-mgmt/local-user-db/ipoe/host/msap-defaults/group-interface/name
                            leaf name {
                                type types-sros:named-item;
                                mandatory true;
                                description "IP interface name";
                            }

                            ///nokia-conf/configure/subscriber-mgmt/local-user-db/ipoe/host/msap-defaults/group-interface/parameters
                            choice parameters {
                                ///nokia-conf/configure/subscriber-mgmt/local-user-db/ipoe/host/msap-defaults/group-interface/parameters/prefix
                                case prefix {

                                    ///nokia-conf/configure/subscriber-mgmt/local-user-db/ipoe/host/msap-defaults/group-interface/parameters/prefix/prefix
                                    leaf prefix {
                                        type enumeration {
                                            enum port-id                        { value 2; }
                                        }
                                        description "Prefix to the IP interface name";
                                    }

                                }
                                ///nokia-conf/configure/subscriber-mgmt/local-user-db/ipoe/host/msap-defaults/group-interface/parameters/suffix
                                case suffix {

                                    ///nokia-conf/configure/subscriber-mgmt/local-user-db/ipoe/host/msap-defaults/group-interface/parameters/suffix/suffix
                                    leaf suffix {
                                        type enumeration {
                                            enum port-id                        { value 2; }
                                        }
                                        description "Suffix for the group interface";
                                    }

                                }
                            }
                        } // container group-interface

                    } // container msap-defaults

                    ///nokia-conf/configure/subscriber-mgmt/local-user-db/ipoe/host/wpp
                    container wpp {
                        description "Enter the wpp context";

                        ///nokia-conf/configure/subscriber-mgmt/local-user-db/ipoe/host/wpp/restore-to-initial-on-disconnect
                        leaf restore-to-initial-on-disconnect {
                            type enumeration {
                                enum restore                        { value 1; }
                                enum no-restore                     { value 2; }
                            }
                            description "Restore initial profiles after a host has disconnected";
                        }

                        ///nokia-conf/configure/subscriber-mgmt/local-user-db/ipoe/host/wpp/portal
                        container portal {
                            description "Enter the portal context";

                            ///nokia-conf/configure/subscriber-mgmt/local-user-db/ipoe/host/wpp/portal/portal
                            choice portal {
                                ///nokia-conf/configure/subscriber-mgmt/local-user-db/ipoe/host/wpp/portal/portal/portal
                                case portal {

                                    ///nokia-conf/configure/subscriber-mgmt/local-user-db/ipoe/host/wpp/portal/portal/portal/router-instance
                                    leaf router-instance {
                                        type union {
                                            type enumeration {
                                                enum base                           { value 0; }
                                            }
                                            type types-services:external-service-id;
                                        }
                                        default "base";
                                        description "Virtual router instance of the WPP portal for the host";
                                    }

                                    ///nokia-conf/configure/subscriber-mgmt/local-user-db/ipoe/host/wpp/portal/portal/portal/name
                                    leaf name {
                                        type types-sros:named-item;
                                        description "Web portal server name";
                                    }

                                }
                                ///nokia-conf/configure/subscriber-mgmt/local-user-db/ipoe/host/wpp/portal/portal/portal-group
                                case portal-group {

                                    ///nokia-conf/configure/subscriber-mgmt/local-user-db/ipoe/host/wpp/portal/portal/portal-group/portal-group
                                    leaf portal-group {
                                        type types-sros:named-item;
                                        description "WPP portal group for this interface";
                                    }

                                }
                            }
                        } // container portal

                        ///nokia-conf/configure/subscriber-mgmt/local-user-db/ipoe/host/wpp/initial
                        container initial {
                            description "Enter the initial context";

                            ///nokia-conf/configure/subscriber-mgmt/local-user-db/ipoe/host/wpp/initial/sub-profile
                            leaf sub-profile {
                                type types-sros:named-item;
                                description "Initial subscriber profile";
                            }

                            ///nokia-conf/configure/subscriber-mgmt/local-user-db/ipoe/host/wpp/initial/sla-profile
                            leaf sla-profile {
                                type types-sros:named-item;
                                description "Initial SLA profile";
                            }

                            ///nokia-conf/configure/subscriber-mgmt/local-user-db/ipoe/host/wpp/initial/app-profile
                            leaf app-profile {
                                type types-sros:named-item;
                                description "Initial application profile name";
                            }

                        } // container initial

                    } // container wpp

                    ///nokia-conf/configure/subscriber-mgmt/local-user-db/ipoe/host/ipv4
                    container ipv4 {
                        description "Enter the ipv4 context";

                        ///nokia-conf/configure/subscriber-mgmt/local-user-db/ipoe/host/ipv4/gi-address
                        leaf gi-address {
                            type types-sros:ipv4-unicast-address;
                            description "GI addresses based on the host entry in the LUDB";
                        }

                        ///nokia-conf/configure/subscriber-mgmt/local-user-db/ipoe/host/ipv4/server
                        leaf server {
                            type types-sros:ipv4-unicast-address;
                            description "IPv4 address of the DHCP server";
                        }

                        ///nokia-conf/configure/subscriber-mgmt/local-user-db/ipoe/host/ipv4/address
                        container address {
                            description "Enter the address context";

                            ///nokia-conf/configure/subscriber-mgmt/local-user-db/ipoe/host/ipv4/address/address
                            choice address {
                                ///nokia-conf/configure/subscriber-mgmt/local-user-db/ipoe/host/ipv4/address/address/ip-address
                                case ip-address {

                                    ///nokia-conf/configure/subscriber-mgmt/local-user-db/ipoe/host/ipv4/address/address/ip-address/ip-address
                                    leaf ip-address {
                                        type types-sros:ipv4-unicast-address;
                                        description "Fixed IPv4 address of the host";
                                    }

                                }
                                ///nokia-conf/configure/subscriber-mgmt/local-user-db/ipoe/host/ipv4/address/address/gi-address
                                case gi-address {

                                    ///nokia-conf/configure/subscriber-mgmt/local-user-db/ipoe/host/ipv4/address/address/gi-address/gi-address
                                    leaf gi-address {
                                        type enumeration {
                                            enum subnet-scope                   { value 0; }
                                            enum pool-scope                     { value 1; }
                                        }
                                        description "Use gi-address to select a pool with the given scope";
                                    }

                                }
                                ///nokia-conf/configure/subscriber-mgmt/local-user-db/ipoe/host/ipv4/address/address/pool
                                case pool {

                                    ///nokia-conf/configure/subscriber-mgmt/local-user-db/ipoe/host/ipv4/address/address/pool/pool
                                    container pool {
                                        presence "Enable the pool context";
                                        description "Enable the pool context";

                                        ///nokia-conf/configure/subscriber-mgmt/local-user-db/ipoe/host/ipv4/address/address/pool/pool/primary
                                        leaf primary {
                                            type types-sros:named-item;
                                            mandatory true;
                                            description "Primary pool name";
                                        }

                                        ///nokia-conf/configure/subscriber-mgmt/local-user-db/ipoe/host/ipv4/address/address/pool/pool/secondary
                                        leaf secondary {
                                            type types-sros:named-item;
                                            description "Secondary pool name";
                                        }

                                        ///nokia-conf/configure/subscriber-mgmt/local-user-db/ipoe/host/ipv4/address/address/pool/pool/delimiter
                                        leaf delimiter {
                                            type string {
                                                length "1";
                                            }
                                            description "Delimiter separating primary and secondary pool names";
                                        }

                                    } // container pool

                                }
                                ///nokia-conf/configure/subscriber-mgmt/local-user-db/ipoe/host/ipv4/address/address/use-pool-from-client
                                case use-pool-from-client {

                                    ///nokia-conf/configure/subscriber-mgmt/local-user-db/ipoe/host/ipv4/address/address/use-pool-from-client/use-pool-from-client
                                    container use-pool-from-client {
                                        presence "Enable the use-pool-from-client context";
                                        description "Enable the use-pool-from-client context";

                                        ///nokia-conf/configure/subscriber-mgmt/local-user-db/ipoe/host/ipv4/address/address/use-pool-from-client/use-pool-from-client/delimiter
                                        leaf delimiter {
                                            type string {
                                                length "1";
                                            }
                                            description "Delimiter character to combine primary and secondary pool names";
                                        }

                                    } // container use-pool-from-client

                                }
                            }
                        } // container address

                        ///nokia-conf/configure/subscriber-mgmt/local-user-db/ipoe/host/ipv4/option
                        list option {
                            key "number";
                            description "Enter the option list instance";

                            ///nokia-conf/configure/subscriber-mgmt/local-user-db/ipoe/host/ipv4/option/number
                            leaf number {
                                type union {
                                    type uint32 {
                                        range "1..254";
                                    }
                                    type enumeration {
                                        enum subnet-mask                    { value 1; }
                                        enum default-router                 { value 3; }
                                        enum dns-server                     { value 6; }
                                        enum domain-name                    { value 15; }
                                        enum netbios-name-server            { value 44; }
                                        enum netbios-node-type              { value 46; }
                                        enum lease-time                     { value 51; }
                                        enum lease-renew-time               { value 58; }
                                        enum lease-rebind-time              { value 59; }
                                    }
                                }
                                description "DHCP option to send identification strings to client";
                            }

                            ///nokia-conf/configure/subscriber-mgmt/local-user-db/ipoe/host/ipv4/option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ipoe/host/ipv4/option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ipoe/host/ipv4/option/value
                            choice value {
                                mandatory true;
                                description "The value of the DHCP option.";
                                ///nokia-conf/configure/subscriber-mgmt/local-user-db/ipoe/host/ipv4/option/value/ascii-string
                                case ascii-string {

                                    ///nokia-conf/configure/subscriber-mgmt/local-user-db/ipoe/host/ipv4/option/value/ascii-string/ascii-string
                                    leaf ascii-string {
                                        when "(not(../number = 46) and not(../number = 'netbios-node-type')) and (not(../number = 51) and not(../number = 'lease-time')) and (not(../number = 58) and not(../number = 'lease-renew-time')) and (not(../number = 59) and not(../number = 'lease-rebind-time'))" {
                                            description "ascii-string is supported only when the option is neither netbios-node-type(46), lease-time(51), lease-renew-time(58) nor lease-rebind-time(59)";
                                        }
                                        type types-sros:string-not-all-spaces {
                                            length "1..127";
                                        }
                                        description "DHCP option specified as an ASCII string";
                                    }

                                }
                                ///nokia-conf/configure/subscriber-mgmt/local-user-db/ipoe/host/ipv4/option/value/hex-string
                                case hex-string {

                                    ///nokia-conf/configure/subscriber-mgmt/local-user-db/ipoe/host/ipv4/option/value/hex-string/hex-string
                                    leaf hex-string {
                                        when "(not(../number = 46) and not(../number = 'netbios-node-type')) and (not(../number = 51) and not(../number = 'lease-time')) and (not(../number = 58) and not(../number = 'lease-renew-time')) and (not(../number = 59) and not(../number = 'lease-rebind-time'))" {
                                            description "hex-string is supported only when the option is neither netbios-node-type(46), lease-time(51), lease-renew-time(58) nor lease-rebind-time(59)";
                                        }
                                        type types-sros:hex-string {
                                            length "1..256";
                                        }
                                        description "DHCP option specified as hexadecimal string";
                                    }

                                }
                                ///nokia-conf/configure/subscriber-mgmt/local-user-db/ipoe/host/ipv4/option/value/netbios-node-type
                                case netbios-node-type {

                                    ///nokia-conf/configure/subscriber-mgmt/local-user-db/ipoe/host/ipv4/option/value/netbios-node-type/netbios-node-type
                                    leaf netbios-node-type {
                                        when "../number = 46 or ../number = 'netbios-node-type'" {
                                            description "netbios-node-type is supported only when the option is netbios-node-type(46)";
                                        }
                                        type enumeration {
                                            enum b-node                         { value 1; }
                                            enum p-node                         { value 2; }
                                            enum m-node                         { value 4; }
                                            enum h-node                         { value 8; }
                                        }
                                        description "DHCP option as NetBIOS node type";
                                    }

                                }
                                ///nokia-conf/configure/subscriber-mgmt/local-user-db/ipoe/host/ipv4/option/value/duration
                                case duration {

                                    ///nokia-conf/configure/subscriber-mgmt/local-user-db/ipoe/host/ipv4/option/value/duration/duration
                                    leaf duration {
                                        when "../number = 51 or ../number = 'lease-time' or ../number = 58 or ../number = 'lease-renew-time' or ../number = 59 or ../number = 'lease-rebind-time'" {
                                            description "duration is supported only when the option is either lease-time(51), lease-renew-time(58) or lease-rebind-time(59)";
                                        }
                                        type types-sros:time-duration {
                                            range "10..315446399";
                                        }
                                        units "seconds";
                                        description "DHCP option as time duration";
                                    }

                                }
                                ///nokia-conf/configure/subscriber-mgmt/local-user-db/ipoe/host/ipv4/option/value/ipv4-address
                                case ipv4-address {

                                    ///nokia-conf/configure/subscriber-mgmt/local-user-db/ipoe/host/ipv4/option/value/ipv4-address/ipv4-address
                                    leaf-list ipv4-address {
                                        when "(not(../number = 46) and not(../number = 'netbios-node-type')) and (not(../number = 51) and not(../number = 'lease-time')) and (not(../number = 58) and not(../number = 'lease-renew-time')) and (not(../number = 59) and not(../number = 'lease-rebind-time'))" {
                                            description "ipv4-address is supported only when the option is neither netbios-node-type(46), lease-time(51), lease-renew-time(58) nor lease-rebind-time(59)";
                                        }
                                        type types-sros:ipv4-address;
                                        max-elements 4;
                                        ordered-by user;
                                        description "DHCP option as a list of IPv4 addresses";
                                    }

                                }
                                ///nokia-conf/configure/subscriber-mgmt/local-user-db/ipoe/host/ipv4/option/value/empty
                                case empty {

                                    ///nokia-conf/configure/subscriber-mgmt/local-user-db/ipoe/host/ipv4/option/value/empty/empty
                                    leaf empty {
                                        when "(not(../number = 46) and not(../number = 'netbios-node-type')) and (not(../number = 51) and not(../number = 'lease-time')) and (not(../number = 58) and not(../number = 'lease-renew-time')) and (not(../number = 59) and not(../number = 'lease-rebind-time'))" {
                                            description "empty is supported only when the option is neither netbios-node-type(46), lease-time(51), lease-renew-time(58) nor lease-rebind-time(59)";
                                        }
                                        type empty;
                                        description "Empty DHCP option.";
                                    }

                                }
                            }
                        } // list option

                    } // container ipv4

                    ///nokia-conf/configure/subscriber-mgmt/local-user-db/ipoe/host/ipv6
                    container ipv6 {
                        description "Enter the ipv6 context";

                        ///nokia-conf/configure/subscriber-mgmt/local-user-db/ipoe/host/ipv6/address
                        leaf address {
                            type types-sros:ipv6-unicast-address;
                            description "Fixed IPv6 address of the host";
                        }

                        ///nokia-conf/configure/subscriber-mgmt/local-user-db/ipoe/host/ipv6/address-pool
                        leaf address-pool {
                            type types-sros:named-item;
                            description "IPv6 address pool name";
                        }

                        ///nokia-conf/configure/subscriber-mgmt/local-user-db/ipoe/host/ipv6/delegated-prefix
                        leaf delegated-prefix {
                            type types-sros:ipv6-unicast-prefix;
                            description "IPv6 delegated prefix of this host";
                        }

                        ///nokia-conf/configure/subscriber-mgmt/local-user-db/ipoe/host/ipv6/delegated-prefix-length
                        leaf delegated-prefix-length {
                            type uint32 {
                                range "48..64";
                            }
                            description "Delegated prefix length";
                        }

                        ///nokia-conf/configure/subscriber-mgmt/local-user-db/ipoe/host/ipv6/delegated-prefix-pool
                        leaf delegated-prefix-pool {
                            type types-sros:named-item;
                            description "Delegated prefix pool";
                        }

                        ///nokia-conf/configure/subscriber-mgmt/local-user-db/ipoe/host/ipv6/slaac-prefix
                        leaf slaac-prefix {
                            type types-sros:ipv6-unicast-prefix;
                            description "IPv6 SLAAC prefix of this host";
                        }

                        ///nokia-conf/configure/subscriber-mgmt/local-user-db/ipoe/host/ipv6/slaac-prefix-pool
                        leaf slaac-prefix-pool {
                            type types-sros:named-item;
                            description "IPv6 SLAAC prefix pool of this host";
                        }

                        ///nokia-conf/configure/subscriber-mgmt/local-user-db/ipoe/host/ipv6/router-advertisement-policy
                        leaf router-advertisement-policy {
                            type types-sros:named-item;
                            description "IPv6 router advertisement policy";
                        }

                        ///nokia-conf/configure/subscriber-mgmt/local-user-db/ipoe/host/ipv6/server
                        leaf server {
                            type types-sros:ipv6-unicast-address;
                            description "IPv6 address of the DHCP server";
                        }

                        ///nokia-conf/configure/subscriber-mgmt/local-user-db/ipoe/host/ipv6/link-address
                        leaf link-address {
                            type types-sros:ipv6-unicast-address;
                            description "Link address used for prefix selection at DHCP server";
                        }

                        ///nokia-conf/configure/subscriber-mgmt/local-user-db/ipoe/host/ipv6/timers
                        container timers {
                            description "Enter the timers context";

                            ///nokia-conf/configure/subscriber-mgmt/local-user-db/ipoe/host/ipv6/timers/preferred-lifetime
                            leaf preferred-lifetime {
                                type union {
                                    type types-sros:time-duration {
                                        range "300..315446399";
                                    }
                                    type enumeration {
                                        enum infinite                       { value -1; }
                                    }
                                }
                                units "seconds";
                                description "Time for a lease to remain preferred";
                            }

                            ///nokia-conf/configure/subscriber-mgmt/local-user-db/ipoe/host/ipv6/timers/rebind
                            leaf rebind {
                                type types-sros:time-duration {
                                    range "0..1209600";
                                }
                                units "seconds";
                                description "Rebind timer (T2)";
                            }

                            ///nokia-conf/configure/subscriber-mgmt/local-user-db/ipoe/host/ipv6/timers/renew
                            leaf renew {
                                type types-sros:time-duration {
                                    range "0..604800";
                                }
                                units "seconds";
                                description "Renew timer (T1)";
                            }

                            ///nokia-conf/configure/subscriber-mgmt/local-user-db/ipoe/host/ipv6/timers/valid-lifetime
                            leaf valid-lifetime {
                                type union {
                                    type types-sros:time-duration {
                                        range "300..315446399";
                                    }
                                    type enumeration {
                                        enum infinite                       { value -1; }
                                    }
                                }
                                units "seconds";
                                description "Time for a lease to remain valid";
                            }

                        } // container timers

                        ///nokia-conf/configure/subscriber-mgmt/local-user-db/ipoe/host/ipv6/option
                        list option {
                            key "number";
                            description "Enter the option list instance";

                            ///nokia-conf/configure/subscriber-mgmt/local-user-db/ipoe/host/ipv6/option/number
                            leaf number {
                                type union {
                                    type uint32 {
                                        range "23";
                                    }
                                    type enumeration {
                                        enum dns-server                     { value 23; }
                                    }
                                }
                                description "The number of the DHCPv6 option.";
                            }

                            ///nokia-conf/configure/subscriber-mgmt/local-user-db/ipoe/host/ipv6/option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ipoe/host/ipv6/option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ipoe/host/ipv6/option/value
                            choice value {
                                mandatory true;
                                description "The value of the DHCP option.";
                                ///nokia-conf/configure/subscriber-mgmt/local-user-db/ipoe/host/ipv6/option/value/hex-string
                                case hex-string {

                                    ///nokia-conf/configure/subscriber-mgmt/local-user-db/ipoe/host/ipv6/option/value/hex-string/hex-string
                                    leaf hex-string {
                                        type types-sros:hex-string {
                                            length "1..256";
                                        }
                                        description "DHCP option specified as hexadecimal string";
                                    }

                                }
                                ///nokia-conf/configure/subscriber-mgmt/local-user-db/ipoe/host/ipv6/option/value/ipv6-address
                                case ipv6-address {

                                    ///nokia-conf/configure/subscriber-mgmt/local-user-db/ipoe/host/ipv6/option/value/ipv6-address/ipv6-address
                                    leaf-list ipv6-address {
                                        type types-sros:ipv6-address;
                                        max-elements 4;
                                        ordered-by user;
                                        description "DHCP option specified as a list of IPv6 addresses";
                                    }

                                }
                            }
                        } // list option

                    } // container ipv6

                    ///nokia-conf/configure/subscriber-mgmt/local-user-db/ipoe/host/mld-import
                    list mld-import {
                        key "policy-name";
                        max-elements 14;
                        description "Add a list entry for mld-import";

                        ///nokia-conf/configure/subscriber-mgmt/local-user-db/ipoe/host/mld-import/policy-name
                        leaf policy-name {
                            type types-sros:named-item;
                            description "MLD import policy used to control the multicast group";
                        }

                    } // list mld-import

                    ///nokia-conf/configure/subscriber-mgmt/local-user-db/ipoe/host/to-client-options
                    container to-client-options {
                        description "Enter the to-client-options context";

                        ///nokia-conf/configure/subscriber-mgmt/local-user-db/ipoe/host/to-client-options/ipv4-option
                        list ipv4-option {
                            key "number";
                            description "Enter the ipv4-option list instance";

                            ///nokia-conf/configure/subscriber-mgmt/local-user-db/ipoe/host/to-client-options/ipv4-option/number
                            leaf number {
                                type union {
                                    type uint32 {
                                        range "1..254";
                                    }
                                    type enumeration {
                                        enum subnet-mask                    { value 1; }
                                        enum default-router                 { value 3; }
                                        enum dns-server                     { value 6; }
                                        enum domain-name                    { value 15; }
                                        enum netbios-name-server            { value 44; }
                                        enum netbios-node-type              { value 46; }
                                        enum lease-time                     { value 51; }
                                        enum lease-renew-time               { value 58; }
                                        enum lease-rebind-time              { value 59; }
                                    }
                                }
                                description "DHCP option to send identification strings to client";
                            }

                            ///nokia-conf/configure/subscriber-mgmt/local-user-db/ipoe/host/to-client-options/ipv4-option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ipoe/host/to-client-options/ipv4-option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ipoe/host/to-client-options/ipv4-option/value
                            choice value {
                                mandatory true;
                                description "The value of the DHCP option.";
                                ///nokia-conf/configure/subscriber-mgmt/local-user-db/ipoe/host/to-client-options/ipv4-option/value/ascii-string
                                case ascii-string {

                                    ///nokia-conf/configure/subscriber-mgmt/local-user-db/ipoe/host/to-client-options/ipv4-option/value/ascii-string/ascii-string
                                    leaf ascii-string {
                                        type types-sros:string-not-all-spaces {
                                            length "1..127";
                                        }
                                        description "DHCP option specified as an ASCII string";
                                    }

                                }
                                ///nokia-conf/configure/subscriber-mgmt/local-user-db/ipoe/host/to-client-options/ipv4-option/value/hex-string
                                case hex-string {

                                    ///nokia-conf/configure/subscriber-mgmt/local-user-db/ipoe/host/to-client-options/ipv4-option/value/hex-string/hex-string
                                    leaf hex-string {
                                        type types-sros:hex-string {
                                            length "1..256";
                                        }
                                        description "DHCP option specified as hexadecimal string";
                                    }

                                }
                                ///nokia-conf/configure/subscriber-mgmt/local-user-db/ipoe/host/to-client-options/ipv4-option/value/netbios-node-type
                                case netbios-node-type {

                                    ///nokia-conf/configure/subscriber-mgmt/local-user-db/ipoe/host/to-client-options/ipv4-option/value/netbios-node-type/netbios-node-type
                                    leaf netbios-node-type {
                                        when "../number = 46 or ../number = 'netbios-node-type'" {
                                            description "netbios-node-type is supported only when the option is netbios-node-type(46)";
                                        }
                                        type enumeration {
                                            enum b-node                         { value 1; }
                                            enum p-node                         { value 2; }
                                            enum m-node                         { value 4; }
                                            enum h-node                         { value 8; }
                                        }
                                        description "DHCP option as NetBIOS node type";
                                    }

                                }
                                ///nokia-conf/configure/subscriber-mgmt/local-user-db/ipoe/host/to-client-options/ipv4-option/value/duration
                                case duration {

                                    ///nokia-conf/configure/subscriber-mgmt/local-user-db/ipoe/host/to-client-options/ipv4-option/value/duration/duration
                                    leaf duration {
                                        when "../number = 51 or ../number = 'lease-time' or ../number = 58 or ../number = 'lease-renew-time' or ../number = 59 or ../number = 'lease-rebind-time'" {
                                            description "duration is supported only when the option is either lease-time(51), lease-renew-time(58) or lease-rebind-time(59)";
                                        }
                                        type types-sros:time-duration {
                                            range "10..315446399";
                                        }
                                        units "seconds";
                                        description "DHCP option as time duration";
                                    }

                                }
                                ///nokia-conf/configure/subscriber-mgmt/local-user-db/ipoe/host/to-client-options/ipv4-option/value/ipv4-address
                                case ipv4-address {

                                    ///nokia-conf/configure/subscriber-mgmt/local-user-db/ipoe/host/to-client-options/ipv4-option/value/ipv4-address/ipv4-address
                                    leaf-list ipv4-address {
                                        when "(not(../number = 46) and not(../number = 'netbios-node-type')) and (not(../number = 51) and not(../number = 'lease-time')) and (not(../number = 58) and not(../number = 'lease-renew-time')) and (not(../number = 59) and not(../number = 'lease-rebind-time'))" {
                                            description "ipv4-address is supported only when the option is neither netbios-node-type(46), lease-time(51), lease-renew-time(58) nor lease-rebind-time(59)";
                                        }
                                        type types-sros:ipv4-address;
                                        max-elements 4;
                                        ordered-by user;
                                        description "DHCP option as a list of IPv4 addresses";
                                    }

                                }
                                ///nokia-conf/configure/subscriber-mgmt/local-user-db/ipoe/host/to-client-options/ipv4-option/value/empty
                                case empty {

                                    ///nokia-conf/configure/subscriber-mgmt/local-user-db/ipoe/host/to-client-options/ipv4-option/value/empty/empty
                                    leaf empty {
                                        type empty;
                                        description "Empty DHCP option";
                                    }

                                }
                            }
                        } // list ipv4-option

                        ///nokia-conf/configure/subscriber-mgmt/local-user-db/ipoe/host/to-client-options/ipv6-option
                        list ipv6-option {
                            key "number";
                            description "Enter the ipv6-option list instance";

                            ///nokia-conf/configure/subscriber-mgmt/local-user-db/ipoe/host/to-client-options/ipv6-option/number
                            leaf number {
                                type union {
                                    type uint32 {
                                        range "1..65535";
                                    }
                                    type enumeration {
                                        enum dns-server                     { value 23; }
                                        enum domain-name                    { value 24; }
                                    }
                                }
                                description "DHCP option to send as identification string";
                            }

                            ///nokia-conf/configure/subscriber-mgmt/local-user-db/ipoe/host/to-client-options/ipv6-option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ipoe/host/to-client-options/ipv6-option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ipoe/host/to-client-options/ipv6-option/value
                            choice value {
                                mandatory true;
                                description "The value of the DHCP option.";
                                ///nokia-conf/configure/subscriber-mgmt/local-user-db/ipoe/host/to-client-options/ipv6-option/value/ascii-string
                                case ascii-string {

                                    ///nokia-conf/configure/subscriber-mgmt/local-user-db/ipoe/host/to-client-options/ipv6-option/value/ascii-string/ascii-string
                                    leaf ascii-string {
                                        type types-sros:string-not-all-spaces {
                                            length "1..127";
                                        }
                                        description "DHCP option specified as an ASCII string";
                                    }

                                }
                                ///nokia-conf/configure/subscriber-mgmt/local-user-db/ipoe/host/to-client-options/ipv6-option/value/hex-string
                                case hex-string {

                                    ///nokia-conf/configure/subscriber-mgmt/local-user-db/ipoe/host/to-client-options/ipv6-option/value/hex-string/hex-string
                                    leaf hex-string {
                                        type types-sros:hex-string {
                                            length "1..256";
                                        }
                                        description "DHCP option specified as hexadecimal string";
                                    }

                                }
                                ///nokia-conf/configure/subscriber-mgmt/local-user-db/ipoe/host/to-client-options/ipv6-option/value/domain-string
                                case domain-string {

                                    ///nokia-conf/configure/subscriber-mgmt/local-user-db/ipoe/host/to-client-options/ipv6-option/value/domain-string/domain-string
                                    leaf domain-string {
                                        type string {
                                            length "1..127";
                                            pattern "[a-z0-9\\-]+(\\.[a-z0-9\\-]+)*";
                                        }
                                        description "DHCP option specified as a domain name";
                                    }

                                }
                                ///nokia-conf/configure/subscriber-mgmt/local-user-db/ipoe/host/to-client-options/ipv6-option/value/ipv6-address
                                case ipv6-address {

                                    ///nokia-conf/configure/subscriber-mgmt/local-user-db/ipoe/host/to-client-options/ipv6-option/value/ipv6-address/ipv6-address
                                    leaf-list ipv6-address {
                                        type types-sros:ipv6-address;
                                        max-elements 4;
                                        ordered-by user;
                                        description "DHCP option specified as a list of IPv6 addresses";
                                    }

                                }
                                ///nokia-conf/configure/subscriber-mgmt/local-user-db/ipoe/host/to-client-options/ipv6-option/value/empty
                                case empty {

                                    ///nokia-conf/configure/subscriber-mgmt/local-user-db/ipoe/host/to-client-options/ipv6-option/value/empty/empty
                                    leaf empty {
                                        type empty;
                                        description "Empty DHCP option";
                                    }

                                }
                            }
                        } // list ipv6-option

                    } // container to-client-options

                    ///nokia-conf/configure/subscriber-mgmt/local-user-db/ipoe/host/to-server-options
                    container to-server-options {
                        description "Enter the to-server-options context";

                        ///nokia-conf/configure/subscriber-mgmt/local-user-db/ipoe/host/to-server-options/ipv6-option
                        list ipv6-option {
                            key "number";
                            description "Enter the ipv6-option list instance";

                            ///nokia-conf/configure/subscriber-mgmt/local-user-db/ipoe/host/to-server-options/ipv6-option/number
                            leaf number {
                                type union {
                                    type uint32 {
                                        range "1..65535";
                                    }
                                    type enumeration {
                                        enum dns-server                     { value 23; }
                                        enum domain-name                    { value 24; }
                                    }
                                }
                                description "DHCP option to send as identification string";
                            }

                            ///nokia-conf/configure/subscriber-mgmt/local-user-db/ipoe/host/to-server-options/ipv6-option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ipoe/host/to-server-options/ipv6-option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ipoe/host/to-server-options/ipv6-option/value
                            choice value {
                                mandatory true;
                                description "The value of the DHCP option.";
                                ///nokia-conf/configure/subscriber-mgmt/local-user-db/ipoe/host/to-server-options/ipv6-option/value/ascii-string
                                case ascii-string {

                                    ///nokia-conf/configure/subscriber-mgmt/local-user-db/ipoe/host/to-server-options/ipv6-option/value/ascii-string/ascii-string
                                    leaf ascii-string {
                                        type types-sros:string-not-all-spaces {
                                            length "1..127";
                                        }
                                        description "DHCP option specified as an ASCII string";
                                    }

                                }
                                ///nokia-conf/configure/subscriber-mgmt/local-user-db/ipoe/host/to-server-options/ipv6-option/value/hex-string
                                case hex-string {

                                    ///nokia-conf/configure/subscriber-mgmt/local-user-db/ipoe/host/to-server-options/ipv6-option/value/hex-string/hex-string
                                    leaf hex-string {
                                        type types-sros:hex-string {
                                            length "1..256";
                                        }
                                        description "DHCP option specified as hexadecimal string";
                                    }

                                }
                                ///nokia-conf/configure/subscriber-mgmt/local-user-db/ipoe/host/to-server-options/ipv6-option/value/domain-string
                                case domain-string {

                                    ///nokia-conf/configure/subscriber-mgmt/local-user-db/ipoe/host/to-server-options/ipv6-option/value/domain-string/domain-string
                                    leaf domain-string {
                                        type string {
                                            length "1..127";
                                            pattern "[a-z0-9\\-]+(\\.[a-z0-9\\-]+)*";
                                        }
                                        description "DHCP option specified as a domain name";
                                    }

                                }
                                ///nokia-conf/configure/subscriber-mgmt/local-user-db/ipoe/host/to-server-options/ipv6-option/value/ipv6-address
                                case ipv6-address {

                                    ///nokia-conf/configure/subscriber-mgmt/local-user-db/ipoe/host/to-server-options/ipv6-option/value/ipv6-address/ipv6-address
                                    leaf-list ipv6-address {
                                        type types-sros:ipv6-address;
                                        max-elements 4;
                                        ordered-by user;
                                        description "DHCP option specified as a list of IPv6 addresses";
                                    }

                                }
                                ///nokia-conf/configure/subscriber-mgmt/local-user-db/ipoe/host/to-server-options/ipv6-option/value/empty
                                case empty {

                                    ///nokia-conf/configure/subscriber-mgmt/local-user-db/ipoe/host/to-server-options/ipv6-option/value/empty/empty
                                    leaf empty {
                                        type empty;
                                        description "Empty DHCP option";
                                    }

                                }
                            }
                        } // list ipv6-option

                    } // container to-server-options

                } // list host

            } // container ipoe

            ///nokia-conf/configure/subscriber-mgmt/local-user-db/ppp
            container ppp {
                description "Enter the ppp context";

                ///nokia-conf/configure/subscriber-mgmt/local-user-db/ppp/match-list
                leaf-list match-list {
                    type enumeration {
                        enum circuit-id                     { value 1; }
                        enum mac                            { value 2; }
                        enum remote-id                      { value 3; }
                        enum user-name                      { value 4; }
                        enum service-name                   { value 5; }
                        enum sap-id                         { value 6; }
                        enum encap-tag-range                { value 7; }
                        enum derived-id                     { value 8; }
                        enum encap-tag-separate-range       { value 9; }
                    }
                    max-elements 3;
                    ordered-by user;
                    sros-ext:auto-restart-to-modify;
                    description "PPP host match type";
                }

                ///nokia-conf/configure/subscriber-mgmt/local-user-db/ppp/mask
                list mask {
                    key "type";
                    description "Enter the mask list instance";

                    ///nokia-conf/configure/subscriber-mgmt/local-user-db/ppp/mask/type
                    leaf type {
                        type enumeration {
                            enum circuit-id                     { value 1; }
                            enum mac                            { value 2; }
                            enum remote-id                      { value 3; }
                            enum user-name                      { value 4; }
                            enum service-name                   { value 5; }
                            enum sap-id                         { value 6; }
                        }
                        description "Matching type to identify a host";
                    }

                    ///nokia-conf/configure/subscriber-mgmt/local-user-db/ppp/mask/apply-groups
                    leaf-list apply-groups {
                        type leafref {
                            path "../../../../../groups/group/name";
                        }
                        max-elements 8;
                        ordered-by user;
                        description "Apply a configuration group at this level";
                    }

                    ///nokia-conf/configure/subscriber-mgmt/local-user-db/ppp/mask/apply-groups-exclude
                    leaf-list apply-groups-exclude {
                        type leafref {
                            path "../../../../../groups/group/name";
                        }
                        max-elements 8;
                        ordered-by user;
                        description "Exclude a configuration group at this level";
                    }

                    ///nokia-conf/configure/subscriber-mgmt/local-user-db/ppp/mask/prefix
                    container prefix {
                        presence "Enable the prefix context";
                        description "Enable the prefix context";

                        ///nokia-conf/configure/subscriber-mgmt/local-user-db/ppp/mask/prefix/prefix
                        choice prefix {
                            mandatory true;
                            ///nokia-conf/configure/subscriber-mgmt/local-user-db/ppp/mask/prefix/prefix/length
                            case length {

                                ///nokia-conf/configure/subscriber-mgmt/local-user-db/ppp/mask/prefix/prefix/length/length
                                leaf length {
                                    type uint32 {
                                        range "1..127";
                                    }
                                    description "PPP mask prefix length";
                                }

                            }
                            ///nokia-conf/configure/subscriber-mgmt/local-user-db/ppp/mask/prefix/prefix/string
                            case string {

                                ///nokia-conf/configure/subscriber-mgmt/local-user-db/ppp/mask/prefix/prefix/string/string
                                leaf string {
                                    type string {
                                        length "1..127";
                                    }
                                    description "Prefix string";
                                }

                            }
                        }
                    } // container prefix

                    ///nokia-conf/configure/subscriber-mgmt/local-user-db/ppp/mask/suffix
                    container suffix {
                        presence "Enable the suffix context";
                        description "Enable the suffix context";

                        ///nokia-conf/configure/subscriber-mgmt/local-user-db/ppp/mask/suffix/suffix
                        choice suffix {
                            mandatory true;
                            ///nokia-conf/configure/subscriber-mgmt/local-user-db/ppp/mask/suffix/suffix/length
                            case length {

                                ///nokia-conf/configure/subscriber-mgmt/local-user-db/ppp/mask/suffix/suffix/length/length
                                leaf length {
                                    type uint32 {
                                        range "1..127";
                                    }
                                    description "PPP mask suffix length";
                                }

                            }
                            ///nokia-conf/configure/subscriber-mgmt/local-user-db/ppp/mask/suffix/suffix/string
                            case string {

                                ///nokia-conf/configure/subscriber-mgmt/local-user-db/ppp/mask/suffix/suffix/string/string
                                leaf string {
                                    type string {
                                        length "1..127";
                                        pattern "[^*].*";
                                    }
                                    description "Suffix string";
                                }

                            }
                        }
                    } // container suffix

                } // list mask

                ///nokia-conf/configure/subscriber-mgmt/local-user-db/ppp/host
                list host {
                    key "host-name";
                    description "Enter the host list instance";

                    ///nokia-conf/configure/subscriber-mgmt/local-user-db/ppp/host/host-name
                    leaf host-name {
                        type types-sros:named-item;
                        description "Host name";
                    }

                    ///nokia-conf/configure/subscriber-mgmt/local-user-db/ppp/host/admin-state
                    leaf admin-state {
                        type types-sros:admin-state;
                        default "disable";
                        description "Administrative state of the host";
                    }

                    ///nokia-conf/configure/subscriber-mgmt/local-user-db/ppp/host/retail-service-id
                    leaf retail-service-id {
                        type types-services:service-id-maf;
                        description "Configure the retail service-id";
                    }

                    ///nokia-conf/configure/subscriber-mgmt/local-user-db/ppp/host/rip-policy
                    leaf rip-policy {
                        type types-sros:named-item;
                        description "RIP policy";
                    }

                    ///nokia-conf/configure/subscriber-mgmt/local-user-db/ppp/host/pado-delay
                    leaf pado-delay {
                        type types-sros:time-duration {
                            range "1..30";
                        }
                        units "deciseconds";
                        description "Delay timeout before sending a PADO";
                    }

                    ///nokia-conf/configure/subscriber-mgmt/local-user-db/ppp/host/steering-profile
                    leaf steering-profile {
                        type types-sros:named-item;
                        description "Steering profile";
                    }

                    ///nokia-conf/configure/subscriber-mgmt/local-user-db/ppp/host/apply-groups
                    leaf-list apply-groups {
                        type leafref {
                            path "../../../../../groups/group/name";
                        }
                        max-elements 8;
                        ordered-by user;
                        description "Apply a configuration group at this level";
                    }

                    ///nokia-conf/configure/subscriber-mgmt/local-user-db/ppp/host/apply-groups-exclude
                    leaf-list apply-groups-exclude {
                        type leafref {
                            path "../../../../../groups/group/name";
                        }
                        max-elements 8;
                        ordered-by user;
                        description "Exclude a configuration group at this level";
                    }

                    ///nokia-conf/configure/subscriber-mgmt/local-user-db/ppp/host/host-identification
                    container host-identification {
                        description "Enter the host-identification context";

                        ///nokia-conf/configure/subscriber-mgmt/local-user-db/ppp/host/host-identification/derived-id
                        leaf derived-id {
                            type types-sros:display-string;
                            sros-ext:auto-restart-to-modify;
                            description "Derived ID string";
                        }

                        ///nokia-conf/configure/subscriber-mgmt/local-user-db/ppp/host/host-identification/mac
                        leaf mac {
                            type types-sros:mac-unicast-address-no-zero;
                            sros-ext:auto-restart-to-modify;
                            description "MAC address";
                        }

                        ///nokia-conf/configure/subscriber-mgmt/local-user-db/ppp/host/host-identification/sap-id
                        leaf sap-id {
                            type types-sros:display-string;
                            sros-ext:auto-restart-to-modify;
                            description "SAP ID";
                        }

                        ///nokia-conf/configure/subscriber-mgmt/local-user-db/ppp/host/host-identification/service-name
                        leaf service-name {
                            type types-sros:display-string;
                            sros-ext:auto-restart-to-modify;
                            description "Administrative service name";
                        }

                        ///nokia-conf/configure/subscriber-mgmt/local-user-db/ppp/host/host-identification/circuit-id
                        container circuit-id {
                            description "Enter the circuit-id context";

                            ///nokia-conf/configure/subscriber-mgmt/local-user-db/ppp/host/host-identification/circuit-id/format
                            choice format {
                                ///nokia-conf/configure/subscriber-mgmt/local-user-db/ppp/host/host-identification/circuit-id/format/ascii-string
                                case ascii-string {

                                    ///nokia-conf/configure/subscriber-mgmt/local-user-db/ppp/host/host-identification/circuit-id/format/ascii-string/ascii-string
                                    leaf ascii-string {
                                        type string {
                                            length "1..127";
                                        }
                                        sros-ext:auto-restart-to-modify;
                                        description "Circuit ID as ASCII string";
                                    }

                                }
                                ///nokia-conf/configure/subscriber-mgmt/local-user-db/ppp/host/host-identification/circuit-id/format/hex-string
                                case hex-string {

                                    ///nokia-conf/configure/subscriber-mgmt/local-user-db/ppp/host/host-identification/circuit-id/format/hex-string/hex-string
                                    leaf hex-string {
                                        type types-sros:hex-string {
                                            length "1..256";
                                        }
                                        sros-ext:auto-restart-to-modify;
                                        description "Circuit ID as hexadecimal string";
                                    }

                                }
                            }
                        } // container circuit-id

                        ///nokia-conf/configure/subscriber-mgmt/local-user-db/ppp/host/host-identification/remote-id
                        container remote-id {
                            description "Enter the remote-id context";

                            ///nokia-conf/configure/subscriber-mgmt/local-user-db/ppp/host/host-identification/remote-id/format
                            choice format {
                                ///nokia-conf/configure/subscriber-mgmt/local-user-db/ppp/host/host-identification/remote-id/format/ascii-string
                                case ascii-string {

                                    ///nokia-conf/configure/subscriber-mgmt/local-user-db/ppp/host/host-identification/remote-id/format/ascii-string/ascii-string
                                    leaf ascii-string {
                                        type string {
                                            length "1..255";
                                        }
                                        sros-ext:auto-restart-to-modify;
                                        description "Remote ID as ASCII string";
                                    }

                                }
                                ///nokia-conf/configure/subscriber-mgmt/local-user-db/ppp/host/host-identification/remote-id/format/hex-string
                                case hex-string {

                                    ///nokia-conf/configure/subscriber-mgmt/local-user-db/ppp/host/host-identification/remote-id/format/hex-string/hex-string
                                    leaf hex-string {
                                        type types-sros:hex-string {
                                            length "1..512";
                                        }
                                        sros-ext:auto-restart-to-modify;
                                        description "Remote ID as hexadecimal string";
                                    }

                                }
                            }
                        } // container remote-id

                        ///nokia-conf/configure/subscriber-mgmt/local-user-db/ppp/host/host-identification/encap-tag-range
                        container encap-tag-range {
                            presence "Enable the encap-tag-range context";
                            description "Enable the encap-tag-range context";

                            ///nokia-conf/configure/subscriber-mgmt/local-user-db/ppp/host/host-identification/encap-tag-range/from
                            leaf from {
                                type types-sros:atm-or-vlan-encap;
                                sros-ext:auto-restart-to-modify;
                                mandatory true;
                                description "Start tag";
                            }

                            ///nokia-conf/configure/subscriber-mgmt/local-user-db/ppp/host/host-identification/encap-tag-range/to
                            leaf to {
                                type types-sros:atm-or-vlan-encap;
                                sros-ext:auto-restart-to-modify;
                                mandatory true;
                                description "End tag";
                            }

                        } // container encap-tag-range

                        ///nokia-conf/configure/subscriber-mgmt/local-user-db/ppp/host/host-identification/encap-tag-separate-range
                        container encap-tag-separate-range {
                            description "Enter the encap-tag-separate-range context";

                            ///nokia-conf/configure/subscriber-mgmt/local-user-db/ppp/host/host-identification/encap-tag-separate-range/outer
                            container outer {
                                description "Enter the outer context";

                                ///nokia-conf/configure/subscriber-mgmt/local-user-db/ppp/host/host-identification/encap-tag-separate-range/outer/start
                                leaf start {
                                    type int32 {
                                        range "0..4094";
                                    }
                                    sros-ext:auto-restart-to-modify;
                                    description "Lower bound of the outer encapsulation tag range";
                                }

                                ///nokia-conf/configure/subscriber-mgmt/local-user-db/ppp/host/host-identification/encap-tag-separate-range/outer/end
                                leaf end {
                                    type int32 {
                                        range "0..4094";
                                    }
                                    sros-ext:auto-restart-to-modify;
                                    description "Upper bound of the outer encapsulation tag range";
                                }

                            } // container outer

                            ///nokia-conf/configure/subscriber-mgmt/local-user-db/ppp/host/host-identification/encap-tag-separate-range/inner
                            container inner {
                                description "Enter the inner context";

                                ///nokia-conf/configure/subscriber-mgmt/local-user-db/ppp/host/host-identification/encap-tag-separate-range/inner/start
                                leaf start {
                                    type int32 {
                                        range "0..4094";
                                    }
                                    sros-ext:auto-restart-to-modify;
                                    description "Lower bound of the inner encapsulation tag range";
                                }

                                ///nokia-conf/configure/subscriber-mgmt/local-user-db/ppp/host/host-identification/encap-tag-separate-range/inner/end
                                leaf end {
                                    type int32 {
                                        range "0..4094";
                                    }
                                    sros-ext:auto-restart-to-modify;
                                    description "Upper bound of the inner encapsulation tag range";
                                }

                            } // container inner

                        } // container encap-tag-separate-range

                        ///nokia-conf/configure/subscriber-mgmt/local-user-db/ppp/host/host-identification/user-name
                        container user-name {
                            presence "Enable the user-name context";
                            description "Enable the user-name context";

                            ///nokia-conf/configure/subscriber-mgmt/local-user-db/ppp/host/host-identification/user-name/name
                            leaf name {
                                type types-sros:display-string {
                                    length "1..253";
                                }
                                sros-ext:auto-restart-to-modify;
                                mandatory true;
                                description "Host username";
                            }

                            ///nokia-conf/configure/subscriber-mgmt/local-user-db/ppp/host/host-identification/user-name/format
                            leaf format {
                                type enumeration {
                                    enum full                           { value 1; }
                                    enum no-domain                      { value 2; }
                                    enum domain-only                    { value 3; }
                                }
                                sros-ext:auto-restart-to-modify;
                                default "full";
                                description "Username format";
                            }

                        } // container user-name

                    } // container host-identification

                    ///nokia-conf/configure/subscriber-mgmt/local-user-db/ppp/host/authentication
                    container authentication {
                        description "Enter the authentication context";

                        ///nokia-conf/configure/subscriber-mgmt/local-user-db/ppp/host/authentication/radius-auth-policy
                        leaf radius-auth-policy {
                            type types-sros:named-item;
                            description "Host authentication policy";
                        }

                        ///nokia-conf/configure/subscriber-mgmt/local-user-db/ppp/host/authentication/gx-policy
                        leaf gx-policy {
                            type types-sros:named-item;
                            description "Diameter application policy";
                        }

                        ///nokia-conf/configure/subscriber-mgmt/local-user-db/ppp/host/authentication/nasreq-auth-policy
                        leaf nasreq-auth-policy {
                            type types-sros:named-item;
                            description "Diameter NASREQ application policy for authentication";
                        }

                        ///nokia-conf/configure/subscriber-mgmt/local-user-db/ppp/host/authentication/padi-auth-policy
                        leaf padi-auth-policy {
                            type types-sros:named-item;
                            description "Authentication policy name";
                        }

                        ///nokia-conf/configure/subscriber-mgmt/local-user-db/ppp/host/authentication/pre-auth-policy
                        leaf pre-auth-policy {
                            type types-sros:named-item;
                            description "Pre-authentication policy of this host";
                        }

                        ///nokia-conf/configure/subscriber-mgmt/local-user-db/ppp/host/authentication/user-db
                        leaf user-db {
                            type types-sros:named-item;
                            description "Local user DB to use for PPP PAP/CHAP authentication";
                        }

                    } // container authentication

                    ///nokia-conf/configure/subscriber-mgmt/local-user-db/ppp/host/lns-interface
                    container lns-interface {
                        presence "Enable the lns-interface context";
                        description "Enable the lns-interface context";

                        ///nokia-conf/configure/subscriber-mgmt/local-user-db/ppp/host/lns-interface/name
                        leaf name {
                            type types-sros:named-item;
                            mandatory true;
                            description "IP interface name";
                        }

                        ///nokia-conf/configure/subscriber-mgmt/local-user-db/ppp/host/lns-interface/service-id
                        leaf service-id {
                            type types-services:service-id-maf;
                            mandatory true;
                            description "Service ID";
                        }

                    } // container lns-interface

                    ///nokia-conf/configure/subscriber-mgmt/local-user-db/ppp/host/radius-accounting-policy
                    container radius-accounting-policy {
                        description "Enter the radius-accounting-policy context";

                        ///nokia-conf/configure/subscriber-mgmt/local-user-db/ppp/host/radius-accounting-policy/name
                        leaf name {
                            type types-sros:named-item;
                            description "RADIUS accounting policy name";
                        }

                        ///nokia-conf/configure/subscriber-mgmt/local-user-db/ppp/host/radius-accounting-policy/duplicate
                        leaf duplicate {
                            type types-sros:named-item;
                            description "RADIUS accounting policy for generating duplicate accounting information";
                        }

                    } // container radius-accounting-policy

                    ///nokia-conf/configure/subscriber-mgmt/local-user-db/ppp/host/identification
                    container identification {
                        presence "Enable the identification context";
                        description "Enable the identification context";

                        ///nokia-conf/configure/subscriber-mgmt/local-user-db/ppp/host/identification/option-number
                        leaf option-number {
                            type uint32 {
                                range "1..254";
                            }
                            sros-ext:immutable;
                            default "254";
                            description "Identification strings for the subscriber";
                        }

                        ///nokia-conf/configure/subscriber-mgmt/local-user-db/ppp/host/identification/ancp-string
                        leaf ancp-string {
                            type string {
                                length "1..63";
                            }
                            description "ANCP string";
                        }

                        ///nokia-conf/configure/subscriber-mgmt/local-user-db/ppp/host/identification/app-profile-string
                        leaf app-profile-string {
                            type string {
                                length "1..16";
                            }
                            description "Application profile string";
                        }

                        ///nokia-conf/configure/subscriber-mgmt/local-user-db/ppp/host/identification/category-map-name
                        leaf category-map-name {
                            type types-sros:named-item;
                            description "Category map name";
                        }

                        ///nokia-conf/configure/subscriber-mgmt/local-user-db/ppp/host/identification/int-dest-id
                        leaf int-dest-id {
                            type types-submgt:int-dest-id;
                            description "Intermediate destination ID";
                        }

                        ///nokia-conf/configure/subscriber-mgmt/local-user-db/ppp/host/identification/sla-profile-string
                        leaf sla-profile-string {
                            type string {
                                length "1..32";
                            }
                            description "SLA profile string";
                        }

                        ///nokia-conf/configure/subscriber-mgmt/local-user-db/ppp/host/identification/sub-profile-string
                        leaf sub-profile-string {
                            type string {
                                length "1..32";
                            }
                            description "Sub profile string";
                        }

                        ///nokia-conf/configure/subscriber-mgmt/local-user-db/ppp/host/identification/subscriber-id
                        leaf subscriber-id {
                            type types-sros:named-item-64;
                            description "Subscriber ID";
                        }

                        ///nokia-conf/configure/subscriber-mgmt/local-user-db/ppp/host/identification/spi-sharing-group-id
                        leaf spi-sharing-group-id {
                            type int32 {
                                range "0..65535";
                            }
                            description "SPI sharing group ID";
                        }

                    } // container identification

                    ///nokia-conf/configure/subscriber-mgmt/local-user-db/ppp/host/msap-defaults
                    container msap-defaults {
                        description "Enter the msap-defaults context";

                        ///nokia-conf/configure/subscriber-mgmt/local-user-db/ppp/host/msap-defaults/policy
                        leaf policy {
                            type types-sros:named-item;
                            description "MSAP policy";
                        }

                        ///nokia-conf/configure/subscriber-mgmt/local-user-db/ppp/host/msap-defaults/service
                        leaf service {
                            type types-services:service-id-maf;
                            description "Service ID";
                        }

                        ///nokia-conf/configure/subscriber-mgmt/local-user-db/ppp/host/msap-defaults/group-interface
                        container group-interface {
                            presence "Enable the group-interface context";
                            description "Enable the group-interface context";

                            ///nokia-conf/configure/subscriber-mgmt/local-user-db/ppp/host/msap-defaults/group-interface/name
                            leaf name {
                                type types-sros:named-item;
                                mandatory true;
                                description "IP interface name";
                            }

                            ///nokia-conf/configure/subscriber-mgmt/local-user-db/ppp/host/msap-defaults/group-interface/parameters
                            choice parameters {
                                ///nokia-conf/configure/subscriber-mgmt/local-user-db/ppp/host/msap-defaults/group-interface/parameters/prefix
                                case prefix {

                                    ///nokia-conf/configure/subscriber-mgmt/local-user-db/ppp/host/msap-defaults/group-interface/parameters/prefix/prefix
                                    leaf prefix {
                                        type enumeration {
                                            enum port-id                        { value 2; }
                                        }
                                        description "Prefix to the IP interface name";
                                    }

                                }
                                ///nokia-conf/configure/subscriber-mgmt/local-user-db/ppp/host/msap-defaults/group-interface/parameters/suffix
                                case suffix {

                                    ///nokia-conf/configure/subscriber-mgmt/local-user-db/ppp/host/msap-defaults/group-interface/parameters/suffix/suffix
                                    leaf suffix {
                                        type enumeration {
                                            enum port-id                        { value 2; }
                                        }
                                        description "Suffix for the group interface";
                                    }

                                }
                            }
                        } // container group-interface

                    } // container msap-defaults

                    ///nokia-conf/configure/subscriber-mgmt/local-user-db/ppp/host/access-loop-information
                    container access-loop-information {
                        description "Enter the access-loop-information context";

                        ///nokia-conf/configure/subscriber-mgmt/local-user-db/ppp/host/access-loop-information/circuit-id
                        container circuit-id {
                            presence "Enable the circuit-id context";
                            description "Enable the circuit-id context";

                            ///nokia-conf/configure/subscriber-mgmt/local-user-db/ppp/host/access-loop-information/circuit-id/format
                            choice format {
                                mandatory true;
                                ///nokia-conf/configure/subscriber-mgmt/local-user-db/ppp/host/access-loop-information/circuit-id/format/ascii-string
                                case ascii-string {

                                    ///nokia-conf/configure/subscriber-mgmt/local-user-db/ppp/host/access-loop-information/circuit-id/format/ascii-string/ascii-string
                                    leaf ascii-string {
                                        type string {
                                            length "1..63";
                                        }
                                        description "Circuit ID as an ASCII string";
                                    }

                                }
                                ///nokia-conf/configure/subscriber-mgmt/local-user-db/ppp/host/access-loop-information/circuit-id/format/sap-id
                                case sap-id {

                                    ///nokia-conf/configure/subscriber-mgmt/local-user-db/ppp/host/access-loop-information/circuit-id/format/sap-id/sap-id
                                    leaf sap-id {
                                        status obsolete;
                                        type boolean;
                                        description "SAP ID as circuit ID";
                                    }

                                }
                                ///nokia-conf/configure/subscriber-mgmt/local-user-db/ppp/host/access-loop-information/circuit-id/format/use-sap-id
                                case use-sap-id {

                                    ///nokia-conf/configure/subscriber-mgmt/local-user-db/ppp/host/access-loop-information/circuit-id/format/use-sap-id/use-sap-id
                                    leaf use-sap-id {
                                        type empty;
                                        description "Use sap-id as circuit-id.";
                                    }

                                }
                            }
                        } // container circuit-id

                        ///nokia-conf/configure/subscriber-mgmt/local-user-db/ppp/host/access-loop-information/remote-id
                        container remote-id {
                            presence "Enable the remote-id context";
                            description "Enable the remote-id context";

                            ///nokia-conf/configure/subscriber-mgmt/local-user-db/ppp/host/access-loop-information/remote-id/format
                            choice format {
                                mandatory true;
                                ///nokia-conf/configure/subscriber-mgmt/local-user-db/ppp/host/access-loop-information/remote-id/format/ascii-string
                                case ascii-string {

                                    ///nokia-conf/configure/subscriber-mgmt/local-user-db/ppp/host/access-loop-information/remote-id/format/ascii-string/ascii-string
                                    leaf ascii-string {
                                        type string {
                                            length "1..63";
                                        }
                                        description "String format for the remote ID";
                                    }

                                }
                                ///nokia-conf/configure/subscriber-mgmt/local-user-db/ppp/host/access-loop-information/remote-id/format/mac
                                case mac {

                                    ///nokia-conf/configure/subscriber-mgmt/local-user-db/ppp/host/access-loop-information/remote-id/format/mac/mac
                                    leaf mac {
                                        status obsolete;
                                        type boolean;
                                        description "Use MAC address as remote ID";
                                    }

                                }
                                ///nokia-conf/configure/subscriber-mgmt/local-user-db/ppp/host/access-loop-information/remote-id/format/use-mac-address
                                case use-mac-address {

                                    ///nokia-conf/configure/subscriber-mgmt/local-user-db/ppp/host/access-loop-information/remote-id/format/use-mac-address/use-mac-address
                                    leaf use-mac-address {
                                        type empty;
                                        description "Use MAC address as remote-id.";
                                    }

                                }
                            }
                        } // container remote-id

                    } // container access-loop-information

                    ///nokia-conf/configure/subscriber-mgmt/local-user-db/ppp/host/l2tp
                    container l2tp {
                        description "Enter the l2tp context";

                        ///nokia-conf/configure/subscriber-mgmt/local-user-db/ppp/host/l2tp/group
                        container group {
                            presence "Enable the group context";
                            description "Enable the group context";

                            ///nokia-conf/configure/subscriber-mgmt/local-user-db/ppp/host/l2tp/group/name
                            leaf name {
                                type string {
                                    length "1..63";
                                }
                                mandatory true;
                                description "L2TP tunnel group name";
                            }

                            ///nokia-conf/configure/subscriber-mgmt/local-user-db/ppp/host/l2tp/group/service-id
                            leaf service-id {
                                type types-services:external-service-id;
                                description "Service ID for the L2TP tunnel group";
                            }

                        } // container group

                    } // container l2tp

                    ///nokia-conf/configure/subscriber-mgmt/local-user-db/ppp/host/password
                    container password {
                        description "Enter the password context";

                        ///nokia-conf/configure/subscriber-mgmt/local-user-db/ppp/host/password/password
                        choice password {
                            ///nokia-conf/configure/subscriber-mgmt/local-user-db/ppp/host/password/password/pap
                            case pap {

                                ///nokia-conf/configure/subscriber-mgmt/local-user-db/ppp/host/password/password/pap/pap
                                leaf pap {
                                    type types-sros:encrypted-leaf {
                                        length "1..115";
                                    }
                                    description "PAP for the password";
                                }

                            }
                            ///nokia-conf/configure/subscriber-mgmt/local-user-db/ppp/host/password/password/chap
                            case chap {

                                ///nokia-conf/configure/subscriber-mgmt/local-user-db/ppp/host/password/password/chap/chap
                                leaf chap {
                                    type types-sros:encrypted-leaf {
                                        length "1..115";
                                    }
                                    description "CHAP protocol";
                                }

                            }
                            ///nokia-conf/configure/subscriber-mgmt/local-user-db/ppp/host/password/password/ignore
                            case ignore {

                                ///nokia-conf/configure/subscriber-mgmt/local-user-db/ppp/host/password/password/ignore/ignore
                                leaf ignore {
                                    type empty;
                                    description "Ignore the PAP and CHAP passwords";
                                }

                            }
                        }
                    } // container password

                    ///nokia-conf/configure/subscriber-mgmt/local-user-db/ppp/host/access-loop-encapsulation
                    container access-loop-encapsulation {
                        presence "Enable the access-loop-encapsulation context";
                        description "Enable the access-loop-encapsulation context";

                        ///nokia-conf/configure/subscriber-mgmt/local-user-db/ppp/host/access-loop-encapsulation/rate-down
                        leaf rate-down {
                            type uint32 {
                                range "1..100000";
                            }
                            units "kilobps";
                            description "Last mile link downstream rate in the access loop";
                        }

                        ///nokia-conf/configure/subscriber-mgmt/local-user-db/ppp/host/access-loop-encapsulation/apply-groups
                        leaf-list apply-groups {
                            type leafref {
                                path "../../../../../../groups/group/name";
                            }
                            max-elements 8;
                            ordered-by user;
                            description "Apply a configuration group at this level";
                        }

                        ///nokia-conf/configure/subscriber-mgmt/local-user-db/ppp/host/access-loop-encapsulation/apply-groups-exclude
                        leaf-list apply-groups-exclude {
                            type leafref {
                                path "../../../../../../groups/group/name";
                            }
                            max-elements 8;
                            ordered-by user;
                            description "Exclude a configuration group at this level";
                        }

                        ///nokia-conf/configure/subscriber-mgmt/local-user-db/ppp/host/access-loop-encapsulation/encap-offset
                        container encap-offset {
                            description "Enter the encap-offset context";

                            ///nokia-conf/configure/subscriber-mgmt/local-user-db/ppp/host/access-loop-encapsulation/encap-offset/type
                            leaf type {
                                type enumeration {
                                    enum pppoa-llc                      { value 1; }
                                    enum pppoa-null                     { value 2; }
                                    enum pppoeoa-llc                    { value 3; }
                                    enum pppoeoa-llc-fcs                { value 4; }
                                    enum pppoeoa-llc-tagged             { value 5; }
                                    enum pppoeoa-llc-tagged-fcs         { value 6; }
                                    enum pppoeoa-null                   { value 7; }
                                    enum pppoeoa-null-fcs               { value 8; }
                                    enum pppoeoa-null-tagged            { value 9; }
                                    enum pppoeoa-null-tagged-fcs        { value 10; }
                                    enum ipoa-llc                       { value 11; }
                                    enum ipoa-null                      { value 12; }
                                    enum ipoeoa-llc                     { value 13; }
                                    enum ipoeoa-llc-fcs                 { value 14; }
                                    enum ipoeoa-llc-tagged              { value 15; }
                                    enum ipoeoa-llc-tagged-fcs          { value 16; }
                                    enum ipoeoa-null                    { value 17; }
                                    enum ipoeoa-null-fcs                { value 18; }
                                    enum ipoeoa-null-tagged             { value 19; }
                                    enum ipoeoa-null-tagged-fcs         { value 20; }
                                    enum pppoe                          { value 21; }
                                    enum pppoe-tagged                   { value 22; }
                                    enum ipoe                           { value 23; }
                                    enum ipoe-tagged                    { value 24; }
                                }
                                description "Egress encapsulation type";
                            }

                        } // container encap-offset

                    } // container access-loop-encapsulation

                    ///nokia-conf/configure/subscriber-mgmt/local-user-db/ppp/host/ipv4
                    container ipv4 {
                        description "Enter the ipv4 context";

                        ///nokia-conf/configure/subscriber-mgmt/local-user-db/ppp/host/ipv4/ignore-df-bit
                        leaf ignore-df-bit {
                            type boolean;
                            default "false";
                            description "Ignore the DF bit in the IPv4 header when fragmenting";
                        }

                        ///nokia-conf/configure/subscriber-mgmt/local-user-db/ppp/host/ipv4/address
                        container address {
                            description "Enter the address context";

                            ///nokia-conf/configure/subscriber-mgmt/local-user-db/ppp/host/ipv4/address/address
                            choice address {
                                ///nokia-conf/configure/subscriber-mgmt/local-user-db/ppp/host/ipv4/address/address/ip-address
                                case ip-address {

                                    ///nokia-conf/configure/subscriber-mgmt/local-user-db/ppp/host/ipv4/address/address/ip-address/ip-address
                                    leaf ip-address {
                                        type types-sros:ipv4-unicast-address;
                                        description "Fixed IPv4 address of the host";
                                    }

                                    ///nokia-conf/configure/subscriber-mgmt/local-user-db/ppp/host/ipv4/address/address/ip-address/prefix-length
                                    leaf prefix-length {
                                        type uint32 {
                                            range "1..32";
                                        }
                                        default "32";
                                        description "IPv4 host address prefix length";
                                    }

                                }
                                ///nokia-conf/configure/subscriber-mgmt/local-user-db/ppp/host/ipv4/address/address/gi-address
                                case gi-address {

                                    ///nokia-conf/configure/subscriber-mgmt/local-user-db/ppp/host/ipv4/address/address/gi-address/gi-address
                                    leaf gi-address {
                                        type enumeration {
                                            enum subnet-scope                   { value 0; }
                                            enum pool-scope                     { value 1; }
                                        }
                                        description "Use gi-address to select a pool with the given scope";
                                    }

                                }
                                ///nokia-conf/configure/subscriber-mgmt/local-user-db/ppp/host/ipv4/address/address/pool
                                case pool {

                                    ///nokia-conf/configure/subscriber-mgmt/local-user-db/ppp/host/ipv4/address/address/pool/pool
                                    container pool {
                                        presence "Enable the pool context";
                                        description "Enable the pool context";

                                        ///nokia-conf/configure/subscriber-mgmt/local-user-db/ppp/host/ipv4/address/address/pool/pool/primary
                                        leaf primary {
                                            type types-sros:named-item;
                                            mandatory true;
                                            description "Primary pool name";
                                        }

                                        ///nokia-conf/configure/subscriber-mgmt/local-user-db/ppp/host/ipv4/address/address/pool/pool/secondary
                                        leaf secondary {
                                            type types-sros:named-item;
                                            description "Secondary pool name";
                                        }

                                        ///nokia-conf/configure/subscriber-mgmt/local-user-db/ppp/host/ipv4/address/address/pool/pool/delimiter
                                        leaf delimiter {
                                            type string {
                                                length "1";
                                            }
                                            description "Delimiter separating primary and secondary pool names";
                                        }

                                    } // container pool

                                }
                                ///nokia-conf/configure/subscriber-mgmt/local-user-db/ppp/host/ipv4/address/address/use-pool-from-client
                                case use-pool-from-client {

                                    ///nokia-conf/configure/subscriber-mgmt/local-user-db/ppp/host/ipv4/address/address/use-pool-from-client/use-pool-from-client
                                    container use-pool-from-client {
                                        presence "Enable the use-pool-from-client context";
                                        description "Enable the use-pool-from-client context";

                                        ///nokia-conf/configure/subscriber-mgmt/local-user-db/ppp/host/ipv4/address/address/use-pool-from-client/use-pool-from-client/delimiter
                                        leaf delimiter {
                                            type string {
                                                length "1";
                                            }
                                            description "Delimiter character to combine primary and secondary pool names";
                                        }

                                    } // container use-pool-from-client

                                }
                            }
                        } // container address

                        ///nokia-conf/configure/subscriber-mgmt/local-user-db/ppp/host/ipv4/option
                        list option {
                            key "number";
                            description "Enter the option list instance";

                            ///nokia-conf/configure/subscriber-mgmt/local-user-db/ppp/host/ipv4/option/number
                            leaf number {
                                type union {
                                    type uint32 {
                                        range "1..254";
                                    }
                                    type enumeration {
                                        enum subnet-mask                    { value 1; }
                                        enum default-router                 { value 3; }
                                        enum dns-server                     { value 6; }
                                        enum domain-name                    { value 15; }
                                        enum netbios-name-server            { value 44; }
                                        enum netbios-node-type              { value 46; }
                                        enum lease-time                     { value 51; }
                                        enum lease-renew-time               { value 58; }
                                        enum lease-rebind-time              { value 59; }
                                    }
                                }
                                description "DHCP option to send identification strings to client";
                            }

                            ///nokia-conf/configure/subscriber-mgmt/local-user-db/ppp/host/ipv4/option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ppp/host/ipv4/option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ppp/host/ipv4/option/value
                            choice value {
                                mandatory true;
                                description "The value of the DHCP option.";
                                ///nokia-conf/configure/subscriber-mgmt/local-user-db/ppp/host/ipv4/option/value/ascii-string
                                case ascii-string {

                                    ///nokia-conf/configure/subscriber-mgmt/local-user-db/ppp/host/ipv4/option/value/ascii-string/ascii-string
                                    leaf ascii-string {
                                        when "(not(../number = 46) and not(../number = 'netbios-node-type')) and (not(../number = 51) and not(../number = 'lease-time')) and (not(../number = 58) and not(../number = 'lease-renew-time')) and (not(../number = 59) and not(../number = 'lease-rebind-time'))" {
                                            description "ascii-string is supported only when the option is neither netbios-node-type(46), lease-time(51), lease-renew-time(58) nor lease-rebind-time(59)";
                                        }
                                        type types-sros:string-not-all-spaces {
                                            length "1..127";
                                        }
                                        description "DHCP option specified as an ASCII string";
                                    }

                                }
                                ///nokia-conf/configure/subscriber-mgmt/local-user-db/ppp/host/ipv4/option/value/hex-string
                                case hex-string {

                                    ///nokia-conf/configure/subscriber-mgmt/local-user-db/ppp/host/ipv4/option/value/hex-string/hex-string
                                    leaf hex-string {
                                        when "(not(../number = 46) and not(../number = 'netbios-node-type')) and (not(../number = 51) and not(../number = 'lease-time')) and (not(../number = 58) and not(../number = 'lease-renew-time')) and (not(../number = 59) and not(../number = 'lease-rebind-time'))" {
                                            description "hex-string is supported only when the option is neither netbios-node-type(46), lease-time(51), lease-renew-time(58) nor lease-rebind-time(59)";
                                        }
                                        type types-sros:hex-string {
                                            length "1..256";
                                        }
                                        description "DHCP option specified as hexadecimal string";
                                    }

                                }
                                ///nokia-conf/configure/subscriber-mgmt/local-user-db/ppp/host/ipv4/option/value/netbios-node-type
                                case netbios-node-type {

                                    ///nokia-conf/configure/subscriber-mgmt/local-user-db/ppp/host/ipv4/option/value/netbios-node-type/netbios-node-type
                                    leaf netbios-node-type {
                                        when "../number = 46 or ../number = 'netbios-node-type'" {
                                            description "netbios-node-type is supported only when the option is netbios-node-type(46)";
                                        }
                                        type enumeration {
                                            enum b-node                         { value 1; }
                                            enum p-node                         { value 2; }
                                            enum m-node                         { value 4; }
                                            enum h-node                         { value 8; }
                                        }
                                        description "DHCP option as NetBIOS node type";
                                    }

                                }
                                ///nokia-conf/configure/subscriber-mgmt/local-user-db/ppp/host/ipv4/option/value/duration
                                case duration {

                                    ///nokia-conf/configure/subscriber-mgmt/local-user-db/ppp/host/ipv4/option/value/duration/duration
                                    leaf duration {
                                        when "../number = 51 or ../number = 'lease-time' or ../number = 58 or ../number = 'lease-renew-time' or ../number = 59 or ../number = 'lease-rebind-time'" {
                                            description "duration is supported only when the option is either lease-time(51), lease-renew-time(58) or lease-rebind-time(59)";
                                        }
                                        type types-sros:time-duration {
                                            range "10..315446399";
                                        }
                                        units "seconds";
                                        description "DHCP option as time duration";
                                    }

                                }
                                ///nokia-conf/configure/subscriber-mgmt/local-user-db/ppp/host/ipv4/option/value/ipv4-address
                                case ipv4-address {

                                    ///nokia-conf/configure/subscriber-mgmt/local-user-db/ppp/host/ipv4/option/value/ipv4-address/ipv4-address
                                    leaf-list ipv4-address {
                                        when "(not(../number = 46) and not(../number = 'netbios-node-type')) and (not(../number = 51) and not(../number = 'lease-time')) and (not(../number = 58) and not(../number = 'lease-renew-time')) and (not(../number = 59) and not(../number = 'lease-rebind-time'))" {
                                            description "ipv4-address is supported only when the option is neither netbios-node-type(46), lease-time(51), lease-renew-time(58) nor lease-rebind-time(59)";
                                        }
                                        type types-sros:ipv4-address;
                                        max-elements 4;
                                        ordered-by user;
                                        description "DHCP option as a list of IPv4 addresses";
                                    }

                                }
                                ///nokia-conf/configure/subscriber-mgmt/local-user-db/ppp/host/ipv4/option/value/empty
                                case empty {

                                    ///nokia-conf/configure/subscriber-mgmt/local-user-db/ppp/host/ipv4/option/value/empty/empty
                                    leaf empty {
                                        when "(not(../number = 46) and not(../number = 'netbios-node-type')) and (not(../number = 51) and not(../number = 'lease-time')) and (not(../number = 58) and not(../number = 'lease-renew-time')) and (not(../number = 59) and not(../number = 'lease-rebind-time'))" {
                                            description "empty is supported only when the option is neither netbios-node-type(46), lease-time(51), lease-renew-time(58) nor lease-rebind-time(59)";
                                        }
                                        type empty;
                                        description "Empty DHCP option.";
                                    }

                                }
                            }
                        } // list option

                    } // container ipv4

                    ///nokia-conf/configure/subscriber-mgmt/local-user-db/ppp/host/ipv6
                    container ipv6 {
                        description "Enter the ipv6 context";

                        ///nokia-conf/configure/subscriber-mgmt/local-user-db/ppp/host/ipv6/address
                        leaf address {
                            type types-sros:ipv6-unicast-address;
                            description "Fixed IPv6 address of the host";
                        }

                        ///nokia-conf/configure/subscriber-mgmt/local-user-db/ppp/host/ipv6/address-pool
                        leaf address-pool {
                            type types-sros:named-item;
                            description "IPv6 address pool name";
                        }

                        ///nokia-conf/configure/subscriber-mgmt/local-user-db/ppp/host/ipv6/delegated-prefix
                        leaf delegated-prefix {
                            type types-sros:ipv6-unicast-prefix;
                            description "IPv6 delegated prefix of this host";
                        }

                        ///nokia-conf/configure/subscriber-mgmt/local-user-db/ppp/host/ipv6/delegated-prefix-length
                        leaf delegated-prefix-length {
                            type uint32 {
                                range "48..64";
                            }
                            description "Delegated prefix length";
                        }

                        ///nokia-conf/configure/subscriber-mgmt/local-user-db/ppp/host/ipv6/delegated-prefix-pool
                        leaf delegated-prefix-pool {
                            type types-sros:named-item;
                            description "Delegated prefix pool";
                        }

                        ///nokia-conf/configure/subscriber-mgmt/local-user-db/ppp/host/ipv6/slaac-prefix
                        leaf slaac-prefix {
                            type types-sros:ipv6-unicast-prefix;
                            description "IPv6 SLAAC prefix of this host";
                        }

                        ///nokia-conf/configure/subscriber-mgmt/local-user-db/ppp/host/ipv6/slaac-prefix-pool
                        leaf slaac-prefix-pool {
                            type types-sros:named-item;
                            description "IPv6 SLAAC prefix pool of this host";
                        }

                        ///nokia-conf/configure/subscriber-mgmt/local-user-db/ppp/host/ipv6/router-advertisement-policy
                        leaf router-advertisement-policy {
                            type types-sros:named-item;
                            description "IPv6 router advertisement policy";
                        }

                        ///nokia-conf/configure/subscriber-mgmt/local-user-db/ppp/host/ipv6/force-ipv6cp
                        leaf force-ipv6cp {
                            type boolean;
                            default "false";
                            description "Force IPv6 control protocol";
                        }

                        ///nokia-conf/configure/subscriber-mgmt/local-user-db/ppp/host/ipv6/timers
                        container timers {
                            description "Enter the timers context";

                            ///nokia-conf/configure/subscriber-mgmt/local-user-db/ppp/host/ipv6/timers/preferred-lifetime
                            leaf preferred-lifetime {
                                type union {
                                    type types-sros:time-duration {
                                        range "300..315446399";
                                    }
                                    type enumeration {
                                        enum infinite                       { value -1; }
                                    }
                                }
                                units "seconds";
                                description "Time for a lease to remain preferred";
                            }

                            ///nokia-conf/configure/subscriber-mgmt/local-user-db/ppp/host/ipv6/timers/rebind
                            leaf rebind {
                                type types-sros:time-duration {
                                    range "0..1209600";
                                }
                                units "seconds";
                                description "Rebind timer (T2)";
                            }

                            ///nokia-conf/configure/subscriber-mgmt/local-user-db/ppp/host/ipv6/timers/renew
                            leaf renew {
                                type types-sros:time-duration {
                                    range "0..604800";
                                }
                                units "seconds";
                                description "Renew timer (T1)";
                            }

                            ///nokia-conf/configure/subscriber-mgmt/local-user-db/ppp/host/ipv6/timers/valid-lifetime
                            leaf valid-lifetime {
                                type union {
                                    type types-sros:time-duration {
                                        range "300..315446399";
                                    }
                                    type enumeration {
                                        enum infinite                       { value -1; }
                                    }
                                }
                                units "seconds";
                                description "Time for a lease to remain valid";
                            }

                        } // container timers

                        ///nokia-conf/configure/subscriber-mgmt/local-user-db/ppp/host/ipv6/option
                        list option {
                            key "number";
                            description "Enter the option list instance";

                            ///nokia-conf/configure/subscriber-mgmt/local-user-db/ppp/host/ipv6/option/number
                            leaf number {
                                type union {
                                    type uint32 {
                                        range "23";
                                    }
                                    type enumeration {
                                        enum dns-server                     { value 23; }
                                    }
                                }
                                description "The number of the DHCPv6 option.";
                            }

                            ///nokia-conf/configure/subscriber-mgmt/local-user-db/ppp/host/ipv6/option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ppp/host/ipv6/option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ppp/host/ipv6/option/value
                            choice value {
                                mandatory true;
                                description "The value of the DHCP option.";
                                ///nokia-conf/configure/subscriber-mgmt/local-user-db/ppp/host/ipv6/option/value/hex-string
                                case hex-string {

                                    ///nokia-conf/configure/subscriber-mgmt/local-user-db/ppp/host/ipv6/option/value/hex-string/hex-string
                                    leaf hex-string {
                                        type types-sros:hex-string {
                                            length "1..256";
                                        }
                                        description "DHCP option specified as hexadecimal string";
                                    }

                                }
                                ///nokia-conf/configure/subscriber-mgmt/local-user-db/ppp/host/ipv6/option/value/ipv6-address
                                case ipv6-address {

                                    ///nokia-conf/configure/subscriber-mgmt/local-user-db/ppp/host/ipv6/option/value/ipv6-address/ipv6-address
                                    leaf-list ipv6-address {
                                        type types-sros:ipv6-address;
                                        max-elements 4;
                                        ordered-by user;
                                        description "DHCP option specified as a list of IPv6 addresses";
                                    }

                                }
                            }
                        } // list option

                    } // container ipv6

                    ///nokia-conf/configure/subscriber-mgmt/local-user-db/ppp/host/mld-import
                    list mld-import {
                        key "policy-name";
                        max-elements 14;
                        description "Add a list entry for mld-import";

                        ///nokia-conf/configure/subscriber-mgmt/local-user-db/ppp/host/mld-import/policy-name
                        leaf policy-name {
                            type types-sros:named-item;
                            description "MLD import policy used to control the multicast group";
                        }

                    } // list mld-import

                    ///nokia-conf/configure/subscriber-mgmt/local-user-db/ppp/host/ppp-policy-parameters
                    container ppp-policy-parameters {
                        description "Enter the ppp-policy-parameters context";

                        ///nokia-conf/configure/subscriber-mgmt/local-user-db/ppp/host/ppp-policy-parameters/max-sessions-per-mac
                        leaf max-sessions-per-mac {
                            type uint32 {
                                range "1..8191";
                            }
                            description "Maximum number of sessions per MAC address";
                        }

                        ///nokia-conf/configure/subscriber-mgmt/local-user-db/ppp/host/ppp-policy-parameters/keepalive
                        container keepalive {
                            presence "Enable the keepalive context";
                            description "Enable the keepalive context";

                            ///nokia-conf/configure/subscriber-mgmt/local-user-db/ppp/host/ppp-policy-parameters/keepalive/hold-up-multiplier
                            leaf hold-up-multiplier {
                                type uint32 {
                                    range "1..5";
                                }
                                default "3";
                                description "PPP LCP keepalive hold up multiplier override";
                            }

                            ///nokia-conf/configure/subscriber-mgmt/local-user-db/ppp/host/ppp-policy-parameters/keepalive/interval
                            leaf interval {
                                type types-sros:time-duration {
                                    range "4..300";
                                }
                                units "seconds";
                                default "30";
                                description "PPP LCP keepalive interval override";
                            }

                        } // container keepalive

                    } // container ppp-policy-parameters

                    ///nokia-conf/configure/subscriber-mgmt/local-user-db/ppp/host/to-client-options
                    container to-client-options {
                        description "Enter the to-client-options context";

                        ///nokia-conf/configure/subscriber-mgmt/local-user-db/ppp/host/to-client-options/ipv6-option
                        list ipv6-option {
                            key "number";
                            description "Enter the ipv6-option list instance";

                            ///nokia-conf/configure/subscriber-mgmt/local-user-db/ppp/host/to-client-options/ipv6-option/number
                            leaf number {
                                type union {
                                    type uint32 {
                                        range "1..65535";
                                    }
                                    type enumeration {
                                        enum dns-server                     { value 23; }
                                        enum domain-name                    { value 24; }
                                    }
                                }
                                description "DHCP option to send as identification string";
                            }

                            ///nokia-conf/configure/subscriber-mgmt/local-user-db/ppp/host/to-client-options/ipv6-option/apply-groups
                            leaf-list apply-groups {
                                type leafref {
                                    path "../../../../../../../groups/group/name";
                                }
                                max-elements 8;
                                ordered-by user;
                                description "Apply a configuration group at this level";
                            }

                            ///nokia-conf/configure/subscriber-mgmt/local-user-db/ppp/host/to-client-options/ipv6-option/apply-groups-exclude
                            leaf-list apply-groups-exclude {
                                type leafref {
                                    path "../../../../../../../groups/group/name";
                                }
                                max-elements 8;
                                ordered-by user;
                                description "Exclude a configuration group at this level";
                            }

                            ///nokia-conf/configure/subscriber-mgmt/local-user-db/ppp/host/to-client-options/ipv6-option/value
                            choice value {
                                mandatory true;
                                description "The value of the DHCP option.";
                                ///nokia-conf/configure/subscriber-mgmt/local-user-db/ppp/host/to-client-options/ipv6-option/value/ascii-string
                                case ascii-string {

                                    ///nokia-conf/configure/subscriber-mgmt/local-user-db/ppp/host/to-client-options/ipv6-option/value/ascii-string/ascii-string
                                    leaf ascii-string {
                                        type types-sros:string-not-all-spaces {
                                            length "1..127";
                                        }
                                        description "DHCP option specified as an ASCII string";
                                    }

                                }
                                ///nokia-conf/configure/subscriber-mgmt/local-user-db/ppp/host/to-client-options/ipv6-option/value/hex-string
                                case hex-string {

                                    ///nokia-conf/configure/subscriber-mgmt/local-user-db/ppp/host/to-client-options/ipv6-option/value/hex-string/hex-string
                                    leaf hex-string {
                                        type types-sros:hex-string {
                                            length "1..256";
                                        }
                                        description "DHCP option specified as hexadecimal string";
                                    }

                                }
                                ///nokia-conf/configure/subscriber-mgmt/local-user-db/ppp/host/to-client-options/ipv6-option/value/domain-string
                                case domain-string {

                                    ///nokia-conf/configure/subscriber-mgmt/local-user-db/ppp/host/to-client-options/ipv6-option/value/domain-string/domain-string
                                    leaf domain-string {
                                        type string {
                                            length "1..127";
                                            pattern "[a-z0-9\\-]+(\\.[a-z0-9\\-]+)*";
                                        }
                                        description "DHCP option specified as a domain name";
                                    }

                                }
                                ///nokia-conf/configure/subscriber-mgmt/local-user-db/ppp/host/to-client-options/ipv6-option/value/ipv6-address
                                case ipv6-address {

                                    ///nokia-conf/configure/subscriber-mgmt/local-user-db/ppp/host/to-client-options/ipv6-option/value/ipv6-address/ipv6-address
                                    leaf-list ipv6-address {
                                        type types-sros:ipv6-address;
                                        max-elements 4;
                                        ordered-by user;
                                        description "DHCP option specified as a list of IPv6 addresses";
                                    }

                                }
                                ///nokia-conf/configure/subscriber-mgmt/local-user-db/ppp/host/to-client-options/ipv6-option/value/empty
                                case empty {

                                    ///nokia-conf/configure/subscriber-mgmt/local-user-db/ppp/host/to-client-options/ipv6-option/value/empty/empty
                                    leaf empty {
                                        type empty;
                                        description "Empty DHCP option";
                                    }

                                }
                            }
                        } // list ipv6-option

                    } // container to-client-options

                } // list host

            } // container ppp

        } // list local-user-db

    } // grouping conf-submgt-local-user-db

}
