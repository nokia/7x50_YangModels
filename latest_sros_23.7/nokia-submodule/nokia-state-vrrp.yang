submodule nokia-state-vrrp {

    yang-version "1.1";

    belongs-to nokia-state { prefix "state"; }

    import ietf-yang-types                { prefix "yang"; }
    import nokia-sros-yang-extensions     { prefix "sros-ext"; }
    import nokia-types-sros               { prefix "types-sros"; }
    import nokia-types-vrrp               { prefix "types-vrrp"; }

    sros-ext:sros-major-release "rel23";
    organization "Nokia";
    contact
        "Nokia SR OS Support
         Web: <http://www.nokia.com>";
    description
        "Nokia YANG Data model with operational state for VRRP policy options on SR OS based routers.

         Copyright 2016 Nokia. All rights reserved. Reproduction of this document
         is authorized on the condition that the foregoing copyright notice is included.

         This nokia-state-vrrp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-11-16";

    grouping state-vrrp {
        ///nokia-state/state/vrrp
        container vrrp {
            description "Enable the vrrp context";

            ///nokia-state/state/vrrp/policy
            list policy {
                key "policy-id";
                description "Enter the policy list instance";

                ///nokia-state/state/vrrp/policy/policy-id
                leaf policy-id {
                    type uint32 {
                        range "1..9999";
                    }
                    description "Policy ID";
                }

                ///nokia-state/state/vrrp/policy/reference-count
                leaf reference-count {
                    type union {
                        type enumeration {
                            enum not-applied                    { value 0; }
                        }
                        type uint32 {
                            range "1..max";
                        }
                    }
                    description
                        "The value indicates the number of VRRPs to which the policy has been applied.
                         The policy cannot be deleted unless this value is 0.";
                }

                ///nokia-state/state/vrrp/policy/current-explicit-priority
                leaf current-explicit-priority {
                    type union {
                        type uint32 {
                            range "0..254";
                        }
                        type enumeration {
                            enum none                           { value 255; }
                        }
                    }
                    description
                        "When multiple explicitly defined events associated with the
                         priority control policy happen simultaneously, the lowest value
                         of all the current explicit priorities will be used as the
                         in-use priority for the virtual router.";
                }

                ///nokia-state/state/vrrp/policy/current-delta-sum
                leaf current-delta-sum {
                    type union {
                        type types-vrrp:priority;
                        type enumeration {
                            enum none                           { value 0; }
                        }
                    }
                    description
                        "When multiple delta events associated with the priority control
                         policy happen simultaneously, the sum of the priorities of all
                         these delta events is specified by the variable current-delta-sum.
                         This sum is subtracted from the base priority of the virtual router
                         to give the in-use priority.";
                }

                ///nokia-state/state/vrrp/policy/priority-event
                container priority-event {
                    description "Enter the priority-event context";

                    ///nokia-state/state/vrrp/policy/priority-event/host-unreachable
                    list host-unreachable {
                        key "ip-address";
                        description "Enter the host-unreachable list instance";

                        ///nokia-state/state/vrrp/policy/priority-event/host-unreachable/ip-address
                        leaf ip-address {
                            type types-sros:ip-address-with-zone;
                            description "Host IP address that receives a constant ping probe";
                        }

                        ///nokia-state/state/vrrp/policy/priority-event/host-unreachable/last-transition
                        leaf last-transition {
                            type yang:date-and-time;
                            description
                                "The value indicates the sysUpTime when the operational state of the
                                 event last changed.";
                        }

                        ///nokia-state/state/vrrp/policy/priority-event/host-unreachable/event-in-use
                        leaf event-in-use {
                            type boolean;
                            description
                                "If value is 'true', then the event is currently affecting the in-use priority
                                 of some virtual router.";
                        }

                        ///nokia-state/state/vrrp/policy/priority-event/host-unreachable/hold-set-remaining
                        leaf hold-set-remaining {
                            type types-vrrp:event-hold-state;
                            units "seconds";
                            description
                                "The value indicates the current value of the hold-set timer i.e. the
                                 amount of time remaining before the event will transition
                                 into the cleared state.";
                        }

                        ///nokia-state/state/vrrp/policy/priority-event/host-unreachable/hold-clear-remaining
                        leaf hold-clear-remaining {
                            type types-vrrp:event-hold-state;
                            units "seconds";
                            description
                                "The value indicates the current value of the hold-clear timer i.e. the
                                 amount of time remaining before the cleared event will have
                                 an effect on the VRRP.";
                        }

                        ///nokia-state/state/vrrp/policy/priority-event/host-unreachable/oper-state
                        leaf oper-state {
                            type types-vrrp:host-unreachable-event-oper-state;
                            description "The value indicates the current operational state of the event.";
                        }

                        ///nokia-state/state/vrrp/policy/priority-event/host-unreachable/previous-state
                        leaf previous-state {
                            type types-vrrp:host-unreachable-event-oper-state;
                            description "The value indicates the previous operational state of the event.";
                        }

                        ///nokia-state/state/vrrp/policy/priority-event/host-unreachable/statistics
                        container statistics {
                            description "Enter the statistics context";

                            ///nokia-state/state/vrrp/policy/priority-event/host-unreachable/statistics/set-counter
                            leaf set-counter {
                                type yang:counter32;
                                description
                                    "The value indicates the number of times the event has transitioned to one of the
                                     'set' states.";
                            }

                        } // container statistics

                    } // list host-unreachable

                    ///nokia-state/state/vrrp/policy/priority-event/lag-port-down
                    list lag-port-down {
                        key "lag-name";
                        description "Enter the lag-port-down list instance";

                        ///nokia-state/state/vrrp/policy/priority-event/lag-port-down/lag-name
                        leaf lag-name {
                            type types-sros:lag-interface;
                            description "LAG name";
                        }

                        ///nokia-state/state/vrrp/policy/priority-event/lag-port-down/last-transition
                        leaf last-transition {
                            type yang:date-and-time;
                            description
                                "The value indicates the sysUpTime when the operational state of the
                                 event last changed.";
                        }

                        ///nokia-state/state/vrrp/policy/priority-event/lag-port-down/event-in-use
                        leaf event-in-use {
                            type boolean;
                            description
                                "If value is 'true', then the event is currently affecting the in-use priority
                                 of some virtual router.";
                        }

                        ///nokia-state/state/vrrp/policy/priority-event/lag-port-down/hold-set-remaining
                        leaf hold-set-remaining {
                            type types-vrrp:event-hold-state;
                            units "seconds";
                            description
                                "The value indicates the current value of the hold-set timer i.e. the
                                 amount of time remaining before the event will transition
                                 into the cleared state.";
                        }

                        ///nokia-state/state/vrrp/policy/priority-event/lag-port-down/hold-clear-remaining
                        leaf hold-clear-remaining {
                            type types-vrrp:event-hold-state;
                            units "seconds";
                            description
                                "The value indicates the current value of the hold-clear timer i.e. the
                                 amount of time remaining before the cleared event will have
                                 an effect on the VRRP.";
                        }

                        ///nokia-state/state/vrrp/policy/priority-event/lag-port-down/oper-state
                        leaf oper-state {
                            type types-vrrp:port-down-oper-state;
                            description "The value indicates the current operational state of the event.";
                        }

                        ///nokia-state/state/vrrp/policy/priority-event/lag-port-down/oper-state-lag-down-ports-count
                        leaf oper-state-lag-down-ports-count {
                            type uint8 {
                                range "0..65";
                            }
                            description "The value indicates count of down ports in lag of current operational state.";
                        }

                        ///nokia-state/state/vrrp/policy/priority-event/lag-port-down/previous-state
                        leaf previous-state {
                            type types-vrrp:port-down-oper-state;
                            description "The value indicates the previous operational state of the event.";
                        }

                        ///nokia-state/state/vrrp/policy/priority-event/lag-port-down/previous-state-lag-down-ports-count
                        leaf previous-state-lag-down-ports-count {
                            type uint8 {
                                range "0..65";
                            }
                            description "The value indicates count of down ports in lag of previous operational state.";
                        }

                        ///nokia-state/state/vrrp/policy/priority-event/lag-port-down/statistics
                        container statistics {
                            description "Enter the statistics context";

                            ///nokia-state/state/vrrp/policy/priority-event/lag-port-down/statistics/set-counter
                            leaf set-counter {
                                type yang:counter32;
                                description
                                    "The value indicates the number of times the event has transitioned to one of the
                                     'set' states.";
                            }

                        } // container statistics

                    } // list lag-port-down

                    ///nokia-state/state/vrrp/policy/priority-event/mc-ipsec-non-forwarding
                    list mc-ipsec-non-forwarding {
                        key "tunnel-group-id";
                        description "Enter the mc-ipsec-non-forwarding list instance";

                        ///nokia-state/state/vrrp/policy/priority-event/mc-ipsec-non-forwarding/tunnel-group-id
                        leaf tunnel-group-id {
                            type uint32 {
                                range "1..64";
                            }
                            description "IPSEC tunnel group monitored by priority control event";
                        }

                        ///nokia-state/state/vrrp/policy/priority-event/mc-ipsec-non-forwarding/last-transition
                        leaf last-transition {
                            type yang:date-and-time;
                            description
                                "The value indicates the sysUpTime when the operational state of the
                                 event last changed.";
                        }

                        ///nokia-state/state/vrrp/policy/priority-event/mc-ipsec-non-forwarding/event-in-use
                        leaf event-in-use {
                            type boolean;
                            description
                                "If value is 'true', then the event is currently affecting the in-use priority
                                 of some virtual router.";
                        }

                        ///nokia-state/state/vrrp/policy/priority-event/mc-ipsec-non-forwarding/hold-set-remaining
                        leaf hold-set-remaining {
                            type types-vrrp:event-hold-state;
                            units "seconds";
                            description
                                "The value indicates the current value of the hold-set timer i.e. the
                                 amount of time remaining before the event will transition
                                 into the cleared state.";
                        }

                        ///nokia-state/state/vrrp/policy/priority-event/mc-ipsec-non-forwarding/hold-clear-remaining
                        leaf hold-clear-remaining {
                            type types-vrrp:event-hold-state;
                            units "seconds";
                            description
                                "The value indicates the current value of the hold-clear timer i.e. the
                                 amount of time remaining before the cleared event will have
                                 an effect on the VRRP.";
                        }

                        ///nokia-state/state/vrrp/policy/priority-event/mc-ipsec-non-forwarding/oper-state
                        leaf oper-state {
                            type types-vrrp:ip-sec-no-forwarding-oper-state;
                            description "The value indicates the current operational state of the event.";
                        }

                        ///nokia-state/state/vrrp/policy/priority-event/mc-ipsec-non-forwarding/previous-state
                        leaf previous-state {
                            type types-vrrp:ip-sec-no-forwarding-oper-state;
                            description "The value indicates the previous operational state of the event.";
                        }

                        ///nokia-state/state/vrrp/policy/priority-event/mc-ipsec-non-forwarding/statistics
                        container statistics {
                            description "Enter the statistics context";

                            ///nokia-state/state/vrrp/policy/priority-event/mc-ipsec-non-forwarding/statistics/set-counter
                            leaf set-counter {
                                type yang:counter32;
                                description
                                    "The value indicates the number of times the event has transitioned to one of the
                                     'set' states.";
                            }

                        } // container statistics

                    } // list mc-ipsec-non-forwarding

                    ///nokia-state/state/vrrp/policy/priority-event/port-down
                    list port-down {
                        key "port-id";
                        description "Enter the port-down list instance";

                        ///nokia-state/state/vrrp/policy/priority-event/port-down/port-id
                        leaf port-id {
                            type types-sros:port-named;
                            description "Port ID for the reduced LAG ports";
                        }

                        ///nokia-state/state/vrrp/policy/priority-event/port-down/last-transition
                        leaf last-transition {
                            type yang:date-and-time;
                            description
                                "The value indicates the sysUpTime when the operational state of the
                                 event last changed.";
                        }

                        ///nokia-state/state/vrrp/policy/priority-event/port-down/event-in-use
                        leaf event-in-use {
                            type boolean;
                            description
                                "If value is 'true', then the event is currently affecting the in-use priority
                                 of some virtual router.";
                        }

                        ///nokia-state/state/vrrp/policy/priority-event/port-down/hold-set-remaining
                        leaf hold-set-remaining {
                            type types-vrrp:event-hold-state;
                            units "seconds";
                            description
                                "The value indicates the current value of the hold-set timer i.e. the
                                 amount of time remaining before the event will transition
                                 into the cleared state.";
                        }

                        ///nokia-state/state/vrrp/policy/priority-event/port-down/hold-clear-remaining
                        leaf hold-clear-remaining {
                            type types-vrrp:event-hold-state;
                            units "seconds";
                            description
                                "The value indicates the current value of the hold-clear timer i.e. the
                                 amount of time remaining before the cleared event will have
                                 an effect on the VRRP.";
                        }

                        ///nokia-state/state/vrrp/policy/priority-event/port-down/oper-state
                        leaf oper-state {
                            type types-vrrp:port-down-event-oper-state;
                            description "The value indicates the current operational state of the event.";
                        }

                        ///nokia-state/state/vrrp/policy/priority-event/port-down/previous-state
                        leaf previous-state {
                            type types-vrrp:port-down-event-oper-state;
                            description "The value indicates the previous operational state of the event.";
                        }

                        ///nokia-state/state/vrrp/policy/priority-event/port-down/statistics
                        container statistics {
                            description "Enter the statistics context";

                            ///nokia-state/state/vrrp/policy/priority-event/port-down/statistics/set-counter
                            leaf set-counter {
                                type yang:counter32;
                                description
                                    "The value indicates the number of times the event has transitioned to one of the
                                     'set' states.";
                            }

                        } // container statistics

                    } // list port-down

                    ///nokia-state/state/vrrp/policy/priority-event/route-unknown
                    list route-unknown {
                        key "ip-prefix";
                        description "Enter the route-unknown list instance";

                        ///nokia-state/state/vrrp/policy/priority-event/route-unknown/ip-prefix
                        leaf ip-prefix {
                            type types-sros:ip-prefix;
                            description "IP prefix of route monitored by priority control event";
                        }

                        ///nokia-state/state/vrrp/policy/priority-event/route-unknown/last-transition
                        leaf last-transition {
                            type yang:date-and-time;
                            description
                                "The value indicates the sysUpTime when the operational state of the
                                 event last changed.";
                        }

                        ///nokia-state/state/vrrp/policy/priority-event/route-unknown/event-in-use
                        leaf event-in-use {
                            type boolean;
                            description
                                "If value is 'true', then the event is currently affecting the in-use priority
                                 of some virtual router.";
                        }

                        ///nokia-state/state/vrrp/policy/priority-event/route-unknown/hold-set-remaining
                        leaf hold-set-remaining {
                            type types-vrrp:event-hold-state;
                            units "seconds";
                            description
                                "The value indicates the current value of the hold-set timer i.e. the
                                 amount of time remaining before the event will transition
                                 into the cleared state.";
                        }

                        ///nokia-state/state/vrrp/policy/priority-event/route-unknown/hold-clear-remaining
                        leaf hold-clear-remaining {
                            type types-vrrp:event-hold-state;
                            units "seconds";
                            description
                                "The value indicates the current value of the hold-clear timer i.e. the
                                 amount of time remaining before the cleared event will have
                                 an effect on the VRRP.";
                        }

                        ///nokia-state/state/vrrp/policy/priority-event/route-unknown/oper-state
                        leaf oper-state {
                            type types-vrrp:route-unknown-event-oper-state;
                            description "The value indicates the current operational state of the event.";
                        }

                        ///nokia-state/state/vrrp/policy/priority-event/route-unknown/previous-state
                        leaf previous-state {
                            type types-vrrp:route-unknown-event-oper-state;
                            description "The value indicates the previous operational state of the event.";
                        }

                        ///nokia-state/state/vrrp/policy/priority-event/route-unknown/statistics
                        container statistics {
                            description "Enter the statistics context";

                            ///nokia-state/state/vrrp/policy/priority-event/route-unknown/statistics/set-counter
                            leaf set-counter {
                                type yang:counter32;
                                description
                                    "The value indicates the number of times the event has transitioned to one of the
                                     'set' states.";
                            }

                        } // container statistics

                    } // list route-unknown

                } // container priority-event

            } // list policy

        } // container vrrp

    } // grouping state-vrrp

}
