submodule nokia-conf-system-security-cpm {

    yang-version "1.1";

    belongs-to nokia-conf { prefix "conf"; }

    import ietf-yang-types                { prefix "yang"; }
    import nokia-sros-yang-extensions     { prefix "sros-ext"; }
    import nokia-types-filter             { prefix "types-filter"; }
    import nokia-types-qos                { prefix "types-qos"; }
    import nokia-types-security           { prefix "types-security"; }
    import nokia-types-services           { prefix "types-services"; }
    import nokia-types-sros               { prefix "types-sros"; }
    import nokia-types-system             { prefix "types-system"; }

    include nokia-conf-filter;
    include nokia-conf-groups;
    include nokia-conf-service;
    include nokia-conf-svc-vpls;

    sros-ext:sros-major-release "rel23";
    organization "Nokia";
    contact
        "Nokia SR OS Support
         Web: <http://www.nokia.com>";
    description
        "Nokia YANG Data model to configure System security cpm-filter and cpm-queue configuration. on SR OS based routers.

         Copyright 2016 Nokia. All rights reserved. Reproduction of this document
         is authorized on the condition that the foregoing copyright notice is included.

         This nokia-conf-system-security-cpm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-07";

    grouping conf-system-security-cpm-cpm-filter {
        ///nokia-conf/configure/system/security/cpm-filter
        container cpm-filter {
            description "Enter the cpm-filter context";

            ///nokia-conf/configure/system/security/cpm-filter/default-action
            leaf default-action {
                type enumeration {
                    enum drop                           { value 1; }
                    enum accept                         { value 2; }
                }
                default "accept";
                description "Action for packets that do not match any filter entries";
            }

            ///nokia-conf/configure/system/security/cpm-filter/apply-groups
            leaf-list apply-groups {
                type leafref {
                    path "../../../../groups/group/name";
                }
                max-elements 8;
                ordered-by user;
                description "Apply a configuration group at this level";
            }

            ///nokia-conf/configure/system/security/cpm-filter/apply-groups-exclude
            leaf-list apply-groups-exclude {
                type leafref {
                    path "../../../../groups/group/name";
                }
                max-elements 8;
                ordered-by user;
                description "Exclude a configuration group at this level";
            }

            ///nokia-conf/configure/system/security/cpm-filter/ip-filter
            container ip-filter {
                description "Enter the ip-filter context";

                ///nokia-conf/configure/system/security/cpm-filter/ip-filter/admin-state
                leaf admin-state {
                    type types-sros:admin-state;
                    default "disable";
                    description "Administrative state of the CPM filter";
                }

                ///nokia-conf/configure/system/security/cpm-filter/ip-filter/entry
                list entry {
                    key "entry-id";
                    description "Enter the entry list instance";

                    ///nokia-conf/configure/system/security/cpm-filter/ip-filter/entry/entry-id
                    leaf entry-id {
                        type uint32 {
                            range "1..131072";
                        }
                        description "Filter entry ID";
                    }

                    ///nokia-conf/configure/system/security/cpm-filter/ip-filter/entry/description
                    leaf description {
                        type types-sros:description;
                        description "Text description";
                    }

                    ///nokia-conf/configure/system/security/cpm-filter/ip-filter/entry/log
                    leaf log {
                        type leafref {
                            path "../../../../../../filter/log/log-id";
                        }
                        description "Log ID where matching packets are entered";
                    }

                    ///nokia-conf/configure/system/security/cpm-filter/ip-filter/entry/apply-groups
                    leaf-list apply-groups {
                        type leafref {
                            path "../../../../../../groups/group/name";
                        }
                        max-elements 8;
                        ordered-by user;
                        description "Apply a configuration group at this level";
                    }

                    ///nokia-conf/configure/system/security/cpm-filter/ip-filter/entry/apply-groups-exclude
                    leaf-list apply-groups-exclude {
                        type leafref {
                            path "../../../../../../groups/group/name";
                        }
                        max-elements 8;
                        ordered-by user;
                        description "Exclude a configuration group at this level";
                    }

                    ///nokia-conf/configure/system/security/cpm-filter/ip-filter/entry/match
                    container match {
                        description "Enter the match context";

                        ///nokia-conf/configure/system/security/cpm-filter/ip-filter/entry/match/router-instance
                        leaf router-instance {
                            type types-sros:named-item-64;
                            description "Router instance as the match criteria";
                        }

                        ///nokia-conf/configure/system/security/cpm-filter/ip-filter/entry/match/protocol
                        leaf protocol {
                            type types-sros:match-ip-protocol;
                            description "IP protocol as the match criterion";
                        }

                        ///nokia-conf/configure/system/security/cpm-filter/ip-filter/entry/match/dscp
                        leaf dscp {
                            type types-qos:dscp-name;
                            description "DSCP used as the match criterion on the packet";
                        }

                        ///nokia-conf/configure/system/security/cpm-filter/ip-filter/entry/match/fragment
                        leaf fragment {
                            type enumeration {
                                enum false                          { value 2; }
                                enum true                           { value 3; }
                            }
                            description "Match criterion based on presence of fragmented packets";
                        }

                        ///nokia-conf/configure/system/security/cpm-filter/ip-filter/entry/match/multiple-option
                        leaf multiple-option {
                            type boolean;
                            description "Match on packets containing multiple option fields";
                        }

                        ///nokia-conf/configure/system/security/cpm-filter/ip-filter/entry/match/option-present
                        leaf option-present {
                            type boolean;
                            description "Match on packets with option field present";
                        }

                        ///nokia-conf/configure/system/security/cpm-filter/ip-filter/entry/match/port-selector
                        choice port-selector {
                            ///nokia-conf/configure/system/security/cpm-filter/ip-filter/entry/match/port-selector/src-dst-port
                            case src-dst-port {

                                ///nokia-conf/configure/system/security/cpm-filter/ip-filter/entry/match/port-selector/src-dst-port/src-port
                                container src-port {
                                    description "Enter the src-port context";

                                    ///nokia-conf/configure/system/security/cpm-filter/ip-filter/entry/match/port-selector/src-dst-port/src-port/port
                                    choice port {
                                        ///nokia-conf/configure/system/security/cpm-filter/ip-filter/entry/match/port-selector/src-dst-port/src-port/port/eq
                                        case eq {

                                            ///nokia-conf/configure/system/security/cpm-filter/ip-filter/entry/match/port-selector/src-dst-port/src-port/port/eq/eq
                                            leaf eq {
                                                type uint16 {
                                                    range "0..65535";
                                                }
                                                description "Port number as the match criterion";
                                            }

                                            ///nokia-conf/configure/system/security/cpm-filter/ip-filter/entry/match/port-selector/src-dst-port/src-port/port/eq/mask
                                            leaf mask {
                                                type uint16 {
                                                    range "1..65535";
                                                }
                                                default "65535";
                                                description "Port mask as the match criterion";
                                            }

                                        }
                                        ///nokia-conf/configure/system/security/cpm-filter/ip-filter/entry/match/port-selector/src-dst-port/src-port/port/range
                                        case range {

                                            ///nokia-conf/configure/system/security/cpm-filter/ip-filter/entry/match/port-selector/src-dst-port/src-port/port/range/range
                                            container range {
                                                presence "Enable the range context";
                                                description "Enable the range context";

                                                ///nokia-conf/configure/system/security/cpm-filter/ip-filter/entry/match/port-selector/src-dst-port/src-port/port/range/range/start
                                                leaf start {
                                                    type uint16 {
                                                        range "0..65535";
                                                    }
                                                    mandatory true;
                                                    description "Lower bound of the port number to match";
                                                }

                                                ///nokia-conf/configure/system/security/cpm-filter/ip-filter/entry/match/port-selector/src-dst-port/src-port/port/range/range/end
                                                leaf end {
                                                    type uint16 {
                                                        range "0..65535";
                                                    }
                                                    mandatory true;
                                                    description "Upper bound of the port number to match";
                                                }

                                            } // container range

                                        }
                                        ///nokia-conf/configure/system/security/cpm-filter/ip-filter/entry/match/port-selector/src-dst-port/src-port/port/port-list
                                        case port-list {

                                            ///nokia-conf/configure/system/security/cpm-filter/ip-filter/entry/match/port-selector/src-dst-port/src-port/port/port-list/port-list
                                            leaf port-list {
                                                type leafref {
                                                    path "../../../../../../../../filter/match-list/port-list/port-list-name";
                                                }
                                                description "Port list as the match criterion";
                                            }

                                        }
                                    }
                                } // container src-port

                                ///nokia-conf/configure/system/security/cpm-filter/ip-filter/entry/match/port-selector/src-dst-port/dst-port
                                container dst-port {
                                    description "Enter the dst-port context";

                                    ///nokia-conf/configure/system/security/cpm-filter/ip-filter/entry/match/port-selector/src-dst-port/dst-port/port
                                    choice port {
                                        ///nokia-conf/configure/system/security/cpm-filter/ip-filter/entry/match/port-selector/src-dst-port/dst-port/port/eq
                                        case eq {

                                            ///nokia-conf/configure/system/security/cpm-filter/ip-filter/entry/match/port-selector/src-dst-port/dst-port/port/eq/eq
                                            leaf eq {
                                                type uint16 {
                                                    range "0..65535";
                                                }
                                                description "Port number as the match criterion";
                                            }

                                            ///nokia-conf/configure/system/security/cpm-filter/ip-filter/entry/match/port-selector/src-dst-port/dst-port/port/eq/mask
                                            leaf mask {
                                                type uint16 {
                                                    range "1..65535";
                                                }
                                                default "65535";
                                                description "Port mask as the match criterion";
                                            }

                                        }
                                        ///nokia-conf/configure/system/security/cpm-filter/ip-filter/entry/match/port-selector/src-dst-port/dst-port/port/range
                                        case range {

                                            ///nokia-conf/configure/system/security/cpm-filter/ip-filter/entry/match/port-selector/src-dst-port/dst-port/port/range/range
                                            container range {
                                                presence "Enable the range context";
                                                description "Enable the range context";

                                                ///nokia-conf/configure/system/security/cpm-filter/ip-filter/entry/match/port-selector/src-dst-port/dst-port/port/range/range/start
                                                leaf start {
                                                    type uint16 {
                                                        range "0..65535";
                                                    }
                                                    mandatory true;
                                                    description "Lower bound of the port number to match";
                                                }

                                                ///nokia-conf/configure/system/security/cpm-filter/ip-filter/entry/match/port-selector/src-dst-port/dst-port/port/range/range/end
                                                leaf end {
                                                    type uint16 {
                                                        range "0..65535";
                                                    }
                                                    mandatory true;
                                                    description "Upper bound of the port number to match";
                                                }

                                            } // container range

                                        }
                                        ///nokia-conf/configure/system/security/cpm-filter/ip-filter/entry/match/port-selector/src-dst-port/dst-port/port/port-list
                                        case port-list {

                                            ///nokia-conf/configure/system/security/cpm-filter/ip-filter/entry/match/port-selector/src-dst-port/dst-port/port/port-list/port-list
                                            leaf port-list {
                                                type leafref {
                                                    path "../../../../../../../../filter/match-list/port-list/port-list-name";
                                                }
                                                description "Port list as the match criterion";
                                            }

                                        }
                                    }
                                } // container dst-port

                            }
                            ///nokia-conf/configure/system/security/cpm-filter/ip-filter/entry/match/port-selector/port
                            case port {

                                ///nokia-conf/configure/system/security/cpm-filter/ip-filter/entry/match/port-selector/port/port
                                container port {
                                    description "Enter the port context";

                                    ///nokia-conf/configure/system/security/cpm-filter/ip-filter/entry/match/port-selector/port/port/port
                                    choice port {
                                        ///nokia-conf/configure/system/security/cpm-filter/ip-filter/entry/match/port-selector/port/port/port/eq
                                        case eq {

                                            ///nokia-conf/configure/system/security/cpm-filter/ip-filter/entry/match/port-selector/port/port/port/eq/eq
                                            leaf eq {
                                                type uint16 {
                                                    range "0..65535";
                                                }
                                                description "Port number as the match criterion";
                                            }

                                            ///nokia-conf/configure/system/security/cpm-filter/ip-filter/entry/match/port-selector/port/port/port/eq/mask
                                            leaf mask {
                                                type uint16 {
                                                    range "1..65535";
                                                }
                                                default "65535";
                                                description "Port mask as the match criterion";
                                            }

                                        }
                                        ///nokia-conf/configure/system/security/cpm-filter/ip-filter/entry/match/port-selector/port/port/port/range
                                        case range {

                                            ///nokia-conf/configure/system/security/cpm-filter/ip-filter/entry/match/port-selector/port/port/port/range/range
                                            container range {
                                                presence "Enable the range context";
                                                description "Enable the range context";

                                                ///nokia-conf/configure/system/security/cpm-filter/ip-filter/entry/match/port-selector/port/port/port/range/range/start
                                                leaf start {
                                                    type uint16 {
                                                        range "0..65535";
                                                    }
                                                    mandatory true;
                                                    description "Lower bound of the port number to match";
                                                }

                                                ///nokia-conf/configure/system/security/cpm-filter/ip-filter/entry/match/port-selector/port/port/port/range/range/end
                                                leaf end {
                                                    type uint16 {
                                                        range "0..65535";
                                                    }
                                                    mandatory true;
                                                    description "Upper bound of the port number to match";
                                                }

                                            } // container range

                                        }
                                        ///nokia-conf/configure/system/security/cpm-filter/ip-filter/entry/match/port-selector/port/port/port/port-list
                                        case port-list {

                                            ///nokia-conf/configure/system/security/cpm-filter/ip-filter/entry/match/port-selector/port/port/port/port-list/port-list
                                            leaf port-list {
                                                type leafref {
                                                    path "../../../../../../../../filter/match-list/port-list/port-list-name";
                                                }
                                                description "Port list as the match criterion";
                                            }

                                        }
                                    }
                                } // container port

                            }
                        }
                        ///nokia-conf/configure/system/security/cpm-filter/ip-filter/entry/match/ip-option
                        container ip-option {
                            presence "Enable the ip-option context";
                            description "Enable the ip-option context";

                            ///nokia-conf/configure/system/security/cpm-filter/ip-filter/entry/match/ip-option/type
                            leaf type {
                                type types-filter:filter-match-ip-option;
                                mandatory true;
                                description "Specific IP option to match";
                            }

                            ///nokia-conf/configure/system/security/cpm-filter/ip-filter/entry/match/ip-option/mask
                            leaf mask {
                                type types-filter:filter-match-ip-option {
                                    range "1..255";
                                }
                                default "255";
                                description "Range of option numbers for the mask match criterion";
                            }

                        } // container ip-option

                        ///nokia-conf/configure/system/security/cpm-filter/ip-filter/entry/match/src-ip
                        container src-ip {
                            description "Enter the src-ip context";

                            ///nokia-conf/configure/system/security/cpm-filter/ip-filter/entry/match/src-ip/match-address-choice
                            choice match-address-choice {
                                ///nokia-conf/configure/system/security/cpm-filter/ip-filter/entry/match/src-ip/match-address-choice/address-and-prefix-or-mask
                                case address-and-prefix-or-mask {

                                    ///nokia-conf/configure/system/security/cpm-filter/ip-filter/entry/match/src-ip/match-address-choice/address-and-prefix-or-mask/address
                                    leaf address {
                                        type union {
                                            type types-sros:ipv4-prefix-with-host-bits;
                                            type types-sros:ipv4-address;
                                        }
                                        description "IPv4 address used as the match criterion";
                                    }

                                    ///nokia-conf/configure/system/security/cpm-filter/ip-filter/entry/match/src-ip/match-address-choice/address-and-prefix-or-mask/mask
                                    leaf mask {
                                        type types-sros:ipv4-address;
                                        description "IPv4 address mask used as the match criterion";
                                    }

                                }
                                ///nokia-conf/configure/system/security/cpm-filter/ip-filter/entry/match/src-ip/match-address-choice/ip-prefix-list
                                case ip-prefix-list {

                                    ///nokia-conf/configure/system/security/cpm-filter/ip-filter/entry/match/src-ip/match-address-choice/ip-prefix-list/ip-prefix-list
                                    leaf ip-prefix-list {
                                        type leafref {
                                            path "../../../../../../../../filter/match-list/ip-prefix-list/prefix-list-name";
                                        }
                                        description "IP4 address prefix list used as match criterion";
                                    }

                                }
                            }
                        } // container src-ip

                        ///nokia-conf/configure/system/security/cpm-filter/ip-filter/entry/match/dst-ip
                        container dst-ip {
                            description "Enter the dst-ip context";

                            ///nokia-conf/configure/system/security/cpm-filter/ip-filter/entry/match/dst-ip/match-address-choice
                            choice match-address-choice {
                                ///nokia-conf/configure/system/security/cpm-filter/ip-filter/entry/match/dst-ip/match-address-choice/address-and-prefix-or-mask
                                case address-and-prefix-or-mask {

                                    ///nokia-conf/configure/system/security/cpm-filter/ip-filter/entry/match/dst-ip/match-address-choice/address-and-prefix-or-mask/address
                                    leaf address {
                                        type union {
                                            type types-sros:ipv4-prefix-with-host-bits;
                                            type types-sros:ipv4-address;
                                        }
                                        description "IPv4 address used as the match criterion";
                                    }

                                    ///nokia-conf/configure/system/security/cpm-filter/ip-filter/entry/match/dst-ip/match-address-choice/address-and-prefix-or-mask/mask
                                    leaf mask {
                                        type types-sros:ipv4-address;
                                        description "IPv4 address mask used as the match criterion";
                                    }

                                }
                                ///nokia-conf/configure/system/security/cpm-filter/ip-filter/entry/match/dst-ip/match-address-choice/ip-prefix-list
                                case ip-prefix-list {

                                    ///nokia-conf/configure/system/security/cpm-filter/ip-filter/entry/match/dst-ip/match-address-choice/ip-prefix-list/ip-prefix-list
                                    leaf ip-prefix-list {
                                        type leafref {
                                            path "../../../../../../../../filter/match-list/ip-prefix-list/prefix-list-name";
                                        }
                                        description "IP4 address prefix list used as match criterion";
                                    }

                                }
                            }
                        } // container dst-ip

                        ///nokia-conf/configure/system/security/cpm-filter/ip-filter/entry/match/icmp
                        container icmp {
                            description "Enter the icmp context";

                            ///nokia-conf/configure/system/security/cpm-filter/ip-filter/entry/match/icmp/icmp-code
                            choice icmp-code {
                                ///nokia-conf/configure/system/security/cpm-filter/ip-filter/entry/match/icmp/icmp-code/code
                                case code {

                                    ///nokia-conf/configure/system/security/cpm-filter/ip-filter/entry/match/icmp/icmp-code/code/code
                                    leaf code {
                                        type types-filter:ipv4-match-icmp-codes;
                                        description "ICMP code to match";
                                    }

                                }
                            }
                            ///nokia-conf/configure/system/security/cpm-filter/ip-filter/entry/match/icmp/icmp-type
                            choice icmp-type {
                                ///nokia-conf/configure/system/security/cpm-filter/ip-filter/entry/match/icmp/icmp-type/type
                                case type {

                                    ///nokia-conf/configure/system/security/cpm-filter/ip-filter/entry/match/icmp/icmp-type/type/type
                                    leaf type {
                                        type types-filter:ipv4-match-icmp-types;
                                        description "ICMP type to match";
                                    }

                                }
                            }
                        } // container icmp

                        ///nokia-conf/configure/system/security/cpm-filter/ip-filter/entry/match/tcp-flags
                        container tcp-flags {
                            description "Enter the tcp-flags context";

                            ///nokia-conf/configure/system/security/cpm-filter/ip-filter/entry/match/tcp-flags/ack
                            leaf ack {
                                type boolean;
                                description "ACK bit in TCP header control bits as match criterion";
                            }

                            ///nokia-conf/configure/system/security/cpm-filter/ip-filter/entry/match/tcp-flags/syn
                            leaf syn {
                                type boolean;
                                description "SYN bit in TCP header control bits as match criterion";
                            }

                        } // container tcp-flags

                    } // container match

                    ///nokia-conf/configure/system/security/cpm-filter/ip-filter/entry/action
                    container action {
                        description "Enter the action context";

                        ///nokia-conf/configure/system/security/cpm-filter/ip-filter/entry/action/action-choice
                        choice action-choice {
                            default "case-drop";
                            ///nokia-conf/configure/system/security/cpm-filter/ip-filter/entry/action/action-choice/case-drop
                            case case-drop {

                                ///nokia-conf/configure/system/security/cpm-filter/ip-filter/entry/action/action-choice/case-drop/drop
                                leaf drop {
                                    type empty;
                                    description "Drop matching packets";
                                }

                            }
                            ///nokia-conf/configure/system/security/cpm-filter/ip-filter/entry/action/action-choice/case-accept
                            case case-accept {

                                ///nokia-conf/configure/system/security/cpm-filter/ip-filter/entry/action/action-choice/case-accept/accept
                                leaf accept {
                                    type empty;
                                    description "Forward matching packets";
                                }

                            }
                            ///nokia-conf/configure/system/security/cpm-filter/ip-filter/entry/action/action-choice/case-default
                            case case-default {

                                ///nokia-conf/configure/system/security/cpm-filter/ip-filter/entry/action/action-choice/case-default/default
                                leaf default {
                                    type empty;
                                    description "Use default action for matching packets";
                                }

                            }
                            ///nokia-conf/configure/system/security/cpm-filter/ip-filter/entry/action/action-choice/case-queue
                            case case-queue {

                                ///nokia-conf/configure/system/security/cpm-filter/ip-filter/entry/action/action-choice/case-queue/queue
                                leaf queue {
                                    type leafref {
                                        path "../../../../../cpm-queue/queue/queue-id";
                                    }
                                    description "Forward matching packets to the CPM hardware queue";
                                }

                            }
                        }
                    } // container action

                } // list entry

            } // container ip-filter

            ///nokia-conf/configure/system/security/cpm-filter/ipv6-filter
            container ipv6-filter {
                description "Enter the ipv6-filter context";

                ///nokia-conf/configure/system/security/cpm-filter/ipv6-filter/admin-state
                leaf admin-state {
                    type types-sros:admin-state;
                    default "disable";
                    description "Administrative state of the CPM filter";
                }

                ///nokia-conf/configure/system/security/cpm-filter/ipv6-filter/entry
                list entry {
                    key "entry-id";
                    description "Enter the entry list instance";

                    ///nokia-conf/configure/system/security/cpm-filter/ipv6-filter/entry/entry-id
                    leaf entry-id {
                        type uint32 {
                            range "1..131072";
                        }
                        description "Filter entry ID";
                    }

                    ///nokia-conf/configure/system/security/cpm-filter/ipv6-filter/entry/description
                    leaf description {
                        type types-sros:description;
                        description "Text description";
                    }

                    ///nokia-conf/configure/system/security/cpm-filter/ipv6-filter/entry/log
                    leaf log {
                        type leafref {
                            path "../../../../../../filter/log/log-id";
                        }
                        description "Log ID where matching packets are entered";
                    }

                    ///nokia-conf/configure/system/security/cpm-filter/ipv6-filter/entry/apply-groups
                    leaf-list apply-groups {
                        type leafref {
                            path "../../../../../../groups/group/name";
                        }
                        max-elements 8;
                        ordered-by user;
                        description "Apply a configuration group at this level";
                    }

                    ///nokia-conf/configure/system/security/cpm-filter/ipv6-filter/entry/apply-groups-exclude
                    leaf-list apply-groups-exclude {
                        type leafref {
                            path "../../../../../../groups/group/name";
                        }
                        max-elements 8;
                        ordered-by user;
                        description "Exclude a configuration group at this level";
                    }

                    ///nokia-conf/configure/system/security/cpm-filter/ipv6-filter/entry/match
                    container match {
                        description "Enter the match context";

                        ///nokia-conf/configure/system/security/cpm-filter/ipv6-filter/entry/match/router-instance
                        leaf router-instance {
                            type types-sros:named-item-64;
                            description "Router instance as the match criteria";
                        }

                        ///nokia-conf/configure/system/security/cpm-filter/ipv6-filter/entry/match/next-header
                        leaf next-header {
                            type types-sros:match-ip-protocol;
                            description "IP protocol to match";
                        }

                        ///nokia-conf/configure/system/security/cpm-filter/ipv6-filter/entry/match/dscp
                        leaf dscp {
                            type types-qos:dscp-name;
                            description "DSCP used as the match criterion on the packet";
                        }

                        ///nokia-conf/configure/system/security/cpm-filter/ipv6-filter/entry/match/flow-label
                        leaf flow-label {
                            type types-filter:filter-match-flow-label;
                            description "Flow label in the IPv6 header as the match criterion";
                        }

                        ///nokia-conf/configure/system/security/cpm-filter/ipv6-filter/entry/match/fragment
                        leaf fragment {
                            type enumeration {
                                enum false                          { value 2; }
                                enum true                           { value 3; }
                            }
                            description "Match criterion based on presence of fragmented packets";
                        }

                        ///nokia-conf/configure/system/security/cpm-filter/ipv6-filter/entry/match/port-selector
                        choice port-selector {
                            ///nokia-conf/configure/system/security/cpm-filter/ipv6-filter/entry/match/port-selector/src-dst-port
                            case src-dst-port {

                                ///nokia-conf/configure/system/security/cpm-filter/ipv6-filter/entry/match/port-selector/src-dst-port/src-port
                                container src-port {
                                    description "Enter the src-port context";

                                    ///nokia-conf/configure/system/security/cpm-filter/ipv6-filter/entry/match/port-selector/src-dst-port/src-port/port
                                    choice port {
                                        ///nokia-conf/configure/system/security/cpm-filter/ipv6-filter/entry/match/port-selector/src-dst-port/src-port/port/eq
                                        case eq {

                                            ///nokia-conf/configure/system/security/cpm-filter/ipv6-filter/entry/match/port-selector/src-dst-port/src-port/port/eq/eq
                                            leaf eq {
                                                type uint16 {
                                                    range "0..65535";
                                                }
                                                description "Port number as the match criterion";
                                            }

                                            ///nokia-conf/configure/system/security/cpm-filter/ipv6-filter/entry/match/port-selector/src-dst-port/src-port/port/eq/mask
                                            leaf mask {
                                                type uint16 {
                                                    range "1..65535";
                                                }
                                                default "65535";
                                                description "Port mask as the match criterion";
                                            }

                                        }
                                        ///nokia-conf/configure/system/security/cpm-filter/ipv6-filter/entry/match/port-selector/src-dst-port/src-port/port/range
                                        case range {

                                            ///nokia-conf/configure/system/security/cpm-filter/ipv6-filter/entry/match/port-selector/src-dst-port/src-port/port/range/range
                                            container range {
                                                presence "Enable the range context";
                                                description "Enable the range context";

                                                ///nokia-conf/configure/system/security/cpm-filter/ipv6-filter/entry/match/port-selector/src-dst-port/src-port/port/range/range/start
                                                leaf start {
                                                    type uint16 {
                                                        range "0..65535";
                                                    }
                                                    mandatory true;
                                                    description "Lower bound of the port number to match";
                                                }

                                                ///nokia-conf/configure/system/security/cpm-filter/ipv6-filter/entry/match/port-selector/src-dst-port/src-port/port/range/range/end
                                                leaf end {
                                                    type uint16 {
                                                        range "0..65535";
                                                    }
                                                    mandatory true;
                                                    description "Upper bound of the port number to match";
                                                }

                                            } // container range

                                        }
                                        ///nokia-conf/configure/system/security/cpm-filter/ipv6-filter/entry/match/port-selector/src-dst-port/src-port/port/port-list
                                        case port-list {

                                            ///nokia-conf/configure/system/security/cpm-filter/ipv6-filter/entry/match/port-selector/src-dst-port/src-port/port/port-list/port-list
                                            leaf port-list {
                                                type leafref {
                                                    path "../../../../../../../../filter/match-list/port-list/port-list-name";
                                                }
                                                description "Port list as the match criterion";
                                            }

                                        }
                                    }
                                } // container src-port

                                ///nokia-conf/configure/system/security/cpm-filter/ipv6-filter/entry/match/port-selector/src-dst-port/dst-port
                                container dst-port {
                                    description "Enter the dst-port context";

                                    ///nokia-conf/configure/system/security/cpm-filter/ipv6-filter/entry/match/port-selector/src-dst-port/dst-port/port
                                    choice port {
                                        ///nokia-conf/configure/system/security/cpm-filter/ipv6-filter/entry/match/port-selector/src-dst-port/dst-port/port/eq
                                        case eq {

                                            ///nokia-conf/configure/system/security/cpm-filter/ipv6-filter/entry/match/port-selector/src-dst-port/dst-port/port/eq/eq
                                            leaf eq {
                                                type uint16 {
                                                    range "0..65535";
                                                }
                                                description "Port number as the match criterion";
                                            }

                                            ///nokia-conf/configure/system/security/cpm-filter/ipv6-filter/entry/match/port-selector/src-dst-port/dst-port/port/eq/mask
                                            leaf mask {
                                                type uint16 {
                                                    range "1..65535";
                                                }
                                                default "65535";
                                                description "Port mask as the match criterion";
                                            }

                                        }
                                        ///nokia-conf/configure/system/security/cpm-filter/ipv6-filter/entry/match/port-selector/src-dst-port/dst-port/port/range
                                        case range {

                                            ///nokia-conf/configure/system/security/cpm-filter/ipv6-filter/entry/match/port-selector/src-dst-port/dst-port/port/range/range
                                            container range {
                                                presence "Enable the range context";
                                                description "Enable the range context";

                                                ///nokia-conf/configure/system/security/cpm-filter/ipv6-filter/entry/match/port-selector/src-dst-port/dst-port/port/range/range/start
                                                leaf start {
                                                    type uint16 {
                                                        range "0..65535";
                                                    }
                                                    mandatory true;
                                                    description "Lower bound of the port number to match";
                                                }

                                                ///nokia-conf/configure/system/security/cpm-filter/ipv6-filter/entry/match/port-selector/src-dst-port/dst-port/port/range/range/end
                                                leaf end {
                                                    type uint16 {
                                                        range "0..65535";
                                                    }
                                                    mandatory true;
                                                    description "Upper bound of the port number to match";
                                                }

                                            } // container range

                                        }
                                        ///nokia-conf/configure/system/security/cpm-filter/ipv6-filter/entry/match/port-selector/src-dst-port/dst-port/port/port-list
                                        case port-list {

                                            ///nokia-conf/configure/system/security/cpm-filter/ipv6-filter/entry/match/port-selector/src-dst-port/dst-port/port/port-list/port-list
                                            leaf port-list {
                                                type leafref {
                                                    path "../../../../../../../../filter/match-list/port-list/port-list-name";
                                                }
                                                description "Port list as the match criterion";
                                            }

                                        }
                                    }
                                } // container dst-port

                            }
                            ///nokia-conf/configure/system/security/cpm-filter/ipv6-filter/entry/match/port-selector/port
                            case port {

                                ///nokia-conf/configure/system/security/cpm-filter/ipv6-filter/entry/match/port-selector/port/port
                                container port {
                                    description "Enter the port context";

                                    ///nokia-conf/configure/system/security/cpm-filter/ipv6-filter/entry/match/port-selector/port/port/port
                                    choice port {
                                        ///nokia-conf/configure/system/security/cpm-filter/ipv6-filter/entry/match/port-selector/port/port/port/eq
                                        case eq {

                                            ///nokia-conf/configure/system/security/cpm-filter/ipv6-filter/entry/match/port-selector/port/port/port/eq/eq
                                            leaf eq {
                                                type uint16 {
                                                    range "0..65535";
                                                }
                                                description "Port number as the match criterion";
                                            }

                                            ///nokia-conf/configure/system/security/cpm-filter/ipv6-filter/entry/match/port-selector/port/port/port/eq/mask
                                            leaf mask {
                                                type uint16 {
                                                    range "1..65535";
                                                }
                                                default "65535";
                                                description "Port mask as the match criterion";
                                            }

                                        }
                                        ///nokia-conf/configure/system/security/cpm-filter/ipv6-filter/entry/match/port-selector/port/port/port/range
                                        case range {

                                            ///nokia-conf/configure/system/security/cpm-filter/ipv6-filter/entry/match/port-selector/port/port/port/range/range
                                            container range {
                                                presence "Enable the range context";
                                                description "Enable the range context";

                                                ///nokia-conf/configure/system/security/cpm-filter/ipv6-filter/entry/match/port-selector/port/port/port/range/range/start
                                                leaf start {
                                                    type uint16 {
                                                        range "0..65535";
                                                    }
                                                    mandatory true;
                                                    description "Lower bound of the port number to match";
                                                }

                                                ///nokia-conf/configure/system/security/cpm-filter/ipv6-filter/entry/match/port-selector/port/port/port/range/range/end
                                                leaf end {
                                                    type uint16 {
                                                        range "0..65535";
                                                    }
                                                    mandatory true;
                                                    description "Upper bound of the port number to match";
                                                }

                                            } // container range

                                        }
                                        ///nokia-conf/configure/system/security/cpm-filter/ipv6-filter/entry/match/port-selector/port/port/port/port-list
                                        case port-list {

                                            ///nokia-conf/configure/system/security/cpm-filter/ipv6-filter/entry/match/port-selector/port/port/port/port-list/port-list
                                            leaf port-list {
                                                type leafref {
                                                    path "../../../../../../../../filter/match-list/port-list/port-list-name";
                                                }
                                                description "Port list as the match criterion";
                                            }

                                        }
                                    }
                                } // container port

                            }
                        }
                        ///nokia-conf/configure/system/security/cpm-filter/ipv6-filter/entry/match/src-ip
                        container src-ip {
                            description "Enter the src-ip context";

                            ///nokia-conf/configure/system/security/cpm-filter/ipv6-filter/entry/match/src-ip/match-address-choice
                            choice match-address-choice {
                                ///nokia-conf/configure/system/security/cpm-filter/ipv6-filter/entry/match/src-ip/match-address-choice/address-and-prefix-or-mask
                                case address-and-prefix-or-mask {

                                    ///nokia-conf/configure/system/security/cpm-filter/ipv6-filter/entry/match/src-ip/match-address-choice/address-and-prefix-or-mask/address
                                    leaf address {
                                        type union {
                                            type types-sros:ipv6-prefix-with-host-bits;
                                            type types-sros:ipv6-address;
                                        }
                                        description "IPv6 address used as the match criterion";
                                    }

                                    ///nokia-conf/configure/system/security/cpm-filter/ipv6-filter/entry/match/src-ip/match-address-choice/address-and-prefix-or-mask/mask
                                    leaf mask {
                                        type types-sros:ipv6-address;
                                        description "IPv6 address mask used as the match criterion";
                                    }

                                }
                                ///nokia-conf/configure/system/security/cpm-filter/ipv6-filter/entry/match/src-ip/match-address-choice/ipv6-prefix-list
                                case ipv6-prefix-list {

                                    ///nokia-conf/configure/system/security/cpm-filter/ipv6-filter/entry/match/src-ip/match-address-choice/ipv6-prefix-list/ipv6-prefix-list
                                    leaf ipv6-prefix-list {
                                        type leafref {
                                            path "../../../../../../../../filter/match-list/ipv6-prefix-list/prefix-list-name";
                                        }
                                        description "IPv6 address prefix list used as match criterion";
                                    }

                                }
                            }
                        } // container src-ip

                        ///nokia-conf/configure/system/security/cpm-filter/ipv6-filter/entry/match/dst-ip
                        container dst-ip {
                            description "Enter the dst-ip context";

                            ///nokia-conf/configure/system/security/cpm-filter/ipv6-filter/entry/match/dst-ip/match-address-choice
                            choice match-address-choice {
                                ///nokia-conf/configure/system/security/cpm-filter/ipv6-filter/entry/match/dst-ip/match-address-choice/address-and-prefix-or-mask
                                case address-and-prefix-or-mask {

                                    ///nokia-conf/configure/system/security/cpm-filter/ipv6-filter/entry/match/dst-ip/match-address-choice/address-and-prefix-or-mask/address
                                    leaf address {
                                        type union {
                                            type types-sros:ipv6-prefix-with-host-bits;
                                            type types-sros:ipv6-address;
                                        }
                                        description "IPv6 address used as the match criterion";
                                    }

                                    ///nokia-conf/configure/system/security/cpm-filter/ipv6-filter/entry/match/dst-ip/match-address-choice/address-and-prefix-or-mask/mask
                                    leaf mask {
                                        type types-sros:ipv6-address;
                                        description "IPv6 address mask used as the match criterion";
                                    }

                                }
                                ///nokia-conf/configure/system/security/cpm-filter/ipv6-filter/entry/match/dst-ip/match-address-choice/ipv6-prefix-list
                                case ipv6-prefix-list {

                                    ///nokia-conf/configure/system/security/cpm-filter/ipv6-filter/entry/match/dst-ip/match-address-choice/ipv6-prefix-list/ipv6-prefix-list
                                    leaf ipv6-prefix-list {
                                        type leafref {
                                            path "../../../../../../../../filter/match-list/ipv6-prefix-list/prefix-list-name";
                                        }
                                        description "IPv6 address prefix list used as match criterion";
                                    }

                                }
                            }
                        } // container dst-ip

                        ///nokia-conf/configure/system/security/cpm-filter/ipv6-filter/entry/match/extension-header
                        container extension-header {
                            description "Enter the extension-header context";

                            ///nokia-conf/configure/system/security/cpm-filter/ipv6-filter/entry/match/extension-header/hop-by-hop
                            leaf hop-by-hop {
                                type boolean;
                                description "Match on existence of Hop-By-Hop Options Header";
                            }

                        } // container extension-header

                        ///nokia-conf/configure/system/security/cpm-filter/ipv6-filter/entry/match/icmp
                        container icmp {
                            description "Enter the icmp context";

                            ///nokia-conf/configure/system/security/cpm-filter/ipv6-filter/entry/match/icmp/icmp-code
                            choice icmp-code {
                                ///nokia-conf/configure/system/security/cpm-filter/ipv6-filter/entry/match/icmp/icmp-code/code
                                case code {

                                    ///nokia-conf/configure/system/security/cpm-filter/ipv6-filter/entry/match/icmp/icmp-code/code/code
                                    leaf code {
                                        type types-filter:ipv6-match-icmp-codes;
                                        description "ICMP code as the match criterion";
                                    }

                                }
                            }
                            ///nokia-conf/configure/system/security/cpm-filter/ipv6-filter/entry/match/icmp/icmp-type
                            choice icmp-type {
                                ///nokia-conf/configure/system/security/cpm-filter/ipv6-filter/entry/match/icmp/icmp-type/type
                                case type {

                                    ///nokia-conf/configure/system/security/cpm-filter/ipv6-filter/entry/match/icmp/icmp-type/type/type
                                    leaf type {
                                        type types-filter:ipv6-match-icmp-types;
                                        description "ICMP type as the match criterion";
                                    }

                                }
                            }
                        } // container icmp

                        ///nokia-conf/configure/system/security/cpm-filter/ipv6-filter/entry/match/tcp-flags
                        container tcp-flags {
                            description "Enter the tcp-flags context";

                            ///nokia-conf/configure/system/security/cpm-filter/ipv6-filter/entry/match/tcp-flags/ack
                            leaf ack {
                                type boolean;
                                description "ACK bit in TCP header control bits as match criterion";
                            }

                            ///nokia-conf/configure/system/security/cpm-filter/ipv6-filter/entry/match/tcp-flags/syn
                            leaf syn {
                                type boolean;
                                description "SYN bit in TCP header control bits as match criterion";
                            }

                        } // container tcp-flags

                    } // container match

                    ///nokia-conf/configure/system/security/cpm-filter/ipv6-filter/entry/action
                    container action {
                        description "Enter the action context";

                        ///nokia-conf/configure/system/security/cpm-filter/ipv6-filter/entry/action/action-choice
                        choice action-choice {
                            default "case-drop";
                            ///nokia-conf/configure/system/security/cpm-filter/ipv6-filter/entry/action/action-choice/case-drop
                            case case-drop {

                                ///nokia-conf/configure/system/security/cpm-filter/ipv6-filter/entry/action/action-choice/case-drop/drop
                                leaf drop {
                                    type empty;
                                    description "Drop matching packets";
                                }

                            }
                            ///nokia-conf/configure/system/security/cpm-filter/ipv6-filter/entry/action/action-choice/case-accept
                            case case-accept {

                                ///nokia-conf/configure/system/security/cpm-filter/ipv6-filter/entry/action/action-choice/case-accept/accept
                                leaf accept {
                                    type empty;
                                    description "Forward matching packets";
                                }

                            }
                            ///nokia-conf/configure/system/security/cpm-filter/ipv6-filter/entry/action/action-choice/case-default
                            case case-default {

                                ///nokia-conf/configure/system/security/cpm-filter/ipv6-filter/entry/action/action-choice/case-default/default
                                leaf default {
                                    type empty;
                                    description "Use default action for matching packets";
                                }

                            }
                            ///nokia-conf/configure/system/security/cpm-filter/ipv6-filter/entry/action/action-choice/case-queue
                            case case-queue {

                                ///nokia-conf/configure/system/security/cpm-filter/ipv6-filter/entry/action/action-choice/case-queue/queue
                                leaf queue {
                                    type leafref {
                                        path "../../../../../cpm-queue/queue/queue-id";
                                    }
                                    description "Forward matching packets to the CPM hardware queue";
                                }

                            }
                        }
                    } // container action

                } // list entry

            } // container ipv6-filter

            ///nokia-conf/configure/system/security/cpm-filter/mac-filter
            container mac-filter {
                description "Enter the mac-filter context";

                ///nokia-conf/configure/system/security/cpm-filter/mac-filter/admin-state
                leaf admin-state {
                    type types-sros:admin-state;
                    default "disable";
                    description "Administrative state of the CPM filter";
                }

                ///nokia-conf/configure/system/security/cpm-filter/mac-filter/entry
                list entry {
                    key "entry-id";
                    description "Enter the entry list instance";

                    ///nokia-conf/configure/system/security/cpm-filter/mac-filter/entry/entry-id
                    leaf entry-id {
                        type uint32 {
                            range "1..131072";
                        }
                        description "Filter entry ID";
                    }

                    ///nokia-conf/configure/system/security/cpm-filter/mac-filter/entry/description
                    leaf description {
                        type types-sros:description;
                        description "Text description";
                    }

                    ///nokia-conf/configure/system/security/cpm-filter/mac-filter/entry/log
                    leaf log {
                        type leafref {
                            path "../../../../../../filter/log/log-id";
                        }
                        description "Log ID where matching packets are entered";
                    }

                    ///nokia-conf/configure/system/security/cpm-filter/mac-filter/entry/apply-groups
                    leaf-list apply-groups {
                        type leafref {
                            path "../../../../../../groups/group/name";
                        }
                        max-elements 8;
                        ordered-by user;
                        description "Apply a configuration group at this level";
                    }

                    ///nokia-conf/configure/system/security/cpm-filter/mac-filter/entry/apply-groups-exclude
                    leaf-list apply-groups-exclude {
                        type leafref {
                            path "../../../../../../groups/group/name";
                        }
                        max-elements 8;
                        ordered-by user;
                        description "Exclude a configuration group at this level";
                    }

                    ///nokia-conf/configure/system/security/cpm-filter/mac-filter/entry/match
                    container match {
                        description "Enter the match context";

                        ///nokia-conf/configure/system/security/cpm-filter/mac-filter/entry/match/service
                        leaf service {
                            type leafref {
                                path "../../../../../../../service/vpls/service-name";
                            }
                            description "Service ID used as the match condition";
                        }

                        ///nokia-conf/configure/system/security/cpm-filter/mac-filter/entry/match/frame-type
                        leaf frame-type {
                            type enumeration {
                                enum 802dot2-llc                    { value 1; }
                                enum ethernet-ii                    { value 3; }
                            }
                            description "MAC frame type as the match criterion";
                        }

                        ///nokia-conf/configure/system/security/cpm-filter/mac-filter/entry/match/etype
                        leaf etype {
                            type types-services:etype-value;
                            description "Ethernet type as the match criterion";
                        }

                        ///nokia-conf/configure/system/security/cpm-filter/mac-filter/entry/match/src-mac
                        container src-mac {
                            presence "Enable the src-mac context";
                            description "Enable the src-mac context";

                            ///nokia-conf/configure/system/security/cpm-filter/mac-filter/entry/match/src-mac/address
                            leaf address {
                                type yang:mac-address;
                                mandatory true;
                                description "MAC address used as the match criterion";
                            }

                            ///nokia-conf/configure/system/security/cpm-filter/mac-filter/entry/match/src-mac/mask
                            leaf mask {
                                type yang:mac-address;
                                default "ff:ff:ff:ff:ff:ff";
                                description "MAC address mask as the match criterion";
                            }

                        } // container src-mac

                        ///nokia-conf/configure/system/security/cpm-filter/mac-filter/entry/match/dst-mac
                        container dst-mac {
                            presence "Enable the dst-mac context";
                            description "Enable the dst-mac context";

                            ///nokia-conf/configure/system/security/cpm-filter/mac-filter/entry/match/dst-mac/address
                            leaf address {
                                type yang:mac-address;
                                mandatory true;
                                description "MAC address used as the match criterion";
                            }

                            ///nokia-conf/configure/system/security/cpm-filter/mac-filter/entry/match/dst-mac/mask
                            leaf mask {
                                type yang:mac-address;
                                default "ff:ff:ff:ff:ff:ff";
                                description "MAC address mask as the match criterion";
                            }

                        } // container dst-mac

                        ///nokia-conf/configure/system/security/cpm-filter/mac-filter/entry/match/llc-ssap
                        container llc-ssap {
                            presence "Enable the llc-ssap context";
                            description "Enable the llc-ssap context";

                            ///nokia-conf/configure/system/security/cpm-filter/mac-filter/entry/match/llc-ssap/ssap
                            leaf ssap {
                                type types-qos:service-access-point;
                                mandatory true;
                                description "8-bit SSAP as the match criterion";
                            }

                            ///nokia-conf/configure/system/security/cpm-filter/mac-filter/entry/match/llc-ssap/mask
                            leaf mask {
                                type types-qos:service-access-point {
                                    range "1..255";
                                }
                                default "255";
                                description "Mask for SSAP value as the match criterion";
                            }

                        } // container llc-ssap

                        ///nokia-conf/configure/system/security/cpm-filter/mac-filter/entry/match/llc-dsap
                        container llc-dsap {
                            presence "Enable the llc-dsap context";
                            description "Enable the llc-dsap context";

                            ///nokia-conf/configure/system/security/cpm-filter/mac-filter/entry/match/llc-dsap/dsap
                            leaf dsap {
                                type types-qos:service-access-point;
                                mandatory true;
                                description "8-bit DSAP as the match criterion";
                            }

                            ///nokia-conf/configure/system/security/cpm-filter/mac-filter/entry/match/llc-dsap/mask
                            leaf mask {
                                type types-qos:service-access-point {
                                    range "1..255";
                                }
                                default "255";
                                description "Mask for DSAP value as the match criterion";
                            }

                        } // container llc-dsap

                        ///nokia-conf/configure/system/security/cpm-filter/mac-filter/entry/match/cfm-opcode
                        container cfm-opcode {
                            description "Enter the cfm-opcode context";

                            ///nokia-conf/configure/system/security/cpm-filter/mac-filter/entry/match/cfm-opcode/cfm-opcode
                            choice cfm-opcode {
                                ///nokia-conf/configure/system/security/cpm-filter/mac-filter/entry/match/cfm-opcode/cfm-opcode/eq
                                case eq {

                                    ///nokia-conf/configure/system/security/cpm-filter/mac-filter/entry/match/cfm-opcode/cfm-opcode/eq/eq
                                    leaf eq {
                                        type uint32 {
                                            range "0..255";
                                        }
                                        description "Equal to comparison operator for the CFM opcode";
                                    }

                                }
                                ///nokia-conf/configure/system/security/cpm-filter/mac-filter/entry/match/cfm-opcode/cfm-opcode/lt
                                case lt {

                                    ///nokia-conf/configure/system/security/cpm-filter/mac-filter/entry/match/cfm-opcode/cfm-opcode/lt/lt
                                    leaf lt {
                                        type uint32 {
                                            range "1..255";
                                        }
                                        description "Less than comparison operator for the CFM opcode";
                                    }

                                }
                                ///nokia-conf/configure/system/security/cpm-filter/mac-filter/entry/match/cfm-opcode/cfm-opcode/gt
                                case gt {

                                    ///nokia-conf/configure/system/security/cpm-filter/mac-filter/entry/match/cfm-opcode/cfm-opcode/gt/gt
                                    leaf gt {
                                        type uint32 {
                                            range "0..254";
                                        }
                                        description "Greater than comparison operator for the CFM opcode";
                                    }

                                }
                                ///nokia-conf/configure/system/security/cpm-filter/mac-filter/entry/match/cfm-opcode/cfm-opcode/range
                                case range {

                                    ///nokia-conf/configure/system/security/cpm-filter/mac-filter/entry/match/cfm-opcode/cfm-opcode/range/range
                                    container range {
                                        presence "Enable the range context";
                                        description "Enable the range context";

                                        ///nokia-conf/configure/system/security/cpm-filter/mac-filter/entry/match/cfm-opcode/cfm-opcode/range/range/start
                                        leaf start {
                                            type uint32 {
                                                range "0..254";
                                            }
                                            mandatory true;
                                            description "Lower bound of the OpCode range to match";
                                        }

                                        ///nokia-conf/configure/system/security/cpm-filter/mac-filter/entry/match/cfm-opcode/cfm-opcode/range/range/end
                                        leaf end {
                                            type uint32 {
                                                range "1..255";
                                            }
                                            mandatory true;
                                            description "Upper bound of the Opcode range to match";
                                        }

                                    } // container range

                                }
                            }
                        } // container cfm-opcode

                    } // container match

                    ///nokia-conf/configure/system/security/cpm-filter/mac-filter/entry/action
                    container action {
                        description "Enter the action context";

                        ///nokia-conf/configure/system/security/cpm-filter/mac-filter/entry/action/action-choice
                        choice action-choice {
                            default "case-drop";
                            ///nokia-conf/configure/system/security/cpm-filter/mac-filter/entry/action/action-choice/case-drop
                            case case-drop {

                                ///nokia-conf/configure/system/security/cpm-filter/mac-filter/entry/action/action-choice/case-drop/drop
                                leaf drop {
                                    type empty;
                                    description "Drop matching packets";
                                }

                            }
                            ///nokia-conf/configure/system/security/cpm-filter/mac-filter/entry/action/action-choice/case-accept
                            case case-accept {

                                ///nokia-conf/configure/system/security/cpm-filter/mac-filter/entry/action/action-choice/case-accept/accept
                                leaf accept {
                                    type empty;
                                    description "Forward matching packets";
                                }

                            }
                            ///nokia-conf/configure/system/security/cpm-filter/mac-filter/entry/action/action-choice/case-default
                            case case-default {

                                ///nokia-conf/configure/system/security/cpm-filter/mac-filter/entry/action/action-choice/case-default/default
                                leaf default {
                                    type empty;
                                    description "Use default action for matching packets";
                                }

                            }
                            ///nokia-conf/configure/system/security/cpm-filter/mac-filter/entry/action/action-choice/case-queue
                            case case-queue {

                                ///nokia-conf/configure/system/security/cpm-filter/mac-filter/entry/action/action-choice/case-queue/queue
                                leaf queue {
                                    type leafref {
                                        path "../../../../../cpm-queue/queue/queue-id";
                                    }
                                    description "Forward matching packets to the CPM hardware queue";
                                }

                            }
                        }
                    } // container action

                } // list entry

            } // container mac-filter

        } // container cpm-filter

    } // grouping conf-system-security-cpm-cpm-filter

    grouping conf-system-security-cpm-cpm-queue {
        ///nokia-conf/configure/system/security/cpm-queue
        container cpm-queue {
            description "Enable the cpm-queue context";

            ///nokia-conf/configure/system/security/cpm-queue/apply-groups
            leaf-list apply-groups {
                type leafref {
                    path "../../../../groups/group/name";
                }
                max-elements 8;
                ordered-by user;
                description "Apply a configuration group at this level";
            }

            ///nokia-conf/configure/system/security/cpm-queue/apply-groups-exclude
            leaf-list apply-groups-exclude {
                type leafref {
                    path "../../../../groups/group/name";
                }
                max-elements 8;
                ordered-by user;
                description "Exclude a configuration group at this level";
            }

            ///nokia-conf/configure/system/security/cpm-queue/queue
            list queue {
                key "queue-id";
                description "Enter the queue list instance";

                ///nokia-conf/configure/system/security/cpm-queue/queue/queue-id
                leaf queue-id {
                    type uint32 {
                        range "33..2000";
                    }
                    description "CPM queue ID";
                }

                ///nokia-conf/configure/system/security/cpm-queue/queue/cbs
                leaf cbs {
                    type types-security:burst-size;
                    units "kilobps";
                    description "Buffer size that can be drawn from queue buffer pool";
                }

                ///nokia-conf/configure/system/security/cpm-queue/queue/mbs
                leaf mbs {
                    type types-security:burst-size;
                    units "kilobps";
                    description "Maximum queue depth to which the queue can grow";
                }

                ///nokia-conf/configure/system/security/cpm-queue/queue/apply-groups
                leaf-list apply-groups {
                    type leafref {
                        path "../../../../../groups/group/name";
                    }
                    max-elements 8;
                    ordered-by user;
                    description "Apply a configuration group at this level";
                }

                ///nokia-conf/configure/system/security/cpm-queue/queue/apply-groups-exclude
                leaf-list apply-groups-exclude {
                    type leafref {
                        path "../../../../../groups/group/name";
                    }
                    max-elements 8;
                    ordered-by user;
                    description "Exclude a configuration group at this level";
                }

                ///nokia-conf/configure/system/security/cpm-queue/queue/rate
                container rate {
                    description "Enter the rate context";

                    ///nokia-conf/configure/system/security/cpm-queue/queue/rate/pir
                    leaf pir {
                        type types-system:pir-rate;
                        units "kilobps";
                        default "max";
                        description "Peak Information Rate for the queue";
                    }

                    ///nokia-conf/configure/system/security/cpm-queue/queue/rate/cir
                    leaf cir {
                        type types-system:cir-rate;
                        units "kilobps";
                        default "max";
                        description "Amount of bandwidth committed to the queue";
                    }

                } // container rate

            } // list queue

        } // container cpm-queue

    } // grouping conf-system-security-cpm-cpm-queue

}
