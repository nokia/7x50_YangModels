submodule nokia-conf-svc-ies-vdo-if {

    yang-version "1.1";

    belongs-to nokia-conf { prefix "conf"; }

    import nokia-sros-yang-extensions     { prefix "sros-ext"; }
    import nokia-types-services           { prefix "types-services"; }
    import nokia-types-sros               { prefix "types-sros"; }

    include nokia-conf-filter;
    include nokia-conf-groups;
    include nokia-conf-isa;
    include nokia-conf-isa-video-group;
    include nokia-conf-log;
    include nokia-conf-qos;
    include nokia-conf-system;
    include nokia-conf-system-security;

    sros-ext:sros-major-release "rel23";
    organization "Nokia";
    contact
        "Nokia SR OS Support
         Web: <http://www.nokia.com>";
    description
        "Nokia YANG Data model to configure ies service video interfaces on SR OS based routers.

         Copyright 2016 Nokia. All rights reserved. Reproduction of this document
         is authorized on the condition that the foregoing copyright notice is included.

         This nokia-conf-svc-ies-vdo-if YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-06";

    grouping conf-svc-ies-vdo-if-video-interface {
        ///nokia-conf/configure/service/ies/video-interface
        list video-interface {
            key "interface-name";
            max-elements 9;
            description "Enter the video-interface list instance";

            ///nokia-conf/configure/service/ies/video-interface/interface-name
            leaf interface-name {
                type types-sros:interface-name {
                    length "1..29";
                }
                description "Video interface name";
            }

            ///nokia-conf/configure/service/ies/video-interface/admin-state
            leaf admin-state {
                type types-sros:admin-state;
                default "disable";
                description "Administrative state of the video interface";
            }

            ///nokia-conf/configure/service/ies/video-interface/accounting-policy
            leaf accounting-policy {
                type leafref {
                    path "../../../../log/accounting-policy/policy-id";
                }
                description "Accounting Policy";
            }

            ///nokia-conf/configure/service/ies/video-interface/description
            leaf description {
                type types-sros:description;
                description "Text description";
            }

            ///nokia-conf/configure/service/ies/video-interface/cpu-protection
            leaf cpu-protection {
                type leafref {
                    path "../../../../system/security/cpu-protection/policy/policy-id";
                }
                description "CPU protection policy";
            }

            ///nokia-conf/configure/service/ies/video-interface/multicast-service
            leaf multicast-service {
                type types-services:external-service-id;
                description "Associated multicast service ID";
            }

            ///nokia-conf/configure/service/ies/video-interface/output-format
            leaf output-format {
                type enumeration {
                    enum udp                            { value 1; }
                    enum rtp-udp                        { value 2; }
                }
                default "rtp-udp";
                description "Output format";
            }

            ///nokia-conf/configure/service/ies/video-interface/apply-groups
            leaf-list apply-groups {
                type leafref {
                    path "../../../../groups/group/name";
                }
                max-elements 8;
                ordered-by user;
                description "Apply a configuration group at this level";
            }

            ///nokia-conf/configure/service/ies/video-interface/apply-groups-exclude
            leaf-list apply-groups-exclude {
                type leafref {
                    path "../../../../groups/group/name";
                }
                max-elements 8;
                ordered-by user;
                description "Exclude a configuration group at this level";
            }

            ///nokia-conf/configure/service/ies/video-interface/rt-client
            container rt-client {
                status obsolete;
                presence "Enable the rt-client context";
                description "Enable the rt-client context";

                ///nokia-conf/configure/service/ies/video-interface/rt-client/src-address
                leaf src-address {
                    status obsolete;
                    type types-sros:ipv4-unicast-address;
                    mandatory true;
                    description "IP address for the RET client on the video interface";
                }

                ///nokia-conf/configure/service/ies/video-interface/rt-client/apply-groups
                leaf-list apply-groups {
                    status obsolete;
                    type leafref {
                        path "../../../../../groups/group/name";
                    }
                    max-elements 8;
                    ordered-by user;
                    description "Apply a configuration group at this level";
                }

                ///nokia-conf/configure/service/ies/video-interface/rt-client/apply-groups-exclude
                leaf-list apply-groups-exclude {
                    status obsolete;
                    type leafref {
                        path "../../../../../groups/group/name";
                    }
                    max-elements 8;
                    ordered-by user;
                    description "Exclude a configuration group at this level";
                }

            } // container rt-client


            ///nokia-conf/configure/service/ies/video-interface/adi
            container adi {
                status obsolete;
                description "Enter the adi context";

                ///nokia-conf/configure/service/ies/video-interface/adi/scte30
                container scte30 {
                    status obsolete;
                    description "Enter the scte30 context";

                    ///nokia-conf/configure/service/ies/video-interface/adi/scte30/ad-server
                    list ad-server {
                        status obsolete;
                        key "address";
                        max-elements 4;
                        description "Add a list entry for ad-server";

                        ///nokia-conf/configure/service/ies/video-interface/adi/scte30/ad-server/address
                        leaf address {
                            status obsolete;
                            type types-sros:ipv4-address;
                            description "Ad server address";
                        }

                    } // list ad-server

                    ///nokia-conf/configure/service/ies/video-interface/adi/scte30/local-address
                    container local-address {
                        status obsolete;
                        presence "Enable the local-address context";
                        description "Enable the local-address context";

                        ///nokia-conf/configure/service/ies/video-interface/adi/scte30/local-address/control
                        leaf control {
                            status obsolete;
                            type types-sros:ipv4-unicast-address;
                            mandatory true;
                            description "Control";
                        }

                        ///nokia-conf/configure/service/ies/video-interface/adi/scte30/local-address/data
                        leaf data {
                            status obsolete;
                            type types-sros:ipv4-unicast-address;
                            mandatory true;
                            description "Data";
                        }

                        ///nokia-conf/configure/service/ies/video-interface/adi/scte30/local-address/apply-groups
                        leaf-list apply-groups {
                            status obsolete;
                            type leafref {
                                path "../../../../../../../groups/group/name";
                            }
                            max-elements 8;
                            ordered-by user;
                            description "Apply a configuration group at this level";
                        }

                        ///nokia-conf/configure/service/ies/video-interface/adi/scte30/local-address/apply-groups-exclude
                        leaf-list apply-groups-exclude {
                            status obsolete;
                            type leafref {
                                path "../../../../../../../groups/group/name";
                            }
                            max-elements 8;
                            ordered-by user;
                            description "Exclude a configuration group at this level";
                        }

                    } // container local-address

                } // container scte30

            } // container adi

            ///nokia-conf/configure/service/ies/video-interface/video-sap
            container video-sap {
                presence "Enable the video-sap context";
                description "Enable the video-sap context";

                ///nokia-conf/configure/service/ies/video-interface/video-sap/video-group-id
                leaf video-group-id {
                    type leafref {
                        path "../../../../../isa/video-group/video-group-id";
                    }
                    sros-ext:immutable;
                    mandatory true;
                    description "Video group ID";
                }

                ///nokia-conf/configure/service/ies/video-interface/video-sap/apply-groups
                leaf-list apply-groups {
                    type leafref {
                        path "../../../../../groups/group/name";
                    }
                    max-elements 8;
                    ordered-by user;
                    description "Apply a configuration group at this level";
                }

                ///nokia-conf/configure/service/ies/video-interface/video-sap/apply-groups-exclude
                leaf-list apply-groups-exclude {
                    type leafref {
                        path "../../../../../groups/group/name";
                    }
                    max-elements 8;
                    ordered-by user;
                    description "Exclude a configuration group at this level";
                }

                ///nokia-conf/configure/service/ies/video-interface/video-sap/egress
                container egress {
                    description "Enter the egress context";

                    ///nokia-conf/configure/service/ies/video-interface/video-sap/egress/apply-groups
                    leaf-list apply-groups {
                        type leafref {
                            path "../../../../../../groups/group/name";
                        }
                        max-elements 8;
                        ordered-by user;
                        description "Apply a configuration group at this level";
                    }

                    ///nokia-conf/configure/service/ies/video-interface/video-sap/egress/apply-groups-exclude
                    leaf-list apply-groups-exclude {
                        type leafref {
                            path "../../../../../../groups/group/name";
                        }
                        max-elements 8;
                        ordered-by user;
                        description "Exclude a configuration group at this level";
                    }

                    ///nokia-conf/configure/service/ies/video-interface/video-sap/egress/filter
                    container filter {
                        description "Enter the filter context";

                        ///nokia-conf/configure/service/ies/video-interface/video-sap/egress/filter/ip
                        leaf ip {
                            type leafref {
                                path "../../../../../../../filter/ip-filter/filter-name";
                            }
                            description "IPv4 filter policy name";
                        }

                    } // container filter

                    ///nokia-conf/configure/service/ies/video-interface/video-sap/egress/qos
                    container qos {
                        description "Enter the qos context";

                        ///nokia-conf/configure/service/ies/video-interface/video-sap/egress/qos/policy-name
                        leaf policy-name {
                            type leafref {
                                path "../../../../../../../qos/sap-egress/sap-egress-policy-name";
                            }
                            description "SAP egress QoS policy ID";
                        }

                    } // container qos

                } // container egress

                ///nokia-conf/configure/service/ies/video-interface/video-sap/ingress
                container ingress {
                    description "Enable the ingress context";

                    ///nokia-conf/configure/service/ies/video-interface/video-sap/ingress/apply-groups
                    leaf-list apply-groups {
                        type leafref {
                            path "../../../../../../groups/group/name";
                        }
                        max-elements 8;
                        ordered-by user;
                        description "Apply a configuration group at this level";
                    }

                    ///nokia-conf/configure/service/ies/video-interface/video-sap/ingress/apply-groups-exclude
                    leaf-list apply-groups-exclude {
                        type leafref {
                            path "../../../../../../groups/group/name";
                        }
                        max-elements 8;
                        ordered-by user;
                        description "Exclude a configuration group at this level";
                    }

                    ///nokia-conf/configure/service/ies/video-interface/video-sap/ingress/filter
                    container filter {
                        description "Enter the filter context";

                        ///nokia-conf/configure/service/ies/video-interface/video-sap/ingress/filter/ip
                        leaf ip {
                            type leafref {
                                path "../../../../../../../filter/ip-filter/filter-name";
                            }
                            description "IPv4 filter policy name";
                        }

                    } // container filter

                    ///nokia-conf/configure/service/ies/video-interface/video-sap/ingress/qos
                    container qos {
                        description "Enter the qos context";

                        ///nokia-conf/configure/service/ies/video-interface/video-sap/ingress/qos/policy-name
                        leaf policy-name {
                            type leafref {
                                path "../../../../../../../qos/sap-ingress/sap-ingress-policy-name";
                            }
                            description "SAP ingress QoS policy ID";
                        }

                    } // container qos

                } // container ingress

            } // container video-sap

            ///nokia-conf/configure/service/ies/video-interface/address
            list address {
                key "ip-address";
                description "Add a list entry for address";

                ///nokia-conf/configure/service/ies/video-interface/address/ip-address
                leaf ip-address {
                    type types-sros:ipv4-prefix-with-host-bits;
                    description "IPv4 address for the video interface within the service";
                }

            } // list address

            ///nokia-conf/configure/service/ies/video-interface/channel
            list channel {
                key "mcast-address source";
                description "Enter the channel list instance";

                ///nokia-conf/configure/service/ies/video-interface/channel/mcast-address
                leaf mcast-address {
                    type types-sros:ipv4-multicast-address;
                    description "Multicast channel address";
                }

                ///nokia-conf/configure/service/ies/video-interface/channel/source
                leaf source {
                    type types-sros:ipv4-unicast-address;
                    description "Unicast source address";
                }

                ///nokia-conf/configure/service/ies/video-interface/channel/channel-name
                leaf channel-name {
                    type types-sros:named-item;
                    mandatory true;
                    description "Channel name";
                }

                ///nokia-conf/configure/service/ies/video-interface/channel/description
                leaf description {
                    type types-sros:description;
                    description "Text description";
                }

                ///nokia-conf/configure/service/ies/video-interface/channel/scte35-action
                leaf scte35-action {
                    type enumeration {
                        enum forward                        { value 1; }
                        enum drop                           { value 2; }
                    }
                    default "forward";
                    description "Enable downstream forwarding of SCTE 35 cue avails";
                }

                ///nokia-conf/configure/service/ies/video-interface/channel/apply-groups
                leaf-list apply-groups {
                    type leafref {
                        path "../../../../../groups/group/name";
                    }
                    max-elements 8;
                    ordered-by user;
                    description "Apply a configuration group at this level";
                }

                ///nokia-conf/configure/service/ies/video-interface/channel/apply-groups-exclude
                leaf-list apply-groups-exclude {
                    type leafref {
                        path "../../../../../groups/group/name";
                    }
                    max-elements 8;
                    ordered-by user;
                    description "Exclude a configuration group at this level";
                }

                ///nokia-conf/configure/service/ies/video-interface/channel/zone-channel
                list zone-channel {
                    key "zone-mcast-address zone-source";
                    description "Enter the zone-channel list instance";

                    ///nokia-conf/configure/service/ies/video-interface/channel/zone-channel/zone-mcast-address
                    leaf zone-mcast-address {
                        type types-sros:ipv4-multicast-address;
                        description "Multicast zone channel address";
                    }

                    ///nokia-conf/configure/service/ies/video-interface/channel/zone-channel/zone-source
                    leaf zone-source {
                        type types-sros:ipv4-unicast-address;
                        description "Unicast source address";
                    }

                    ///nokia-conf/configure/service/ies/video-interface/channel/zone-channel/adi-channel-name
                    leaf adi-channel-name {
                        type types-sros:named-item;
                        description "Zone channel name";
                    }

                    ///nokia-conf/configure/service/ies/video-interface/channel/zone-channel/apply-groups
                    leaf-list apply-groups {
                        type leafref {
                            path "../../../../../../groups/group/name";
                        }
                        max-elements 8;
                        ordered-by user;
                        description "Apply a configuration group at this level";
                    }

                    ///nokia-conf/configure/service/ies/video-interface/channel/zone-channel/apply-groups-exclude
                    leaf-list apply-groups-exclude {
                        type leafref {
                            path "../../../../../../groups/group/name";
                        }
                        max-elements 8;
                        ordered-by user;
                        description "Exclude a configuration group at this level";
                    }

                } // list zone-channel

            } // list channel

        } // list video-interface

    } // grouping conf-svc-ies-vdo-if-video-interface

}
