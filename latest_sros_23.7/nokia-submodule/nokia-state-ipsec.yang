submodule nokia-state-ipsec {

    yang-version "1.1";

    belongs-to nokia-state { prefix "state"; }

    import ietf-yang-types                { prefix "yang"; }
    import nokia-sros-yang-extensions     { prefix "sros-ext"; }
    import nokia-types-sros               { prefix "types-sros"; }

    sros-ext:sros-major-release "rel23";
    organization "Nokia";
    contact
        "Nokia SR OS Support
         Web: <http://www.nokia.com>";
    description
        "Nokia YANG Data model with operational state for IPsec configuration on SR OS based routers.

         Copyright 2016 Nokia. All rights reserved. Reproduction of this document
         is authorized on the condition that the foregoing copyright notice is included.

         This nokia-state-ipsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-27";

    grouping state-ipsec {
        ///nokia-state/state/ipsec
        container ipsec {
            description "Enable the ipsec context";

            ///nokia-state/state/ipsec/cert-profile
            list cert-profile {
                key "name";
                description "Enter the cert-profile list instance";

                ///nokia-state/state/ipsec/cert-profile/name
                leaf name {
                    type types-sros:named-item;
                    description "Certificate profile name";
                }

                ///nokia-state/state/ipsec/cert-profile/oper-flags
                leaf oper-flags {
                    type bits {
                        bit profile-admin-down             { position 0; }
                        bit invalid-cert-file              { position 1; }
                        bit invalid-key-file               { position 2; }
                        bit invalid-cert-key-combo         { position 3; }
                        bit ca-profile-oper-down           { position 4; }
                        bit invalid-ca-prof-entry          { position 5; }
                    }
                    description
                        "The operational condition of the certificate profile which
                         is aggregated from all its configured entries.";
                }

                ///nokia-state/state/ipsec/cert-profile/oper-state
                leaf oper-state {
                    type types-sros:oper-state;
                    description "The operational status of this certificate profile.";
                }

                ///nokia-state/state/ipsec/cert-profile/entry
                list entry {
                    key "id";
                    description "Enter the entry list instance";

                    ///nokia-state/state/ipsec/cert-profile/entry/id
                    leaf id {
                        type uint32 {
                            range "1..8";
                        }
                        description "Certificate profile entry ID";
                    }

                    ///nokia-state/state/ipsec/cert-profile/entry/computed-chain-status
                    leaf computed-chain-status {
                        type enumeration {
                            enum not-available                  { value 0; }
                            enum partial                        { value 1; }
                            enum complete                       { value 2; }
                        }
                        description "The computed chain status for this certificate profile entry.";
                    }

                    ///nokia-state/state/ipsec/cert-profile/entry/oper-flags
                    leaf oper-flags {
                        type bits {
                            bit profile-admin-down             { position 0; }
                            bit invalid-cert-file              { position 1; }
                            bit invalid-key-file               { position 2; }
                            bit invalid-cert-key-combo         { position 3; }
                            bit ca-profile-oper-down           { position 4; }
                            bit invalid-ca-prof-entry          { position 5; }
                        }
                        description "The operational condition of this certificate profile entry.";
                    }

                    ///nokia-state/state/ipsec/cert-profile/entry/comp-chain-ca-profile
                    list comp-chain-ca-profile {
                        key "order";
                        description "Enter the comp-chain-ca-profile list instance";

                        ///nokia-state/state/ipsec/cert-profile/entry/comp-chain-ca-profile/order
                        leaf order {
                            type uint32;
                            description
                                "Indicates the order in which certificate-authority (CA) profile are maintained
                                 for the computed chain of this certificate profile entry.";
                        }

                        ///nokia-state/state/ipsec/cert-profile/entry/comp-chain-ca-profile/ca-profile
                        leaf ca-profile {
                            type types-sros:named-item;
                            description
                                "The certificate-authority (CA) profile which is part of the computed
                                 chain for this certificate profile entry.";
                        }

                    } // list comp-chain-ca-profile

                } // list entry

            } // list cert-profile

            ///nokia-state/state/ipsec/trust-anchor-profile
            list trust-anchor-profile {
                key "name";
                description "Enter the trust-anchor-profile list instance";

                ///nokia-state/state/ipsec/trust-anchor-profile/name
                leaf name {
                    type types-sros:named-item;
                    description "Trust anchor profile name for IPsec tunnel or gateway";
                }

                ///nokia-state/state/ipsec/trust-anchor-profile/num-of-ca-profile-down
                leaf num-of-ca-profile-down {
                    type int32;
                    description
                        "The total number of trusted Certificate Authority (CA)
                         profiles which are not operational in this trust anchor
                         profile.";
                }

            } // list trust-anchor-profile

            ///nokia-state/state/ipsec/statistics
            container statistics {
                description "Enter the statistics context";

                ///nokia-state/state/ipsec/statistics/tunnel
                container tunnel {
                    description "Enter the tunnel context";

                    ///nokia-state/state/ipsec/statistics/tunnel/total
                    leaf total {
                        type yang:gauge32;
                        description "The number of total IPSec tunnels.";
                    }

                    ///nokia-state/state/ipsec/statistics/tunnel/gateway
                    container gateway {
                        description "Enter the gateway context";

                        ///nokia-state/state/ipsec/statistics/tunnel/gateway/psk
                        leaf psk {
                            type yang:gauge32;
                            description "The number of IPSec gateway tunnels with auth-method set to 'psk'.";
                        }

                        ///nokia-state/state/ipsec/statistics/tunnel/gateway/plain-psk-xauth
                        leaf plain-psk-xauth {
                            type yang:gauge32;
                            description "The number of IPSec gateway tunnels with auth-method set to 'plain-psk-xauth'.";
                        }

                        ///nokia-state/state/ipsec/statistics/tunnel/gateway/cert
                        leaf cert {
                            type yang:gauge32;
                            description "The of IPSec gateway tunnels with auth-method set to 'cert'.";
                        }

                        ///nokia-state/state/ipsec/statistics/tunnel/gateway/psk-radius
                        leaf psk-radius {
                            type yang:gauge32;
                            description "The number of IPSec gateway tunnels with auth-method set to 'psk-radius'.";
                        }

                        ///nokia-state/state/ipsec/statistics/tunnel/gateway/cert-radius
                        leaf cert-radius {
                            type yang:gauge32;
                            description "The number of IPSec gateway tunnels with auth-method set to 'cert-radius'.";
                        }

                        ///nokia-state/state/ipsec/statistics/tunnel/gateway/eap
                        leaf eap {
                            type yang:gauge32;
                            description "The number of IPSec gateway tunnels with auth-method set to 'eap'.";
                        }

                        ///nokia-state/state/ipsec/statistics/tunnel/gateway/auto-eap-radius
                        leaf auto-eap-radius {
                            type yang:gauge32;
                            description "The number of IPsec gateway tunnels with auth-method set to 'auto-eap-radius'.";
                        }

                        ///nokia-state/state/ipsec/statistics/tunnel/gateway/auto-eap
                        leaf auto-eap {
                            type yang:gauge32;
                            description "The number of IPsec gateway tunnels with auth-method set to 'auto-eap'.";
                        }

                        ///nokia-state/state/ipsec/statistics/tunnel/gateway/total
                        leaf total {
                            type yang:gauge64;
                            description "The number of total IPSec gateway tunnels.";
                        }

                    } // container gateway

                } // container tunnel

            } // container statistics

        } // container ipsec

    } // grouping state-ipsec

}
