submodule nokia-conf-port-eth-efm-oam {

    yang-version "1.1";

    belongs-to nokia-conf { prefix "conf"; }

    import nokia-sros-yang-extensions     { prefix "sros-ext"; }
    import nokia-types-port               { prefix "types-port"; }
    import nokia-types-sros               { prefix "types-sros"; }

    include nokia-conf-groups;

    sros-ext:sros-major-release "rel23";
    organization "Nokia";
    contact
        "Nokia SR OS Support
         Web: <http://www.nokia.com>";
    description
        "Nokia YANG Data model to configure ethernet ports supporting efm-oam on SR OS based routers.

         Copyright 2016 Nokia. All rights reserved. Reproduction of this document
         is authorized on the condition that the foregoing copyright notice is included.

         This nokia-conf-port-eth-efm-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-25";

    grouping conf-port-eth-efm-oam {
        ///nokia-conf/configure/port/ethernet/efm-oam
        container efm-oam {
            description "Enable the efm-oam context";

            ///nokia-conf/configure/port/ethernet/efm-oam/accept-remote-loopback
            leaf accept-remote-loopback {
                type boolean;
                default "false";
                description "Enable reactions to loopback control OAMPDUs from peers";
            }

            ///nokia-conf/configure/port/ethernet/efm-oam/admin-state
            leaf admin-state {
                type types-sros:admin-state;
                default "disable";
                description "Administrative state of the EFM OAM operation";
            }

            ///nokia-conf/configure/port/ethernet/efm-oam/dying-gasp-tx-on-reset
            leaf dying-gasp-tx-on-reset {
                type boolean;
                default "true";
                description "Enable generation of the Information OAMPDU off-cycle";
            }

            ///nokia-conf/configure/port/ethernet/efm-oam/grace-tx
            leaf grace-tx {
                type boolean;
                description "Enable the sending of Grace TLV for EFM-OAM";
            }

            ///nokia-conf/configure/port/ethernet/efm-oam/grace-vendor-oui
            leaf grace-vendor-oui {
                type string;
                default "00:16:4D";
                description "Peer vendor OUI to support grace function";
            }

            ///nokia-conf/configure/port/ethernet/efm-oam/hold-time
            leaf hold-time {
                type uint32 {
                    range "1..50";
                }
                units "seconds";
                description "Wait time before protocol returns to operational state";
            }

            ///nokia-conf/configure/port/ethernet/efm-oam/ignore-efm-state
            leaf ignore-efm-state {
                type boolean;
                default "false";
                description "Suppress port state changes for EFM-OAM faults";
            }

            ///nokia-conf/configure/port/ethernet/efm-oam/mode
            leaf mode {
                type enumeration {
                    enum passive                        { value 1; }
                    enum active                         { value 2; }
                }
                default "active";
                description "Mode of OAM operation for the Ethernet port";
            }

            ///nokia-conf/configure/port/ethernet/efm-oam/transmit-interval
            leaf transmit-interval {
                type uint32 {
                    range "1..600";
                }
                units "deciseconds";
                default "10";
                description "Transmit interval of OAMPDUs";
            }

            ///nokia-conf/configure/port/ethernet/efm-oam/multiplier
            leaf multiplier {
                type uint32 {
                    range "2..5";
                }
                default "5";
                description "Multiplier for the transmit interval of OAMPDUs";
            }

            ///nokia-conf/configure/port/ethernet/efm-oam/trigger-fault
            leaf trigger-fault {
                type enumeration {
                    enum dying-gasp                     { value 2; }
                    enum critical-event                 { value 3; }
                }
                description "Flag setting in the information OAMPDU";
            }

            ///nokia-conf/configure/port/ethernet/efm-oam/tunneling
            leaf tunneling {
                type boolean;
                default "false";
                description "Enable EFM-OAM PDU tunneling";
            }

            ///nokia-conf/configure/port/ethernet/efm-oam/apply-groups
            leaf-list apply-groups {
                type leafref {
                    path "../../../../groups/group/name";
                }
                max-elements 8;
                ordered-by user;
                description "Apply a configuration group at this level";
            }

            ///nokia-conf/configure/port/ethernet/efm-oam/apply-groups-exclude
            leaf-list apply-groups-exclude {
                type leafref {
                    path "../../../../groups/group/name";
                }
                max-elements 8;
                ordered-by user;
                description "Exclude a configuration group at this level";
            }

            ///nokia-conf/configure/port/ethernet/efm-oam/discovery
            container discovery {
                description "Enter the discovery context";

                ///nokia-conf/configure/port/ethernet/efm-oam/discovery/advertise-capabilities
                container advertise-capabilities {
                    description "Enter the advertise-capabilities context";

                    ///nokia-conf/configure/port/ethernet/efm-oam/discovery/advertise-capabilities/link-monitoring
                    leaf link-monitoring {
                        type boolean;
                        default "true";
                        description "Advertise link monitoring capabilities to peer";
                    }

                } // container advertise-capabilities

            } // container discovery

            ///nokia-conf/configure/port/ethernet/efm-oam/link-monitoring
            container link-monitoring {
                description "Enable the link-monitoring context";

                ///nokia-conf/configure/port/ethernet/efm-oam/link-monitoring/admin-state
                leaf admin-state {
                    type types-sros:admin-state;
                    default "disable";
                    description "Administrative state of link monitoring on the port";
                }

                ///nokia-conf/configure/port/ethernet/efm-oam/link-monitoring/apply-groups
                leaf-list apply-groups {
                    type leafref {
                        path "../../../../../groups/group/name";
                    }
                    max-elements 8;
                    ordered-by user;
                    description "Apply a configuration group at this level";
                }

                ///nokia-conf/configure/port/ethernet/efm-oam/link-monitoring/apply-groups-exclude
                leaf-list apply-groups-exclude {
                    type leafref {
                        path "../../../../../groups/group/name";
                    }
                    max-elements 8;
                    ordered-by user;
                    description "Exclude a configuration group at this level";
                }

                ///nokia-conf/configure/port/ethernet/efm-oam/link-monitoring/errored-frame
                container errored-frame {
                    description "Enter the errored-frame context";

                    ///nokia-conf/configure/port/ethernet/efm-oam/link-monitoring/errored-frame/admin-state
                    leaf admin-state {
                        type types-sros:admin-state;
                        default "disable";
                        description "Administrative state of link monitoring on the port";
                    }

                    ///nokia-conf/configure/port/ethernet/efm-oam/link-monitoring/errored-frame/event-notification
                    leaf event-notification {
                        type boolean;
                        default "true";
                        description "Transmit Event Notification OAMPDU with link event TLV";
                    }

                    ///nokia-conf/configure/port/ethernet/efm-oam/link-monitoring/errored-frame/sd-threshold
                    leaf sd-threshold {
                        type uint32 {
                            range "1..1000000";
                        }
                        description "SD threshold";
                    }

                    ///nokia-conf/configure/port/ethernet/efm-oam/link-monitoring/errored-frame/sf-threshold
                    leaf sf-threshold {
                        type uint32 {
                            range "1..1000000";
                        }
                        default "1";
                        description "SF threshold";
                    }

                    ///nokia-conf/configure/port/ethernet/efm-oam/link-monitoring/errored-frame/window
                    leaf window {
                        type uint32 {
                            range "10..600";
                        }
                        units "deciseconds";
                        default "10";
                        description "Window size";
                    }

                } // container errored-frame

                ///nokia-conf/configure/port/ethernet/efm-oam/link-monitoring/errored-frame-period
                container errored-frame-period {
                    description "Enter the errored-frame-period context";

                    ///nokia-conf/configure/port/ethernet/efm-oam/link-monitoring/errored-frame-period/admin-state
                    leaf admin-state {
                        type types-sros:admin-state;
                        default "disable";
                        description "Administrative state of link monitoring on the port";
                    }

                    ///nokia-conf/configure/port/ethernet/efm-oam/link-monitoring/errored-frame-period/event-notification
                    leaf event-notification {
                        type boolean;
                        default "true";
                        description "Transmit Event Notification OAMPDU with link event TLV";
                    }

                    ///nokia-conf/configure/port/ethernet/efm-oam/link-monitoring/errored-frame-period/sd-threshold
                    leaf sd-threshold {
                        type uint32 {
                            range "1..1000000";
                        }
                        description "SD threshold";
                    }

                    ///nokia-conf/configure/port/ethernet/efm-oam/link-monitoring/errored-frame-period/sf-threshold
                    leaf sf-threshold {
                        type uint32 {
                            range "1..1000000";
                        }
                        default "1";
                        description "SF threshold";
                    }

                    ///nokia-conf/configure/port/ethernet/efm-oam/link-monitoring/errored-frame-period/window
                    leaf window {
                        type uint32 {
                            range "1..4294967295";
                        }
                        units "packets";
                        default "1488095";
                        description "Window size";
                    }

                } // container errored-frame-period

                ///nokia-conf/configure/port/ethernet/efm-oam/link-monitoring/errored-frame-seconds
                container errored-frame-seconds {
                    description "Enter the errored-frame-seconds context";

                    ///nokia-conf/configure/port/ethernet/efm-oam/link-monitoring/errored-frame-seconds/admin-state
                    leaf admin-state {
                        type types-sros:admin-state;
                        default "disable";
                        description "Administrative state of link monitoring on the port";
                    }

                    ///nokia-conf/configure/port/ethernet/efm-oam/link-monitoring/errored-frame-seconds/event-notification
                    leaf event-notification {
                        type boolean;
                        default "true";
                        description "Transmit Event Notification OAMPDU with link event TLV";
                    }

                    ///nokia-conf/configure/port/ethernet/efm-oam/link-monitoring/errored-frame-seconds/sd-threshold
                    leaf sd-threshold {
                        type uint32 {
                            range "1..900";
                        }
                        description "SD threshold";
                    }

                    ///nokia-conf/configure/port/ethernet/efm-oam/link-monitoring/errored-frame-seconds/sf-threshold
                    leaf sf-threshold {
                        type uint32 {
                            range "1..900";
                        }
                        default "1";
                        description "SF threshold";
                    }

                    ///nokia-conf/configure/port/ethernet/efm-oam/link-monitoring/errored-frame-seconds/window
                    leaf window {
                        type uint32 {
                            range "100..9000";
                        }
                        units "deciseconds";
                        default "600";
                        description "Window size";
                    }

                } // container errored-frame-seconds

                ///nokia-conf/configure/port/ethernet/efm-oam/link-monitoring/errored-symbols
                container errored-symbols {
                    description "Enter the errored-symbols context";

                    ///nokia-conf/configure/port/ethernet/efm-oam/link-monitoring/errored-symbols/admin-state
                    leaf admin-state {
                        type types-sros:admin-state;
                        default "disable";
                        description "Administrative state of link monitoring on the port";
                    }

                    ///nokia-conf/configure/port/ethernet/efm-oam/link-monitoring/errored-symbols/event-notification
                    leaf event-notification {
                        type boolean;
                        default "true";
                        description "Transmit Event Notification OAMPDU with link event TLV";
                    }

                    ///nokia-conf/configure/port/ethernet/efm-oam/link-monitoring/errored-symbols/sd-threshold
                    leaf sd-threshold {
                        type uint32 {
                            range "1..1000000";
                        }
                        description "SD threshold";
                    }

                    ///nokia-conf/configure/port/ethernet/efm-oam/link-monitoring/errored-symbols/sf-threshold
                    leaf sf-threshold {
                        type uint32 {
                            range "1..1000000";
                        }
                        default "1";
                        description "SF threshold";
                    }

                    ///nokia-conf/configure/port/ethernet/efm-oam/link-monitoring/errored-symbols/window
                    leaf window {
                        type uint32 {
                            range "10..600";
                        }
                        units "deciseconds";
                        default "10";
                        description "Window size";
                    }

                } // container errored-symbols

                ///nokia-conf/configure/port/ethernet/efm-oam/link-monitoring/local-sf-action
                container local-sf-action {
                    description "Enter the local-sf-action context";

                    ///nokia-conf/configure/port/ethernet/efm-oam/link-monitoring/local-sf-action/event-notification-burst
                    leaf event-notification-burst {
                        type uint32 {
                            range "1..5";
                        }
                        units "packets";
                        default "1";
                        description "Number of OAMPDUs to send when SF threshold is reached";
                    }

                    ///nokia-conf/configure/port/ethernet/efm-oam/link-monitoring/local-sf-action/local-port-action
                    leaf local-port-action {
                        type types-port:efm-oam-local-port-action;
                        default "port-out-of-service";
                        description "Local port action when SF threshold is reached";
                    }

                    ///nokia-conf/configure/port/ethernet/efm-oam/link-monitoring/local-sf-action/info-notification
                    container info-notification {
                        description "Enter the info-notification context";

                        ///nokia-conf/configure/port/ethernet/efm-oam/link-monitoring/local-sf-action/info-notification/critical-event
                        leaf critical-event {
                            type boolean;
                            default "false";
                            description "Set critical event flag when SF threshold is reached";
                        }

                        ///nokia-conf/configure/port/ethernet/efm-oam/link-monitoring/local-sf-action/info-notification/dying-gasp
                        leaf dying-gasp {
                            type boolean;
                            default "false";
                            description "Set dying gasp flag when SF threshold is reached";
                        }

                    } // container info-notification

                } // container local-sf-action

            } // container link-monitoring

            ///nokia-conf/configure/port/ethernet/efm-oam/peer-rdi-rx
            container peer-rdi-rx {
                description "Enter the peer-rdi-rx context";

                ///nokia-conf/configure/port/ethernet/efm-oam/peer-rdi-rx/critical-event
                leaf critical-event {
                    type types-port:efm-oam-local-port-action;
                    default "port-out-of-service";
                    description "Action taken upon receipt of critical event flag";
                }

                ///nokia-conf/configure/port/ethernet/efm-oam/peer-rdi-rx/dying-gasp
                leaf dying-gasp {
                    type types-port:efm-oam-local-port-action;
                    default "port-out-of-service";
                    description "Action taken upon receipt of dying gasp flag";
                }

                ///nokia-conf/configure/port/ethernet/efm-oam/peer-rdi-rx/event-notification
                leaf event-notification {
                    type types-port:efm-oam-local-port-action;
                    default "log-only";
                    description "Action taken upon receipt of event TLVs";
                }

                ///nokia-conf/configure/port/ethernet/efm-oam/peer-rdi-rx/link-fault
                leaf link-fault {
                    type types-port:efm-oam-local-port-action;
                    default "port-out-of-service";
                    description "Action taken upon receipt of link fault flag";
                }

            } // container peer-rdi-rx

        } // container efm-oam

    } // grouping conf-port-eth-efm-oam

}
