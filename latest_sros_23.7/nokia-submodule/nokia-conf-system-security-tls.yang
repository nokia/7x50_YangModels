submodule nokia-conf-system-security-tls {

    yang-version "1.1";

    belongs-to nokia-conf { prefix "conf"; }

    import nokia-sros-yang-extensions     { prefix "sros-ext"; }
    import nokia-types-sros               { prefix "types-sros"; }

    include nokia-conf-groups;
    include nokia-conf-system;
    include nokia-conf-system-security;
    include nokia-conf-system-security-pki;

    sros-ext:sros-major-release "rel23";
    organization "Nokia";
    contact
        "Nokia SR OS Support
         Web: <http://www.nokia.com>";
    description
        "Nokia YANG Data model to configure system security tls parameters. on SR OS based routers.

         Copyright 2016 Nokia. All rights reserved. Reproduction of this document
         is authorized on the condition that the foregoing copyright notice is included.

         This nokia-conf-system-security-tls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-03-08";

    grouping conf-system-security-tls {
        container tls {
            description "Enter the tls context";

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            list cert-profile {
                key "cert-profile-name";
                max-elements 16;
                description "Enter the cert-profile list instance";

                leaf cert-profile-name {
                    type types-sros:named-item;
                    description "TLS certificate profile name";
                }

                leaf admin-state {
                    type types-sros:admin-state;
                    default "disable";
                    description "Administrative state of the certificate profile";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list entry {
                    key "entry-id";
                    max-elements 8;
                    description "Enter the entry list instance";

                    leaf entry-id {
                        type int32 {
                            range "1..8";
                        }
                        description "Certificate profile ID";
                    }

                    leaf certificate-file {
                        type types-sros:string-not-all-spaces {
                            length "1..95";
                            pattern "[^:\\\\/]+";
                        }
                        description "Certificate file name";
                    }

                    leaf key-file {
                        type types-sros:string-not-all-spaces {
                            length "1..95";
                            pattern "[^:\\\\/]+";
                        }
                        description "Key file name";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container send-chain {
                        description "Enter the send-chain context";

                        list ca-profile {
                            key "ca-profile-name";
                            max-elements 7;
                            description "Add a list entry for ca-profile";

                            leaf ca-profile-name {
                                type leafref {
                                    path "../../../../../../pki/ca-profile/ca-profile-name";
                                }
                                description "CA profile name";
                            }

                        } // list ca-profile

                    } // container send-chain

                } // list entry

            } // list cert-profile

            list client-cipher-list {
                key "client-cipher-list-name";
                max-elements 16;
                description "Enter the client-cipher-list list instance";

                leaf client-cipher-list-name {
                    type types-sros:named-item;
                    description "Client cipher list name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list cipher {
                    status obsolete;
                    key "index";
                    description "Enter the cipher list instance";

                    leaf index {
                        status obsolete;
                        type uint32 {
                            range "1..255";
                        }
                        description "Index of the cipher";
                    }

                    leaf name {
                        status obsolete;
                        type enumeration {
                            enum tls-rsa-with3des-ede-cbc-sha   { value 10; }
                            enum tls-rsa-with-aes128-cbc-sha    { value 47; }
                            enum tls-rsa-with-aes256-cbc-sha    { value 53; }
                            enum tls-rsa-with-aes128-cbc-sha256 { value 60; }
                            enum tls-rsa-with-aes256-cbc-sha256 { value 61; }
                            enum tls-rsa-with-aes128-gcm-sha256 { value 156; }
                            enum tls-rsa-with-aes256-gcm-sha384 { value 157; }
                            enum tls-rsa-with-null-md5          { status obsolete; }
                            enum tls-rsa-with-null-sha          { status obsolete; }
                            enum tls-rsa-with-null-sha256       { status obsolete; }
                        }
                        mandatory true;
                        description "Cipher suite code value";
                    }

                    leaf-list apply-groups {
                        status obsolete;
                        type leafref {
                            path "../../../../../../groups/group/name";
                        }
                        max-elements 8;
                        ordered-by user;
                        description "Apply a configuration group at this level";
                    }

                    leaf-list apply-groups-exclude {
                        status obsolete;
                        type leafref {
                            path "../../../../../../groups/group/name";
                        }
                        max-elements 8;
                        ordered-by user;
                        description "Exclude a configuration group at this level";
                    }

                } // list cipher

                list tls12-cipher {
                    key "index";
                    description "Enter the tls12-cipher list instance";

                    leaf index {
                        type uint32 {
                            range "1..255";
                        }
                        description "Index of the cipher";
                    }

                    leaf name {
                        type enumeration {
                            enum tls-rsa-with3des-ede-cbc-sha   { value 10; }
                            enum tls-rsa-with-aes128-cbc-sha    { value 47; }
                            enum tls-rsa-with-aes256-cbc-sha    { value 53; }
                            enum tls-rsa-with-aes128-cbc-sha256 { value 60; }
                            enum tls-rsa-with-aes256-cbc-sha256 { value 61; }
                            enum tls-rsa-with-aes128-gcm-sha256 { value 156; }
                            enum tls-rsa-with-aes256-gcm-sha384 { value 157; }
                        }
                        mandatory true;
                        description "Cipher suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls12-cipher

                list tls13-cipher {
                    key "index";
                    description "Enter the tls13-cipher list instance";

                    leaf index {
                        type uint32 {
                            range "1..255";
                        }
                        description "Index number of the TLS 1.3 cipher";
                    }

                    leaf name {
                        type enumeration {
                            enum tls-aes256-gcm-sha384          { value 4865; }
                            enum tls-aes128-gcm-sha256          { value 4866; }
                            enum tls-chacha20-poly1305-sha256   { value 4867; }
                            enum tls-aes128-ccm8-sha256         { value 4868; }
                            enum tls-aes128-ccm-sha256          { value 4869; }
                        }
                        mandatory true;
                        description "Name of the TLS 1.3 cipher suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-cipher

            } // list client-cipher-list

            list client-group-list {
                key "client-group-list-name";
                max-elements 16;
                description "Enter the client-group-list list instance";

                leaf client-group-list-name {
                    type types-sros:named-item;
                    description "Name of the TLS client group list";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list tls13-group {
                    key "index";
                    description "Enter the tls13-group list instance";

                    leaf index {
                        type uint32 {
                            range "1..255";
                        }
                        description "Index number of the TLS 1.3 group";
                    }

                    leaf name {
                        type enumeration {
                            enum tls-ecdhe-256                  { value 23; }
                            enum tls-ecdhe-384                  { value 24; }
                            enum tls-ecdhe-521                  { value 25; }
                            enum tls-x25519                     { value 29; }
                            enum tls-x448                       { value 30; }
                        }
                        mandatory true;
                        description "Name of the TLS 1.3 group suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-group

            } // list client-group-list

            list client-signature-list {
                key "client-signature-list-name";
                max-elements 16;
                description "Enter the client-signature-list list instance";

                leaf client-signature-list-name {
                    type types-sros:named-item;
                    description "Name of the TLS 1.3 client signature list";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list tls13-signature {
                    key "index";
                    description "Enter the tls13-signature list instance";

                    leaf index {
                        type uint32 {
                            range "1..255";
                        }
                        description "Index number of the TLS 1.3 signature";
                    }

                    leaf name {
                        type enumeration {
                            enum tls-rsa-pkcs1-sha256           { value 1025; }
                            enum tls-ecdsa-secp256r1-sha256     { value 1027; }
                            enum tls-rsa-pkcs1-sha384           { value 1281; }
                            enum tls-ecdsa-secp384r1-sha384     { value 1283; }
                            enum tls-rsa-pkcs1-sha512           { value 1537; }
                            enum tls-ecdsa-secp521r1-sha512     { value 1539; }
                            enum tls-rsa-pss-rsae-sha256        { value 2052; }
                            enum tls-rsa-pss-rsae-sha384        { value 2053; }
                            enum tls-rsa-pss-rsae-sha512        { value 2054; }
                            enum tls-ed25519                    { value 2055; }
                            enum tls-ed448                      { value 2056; }
                            enum tls-rsa-pss-pss-sha256         { value 2057; }
                            enum tls-rsa-pss-pss-sha384         { value 2058; }
                            enum tls-rsa-pss-pss-sha512         { value 2059; }
                        }
                        mandatory true;
                        description "Name of the TLS 1.3 signature suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-signature

            } // list client-signature-list

            list server-cipher-list {
                key "server-cipher-list-name";
                max-elements 16;
                description "Enter the server-cipher-list list instance";

                leaf server-cipher-list-name {
                    type types-sros:named-item;
                    description "Server cipher list name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list cipher {
                    status obsolete;
                    key "index";
                    description "Enter the cipher list instance";

                    leaf index {
                        status obsolete;
                        type uint32 {
                            range "1..255";
                        }
                        description "Index of the cipher";
                    }

                    leaf name {
                        status obsolete;
                        type enumeration {
                            enum tls-rsa-with3des-ede-cbc-sha   { value 10; }
                            enum tls-rsa-with-aes128-cbc-sha    { value 47; }
                            enum tls-rsa-with-aes256-cbc-sha    { value 53; }
                            enum tls-rsa-with-aes128-cbc-sha256 { value 60; }
                            enum tls-rsa-with-aes256-cbc-sha256 { value 61; }
                            enum tls-rsa-with-aes128-gcm-sha256 { value 156; }
                            enum tls-rsa-with-aes256-gcm-sha384 { value 157; }
                            enum tls-rsa-with-null-md5          { status obsolete; }
                            enum tls-rsa-with-null-sha          { status obsolete; }
                            enum tls-rsa-with-null-sha256       { status obsolete; }
                        }
                        mandatory true;
                        description "Cipher suite code value";
                    }

                    leaf-list apply-groups {
                        status obsolete;
                        type leafref {
                            path "../../../../../../groups/group/name";
                        }
                        max-elements 8;
                        ordered-by user;
                        description "Apply a configuration group at this level";
                    }

                    leaf-list apply-groups-exclude {
                        status obsolete;
                        type leafref {
                            path "../../../../../../groups/group/name";
                        }
                        max-elements 8;
                        ordered-by user;
                        description "Exclude a configuration group at this level";
                    }

                } // list cipher

                list tls12-cipher {
                    key "index";
                    description "Enter the tls12-cipher list instance";

                    leaf index {
                        type uint32 {
                            range "1..255";
                        }
                        description "Index of the cipher";
                    }

                    leaf name {
                        type enumeration {
                            enum tls-rsa-with3des-ede-cbc-sha   { value 10; }
                            enum tls-rsa-with-aes128-cbc-sha    { value 47; }
                            enum tls-rsa-with-aes256-cbc-sha    { value 53; }
                            enum tls-rsa-with-aes128-cbc-sha256 { value 60; }
                            enum tls-rsa-with-aes256-cbc-sha256 { value 61; }
                            enum tls-rsa-with-aes128-gcm-sha256 { value 156; }
                            enum tls-rsa-with-aes256-gcm-sha384 { value 157; }
                        }
                        mandatory true;
                        description "Cipher suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls12-cipher

                list tls13-cipher {
                    key "index";
                    description "Enter the tls13-cipher list instance";

                    leaf index {
                        type uint32 {
                            range "1..255";
                        }
                        description "Index number of the TLS 1.3 cipher";
                    }

                    leaf name {
                        type enumeration {
                            enum tls-aes256-gcm-sha384          { value 4865; }
                            enum tls-aes128-gcm-sha256          { value 4866; }
                            enum tls-chacha20-poly1305-sha256   { value 4867; }
                            enum tls-aes128-ccm8-sha256         { value 4868; }
                            enum tls-aes128-ccm-sha256          { value 4869; }
                        }
                        mandatory true;
                        description "Name of the TLS 1.3 cipher suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-cipher

            } // list server-cipher-list

            list server-group-list {
                key "server-group-list-name";
                max-elements 16;
                description "Enter the server-group-list list instance";

                leaf server-group-list-name {
                    type types-sros:named-item;
                    description "Name of the TLS server group list";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list tls13-group {
                    key "index";
                    description "Enter the tls13-group list instance";

                    leaf index {
                        type uint32 {
                            range "1..255";
                        }
                        description "Index number of the TLS 1.3 group";
                    }

                    leaf name {
                        type enumeration {
                            enum tls-ecdhe-256                  { value 23; }
                            enum tls-ecdhe-384                  { value 24; }
                            enum tls-ecdhe-521                  { value 25; }
                            enum tls-x25519                     { value 29; }
                            enum tls-x448                       { value 30; }
                        }
                        mandatory true;
                        description "Name of the TLS 1.3 group suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-group

            } // list server-group-list

            list server-signature-list {
                key "server-signature-list-name";
                max-elements 16;
                description "Enter the server-signature-list list instance";

                leaf server-signature-list-name {
                    type types-sros:named-item;
                    description "Name of the TLS 1.3 server signature list";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list tls13-signature {
                    key "index";
                    description "Enter the tls13-signature list instance";

                    leaf index {
                        type uint32 {
                            range "1..255";
                        }
                        description "Index number of the TLS 1.3 signature";
                    }

                    leaf name {
                        type enumeration {
                            enum tls-rsa-pkcs1-sha256           { value 1025; }
                            enum tls-ecdsa-secp256r1-sha256     { value 1027; }
                            enum tls-rsa-pkcs1-sha384           { value 1281; }
                            enum tls-ecdsa-secp384r1-sha384     { value 1283; }
                            enum tls-rsa-pkcs1-sha512           { value 1537; }
                            enum tls-ecdsa-secp521r1-sha512     { value 1539; }
                            enum tls-rsa-pss-rsae-sha256        { value 2052; }
                            enum tls-rsa-pss-rsae-sha384        { value 2053; }
                            enum tls-rsa-pss-rsae-sha512        { value 2054; }
                            enum tls-ed25519                    { value 2055; }
                            enum tls-ed448                      { value 2056; }
                            enum tls-rsa-pss-pss-sha256         { value 2057; }
                            enum tls-rsa-pss-pss-sha384         { value 2058; }
                            enum tls-rsa-pss-pss-sha512         { value 2059; }
                        }
                        mandatory true;
                        description "Name of the TLS 1.3 signature suite code";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list tls13-signature

            } // list server-signature-list

            list client-tls-profile {
                key "client-profile-name";
                max-elements 16;
                description "Enter the client-tls-profile list instance";

                leaf client-profile-name {
                    type types-sros:named-item;
                    description "Client TLS profile name";
                }

                leaf cert-profile {
                    type leafref {
                        path "../../cert-profile/cert-profile-name";
                    }
                    description "Certificate profile ID";
                }

                leaf cipher-list {
                    type leafref {
                        path "../../client-cipher-list/client-cipher-list-name";
                    }
                    description "Cipher list for negotiation in the client Hello message";
                }

                leaf admin-state {
                    type types-sros:admin-state;
                    default "disable";
                    description "Administrative state of the client TLS profile";
                }

                leaf trust-anchor-profile {
                    type leafref {
                        path "../../trust-anchor-profile/trust-anchor-profile-name";
                    }
                    description "Trust anchor profile";
                }

                leaf group-list {
                    type leafref {
                        path "../../client-group-list/client-group-list-name";
                    }
                    description "Name of the list of supported group suite codes";
                }

                leaf signature-list {
                    type leafref {
                        path "../../client-signature-list/client-signature-list-name";
                    }
                    description "Name of the list of supported signature suite codes";
                }

                leaf protocol-version {
                    type types-sros:tls-protocol-version;
                    default "tls-version-12";
                    description "TLS protocol version used by the TLS client profile";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container status-verify {
                    description "Enter the status-verify context";

                    leaf default-result {
                        type types-sros:tls-status-verify;
                        default "revoked";
                        description "Default result of certificate status verification";
                    }

                } // container status-verify

            } // list client-tls-profile

            list server-tls-profile {
                key "server-profile-name";
                max-elements 16;
                description "Enter the server-tls-profile list instance";

                leaf server-profile-name {
                    type types-sros:named-item;
                    description "TLS server profile name";
                }

                leaf cert-profile {
                    type leafref {
                        path "../../cert-profile/cert-profile-name";
                    }
                    description "Certificate profile ID";
                }

                leaf tls-re-negotiate-timer {
                    type uint32 {
                        range "0..65000";
                    }
                    units "minutes";
                    default "0";
                    description "TLS HELLO request timer";
                }

                leaf cipher-list {
                    type leafref {
                        path "../../server-cipher-list/server-cipher-list-name";
                    }
                    description "Cipher list used by the TLS server profile";
                }

                leaf group-list {
                    type leafref {
                        path "../../server-group-list/server-group-list-name";
                    }
                    description "Name of the list of supported group suite codes";
                }

                leaf signature-list {
                    type leafref {
                        path "../../server-signature-list/server-signature-list-name";
                    }
                    description "Name of the list of supported signature suite codes";
                }

                leaf protocol-version {
                    type types-sros:tls-protocol-version;
                    default "tls-version-12";
                    description "TLS protocol version used by the TLS server profile";
                }

                leaf admin-state {
                    type types-sros:admin-state;
                    default "disable";
                    description "Administrative state of the server TLS profile";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container status-verify {
                    description "Enter the status-verify context";

                    leaf default-result {
                        type types-sros:tls-status-verify;
                        default "revoked";
                        description "Default result of certificate status verification";
                    }

                } // container status-verify

                container authenticate-client {
                    description "Enter the authenticate-client context";

                    leaf trust-anchor-profile {
                        type leafref {
                            path "../../../trust-anchor-profile/trust-anchor-profile-name";
                        }
                        description "Trust anchor profile for client authentication";
                    }

                    leaf common-name-list {
                        type leafref {
                            path "../../../../pki/common-name-list/cn-list-name";
                        }
                        description "Common name list for client certificate authentication";
                    }

                } // container authenticate-client

            } // list server-tls-profile

            list trust-anchor-profile {
                key "trust-anchor-profile-name";
                max-elements 16;
                description "Enter the trust-anchor-profile list instance";

                leaf trust-anchor-profile-name {
                    type types-sros:named-item;
                    description "Trust anchor profile name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list trust-anchor {
                    key "ca-profile-name";
                    max-elements 8;
                    description "Add a list entry for trust-anchor";

                    leaf ca-profile-name {
                        type leafref {
                            path "../../../../pki/ca-profile/ca-profile-name";
                        }
                        description "Trusted CA profile name";
                    }

                } // list trust-anchor

            } // list trust-anchor-profile

        } // container tls

    } // grouping conf-system-security-tls

}
