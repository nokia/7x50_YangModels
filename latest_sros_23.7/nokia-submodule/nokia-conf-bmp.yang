submodule nokia-conf-bmp {

    yang-version "1.1";

    belongs-to nokia-conf { prefix "conf"; }

    import nokia-sros-yang-extensions     { prefix "sros-ext"; }
    import nokia-types-sros               { prefix "types-sros"; }

    include nokia-conf-groups;
    include nokia-conf-system;
    include nokia-conf-system-security;

    sros-ext:sros-major-release "rel23";
    organization "Nokia";
    contact
        "Nokia SR OS Support
         Web: <http://www.nokia.com>";
    description
        "Nokia YANG Data model to configure BGP Monitoring Protocol on SR OS based routers.

         Copyright 2016 Nokia. All rights reserved. Reproduction of this document
         is authorized on the condition that the foregoing copyright notice is included.

         This nokia-conf-bmp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-10-14";

    grouping conf-bmp {
        ///nokia-conf/configure/bmp
        container bmp {
            description "Enable the bmp context";

            ///nokia-conf/configure/bmp/admin-state
            leaf admin-state {
                type types-sros:admin-state;
                default "disable";
                description "Administrative state of the BMP operation";
            }

            ///nokia-conf/configure/bmp/apply-groups
            leaf-list apply-groups {
                type leafref {
                    path "../../groups/group/name";
                }
                max-elements 8;
                ordered-by user;
                description "Apply a configuration group at this level";
            }

            ///nokia-conf/configure/bmp/apply-groups-exclude
            leaf-list apply-groups-exclude {
                type leafref {
                    path "../../groups/group/name";
                }
                max-elements 8;
                ordered-by user;
                description "Exclude a configuration group at this level";
            }

            ///nokia-conf/configure/bmp/collector
            container collector {
                description "Enable the collector context";

                ///nokia-conf/configure/bmp/collector/admin-state
                leaf admin-state {
                    type types-sros:admin-state;
                    default "disable";
                    description "Administrative state of the BMP collector";
                }

                ///nokia-conf/configure/bmp/collector/apply-groups
                leaf-list apply-groups {
                    type leafref {
                        path "../../../groups/group/name";
                    }
                    max-elements 8;
                    ordered-by user;
                    sros-ext:auto-restart-to-modify;
                    description "Apply a configuration group at this level";
                }

                ///nokia-conf/configure/bmp/collector/apply-groups-exclude
                leaf-list apply-groups-exclude {
                    type leafref {
                        path "../../../groups/group/name";
                    }
                    max-elements 8;
                    ordered-by user;
                    sros-ext:auto-restart-to-modify;
                    description "Exclude a configuration group at this level";
                }

                ///nokia-conf/configure/bmp/collector/connection
                container connection {
                    sros-ext:auto-restart-to-modify;
                    description "Enter the connection context";

                    ///nokia-conf/configure/bmp/collector/connection/ipv4
                    container ipv4 {
                        sros-ext:auto-restart-to-modify;
                        description "Enter the ipv4 context";

                        ///nokia-conf/configure/bmp/collector/connection/ipv4/address
                        leaf address {
                            type types-sros:ipv4-unicast-address;
                            sros-ext:auto-restart-to-modify;
                            description "IPv4 address";
                        }

                        ///nokia-conf/configure/bmp/collector/connection/ipv4/port
                        leaf port {
                            type types-sros:tcp-udp-port-non-zero;
                            sros-ext:auto-restart-to-modify;
                            default "4210";
                            description "IPv4 TCP destination port number";
                        }

                    } // container ipv4

                    ///nokia-conf/configure/bmp/collector/connection/ipv6
                    container ipv6 {
                        sros-ext:auto-restart-to-modify;
                        description "Enter the ipv6 context";

                        ///nokia-conf/configure/bmp/collector/connection/ipv6/address
                        leaf address {
                            type types-sros:ipv6-unicast-address;
                            sros-ext:auto-restart-to-modify;
                            description "IPv6 address";
                        }

                        ///nokia-conf/configure/bmp/collector/connection/ipv6/port
                        leaf port {
                            type types-sros:tcp-udp-port-non-zero;
                            sros-ext:auto-restart-to-modify;
                            default "4210";
                            description "IPv6 TCP destination port";
                        }

                    } // container ipv6

                } // container connection

            } // container collector

            ///nokia-conf/configure/bmp/station
            list station {
                key "name";
                max-elements 8;
                description "Enter the station list instance";

                ///nokia-conf/configure/bmp/station/name
                leaf name {
                    type types-sros:named-item;
                    description "BMP monitoring station name";
                }

                ///nokia-conf/configure/bmp/station/description
                leaf description {
                    type types-sros:description;
                    description "Text description";
                }

                ///nokia-conf/configure/bmp/station/admin-state
                leaf admin-state {
                    type types-sros:admin-state;
                    default "disable";
                    description "Administrative state of the BMP monitoring station";
                }

                ///nokia-conf/configure/bmp/station/initiation-message
                leaf initiation-message {
                    type string {
                        length "1..255";
                    }
                    description "Free form initiation message sent to monitoring station";
                }

                ///nokia-conf/configure/bmp/station/stats-report-interval
                leaf stats-report-interval {
                    type types-sros:time-duration {
                        range "15..65535";
                    }
                    units "seconds";
                    description "Frequency of reports sent to the BMP monitoring station";
                }

                ///nokia-conf/configure/bmp/station/report-local-routes
                leaf report-local-routes {
                    type boolean;
                    default "false";
                    description "Allow local route reporting to BMP monitoring station";
                }

                ///nokia-conf/configure/bmp/station/apply-groups
                leaf-list apply-groups {
                    type leafref {
                        path "../../../groups/group/name";
                    }
                    max-elements 8;
                    ordered-by user;
                    description "Apply a configuration group at this level";
                }

                ///nokia-conf/configure/bmp/station/apply-groups-exclude
                leaf-list apply-groups-exclude {
                    type leafref {
                        path "../../../groups/group/name";
                    }
                    max-elements 8;
                    ordered-by user;
                    description "Exclude a configuration group at this level";
                }


                ///nokia-conf/configure/bmp/station/connection
                container connection {
                    description "Enter the connection context";

                    ///nokia-conf/configure/bmp/station/connection/connect-retry
                    leaf connect-retry {
                        type types-sros:time-duration {
                            range "1..65535";
                        }
                        units "seconds";
                        default "120";
                        description "Maximum time between connection attempts";
                    }

                    ///nokia-conf/configure/bmp/station/connection/local-address
                    leaf local-address {
                        type types-sros:ip-unicast-address;
                        description "Local IP address to communicate with monitoring station";
                    }

                    ///nokia-conf/configure/bmp/station/connection/router-instance
                    leaf router-instance {
                        type string;
                        default "Base";
                        description "Router instance used to reach the BMP station";
                    }

                    ///nokia-conf/configure/bmp/station/connection/station-address
                    container station-address {
                        description "Enter the station-address context";

                        ///nokia-conf/configure/bmp/station/connection/station-address/ip-address
                        leaf ip-address {
                            type types-sros:ip-unicast-address;
                            description "IP address of the remote BMP monitoring station";
                        }

                        ///nokia-conf/configure/bmp/station/connection/station-address/port
                        leaf port {
                            type types-sros:tcp-udp-port-non-zero;
                            description "BMP monitoring station port";
                        }

                    } // container station-address

                    ///nokia-conf/configure/bmp/station/connection/tcp-keepalive
                    container tcp-keepalive {
                        description "Enter the tcp-keepalive context";

                        ///nokia-conf/configure/bmp/station/connection/tcp-keepalive/admin-state
                        leaf admin-state {
                            type types-sros:admin-state;
                            default "disable";
                            description "Administrative state of the TCP keepalive";
                        }

                        ///nokia-conf/configure/bmp/station/connection/tcp-keepalive/keep-idle
                        leaf keep-idle {
                            type types-sros:time-duration {
                                range "1..100000";
                            }
                            units "seconds";
                            default "600";
                            description "Time until the first TCP keepalive probe is sent";
                        }

                        ///nokia-conf/configure/bmp/station/connection/tcp-keepalive/keep-interval
                        leaf keep-interval {
                            type types-sros:time-duration {
                                range "1..100000";
                            }
                            units "seconds";
                            default "15";
                            description "Time between two TCP keepalive probes";
                        }

                        ///nokia-conf/configure/bmp/station/connection/tcp-keepalive/keep-count
                        leaf keep-count {
                            type uint32 {
                                range "3..100";
                            }
                            default "4";
                            description "Keepalive threshold before connection is declared down";
                        }

                    } // container tcp-keepalive

                } // container connection

                ///nokia-conf/configure/bmp/station/family
                container family {
                    description "Enter the family context";

                    ///nokia-conf/configure/bmp/station/family/ipv4
                    leaf ipv4 {
                        type boolean;
                        default "true";
                        description "Support IPv4 address family";
                    }

                    ///nokia-conf/configure/bmp/station/family/ipv6
                    leaf ipv6 {
                        type boolean;
                        default "false";
                        description "Support IPv6 address family";
                    }

                    ///nokia-conf/configure/bmp/station/family/label-ipv4
                    leaf label-ipv4 {
                        type boolean;
                        default "false";
                        description "Support labeled IPv4 address family";
                    }

                    ///nokia-conf/configure/bmp/station/family/label-ipv6
                    leaf label-ipv6 {
                        type boolean;
                        default "false";
                        description "Support labeled IPv6 address family";
                    }

                    ///nokia-conf/configure/bmp/station/family/mcast-ipv4
                    leaf mcast-ipv4 {
                        type boolean;
                        default "false";
                        description "Support IPv4 multicast address family";
                    }

                    ///nokia-conf/configure/bmp/station/family/mcast-ipv6
                    leaf mcast-ipv6 {
                        type boolean;
                        default "false";
                        description "Support IPv6 multicast address family";
                    }

                    ///nokia-conf/configure/bmp/station/family/vpn-ipv4
                    leaf vpn-ipv4 {
                        type boolean;
                        default "false";
                        description "Support VPN IPv4 address family";
                    }

                    ///nokia-conf/configure/bmp/station/family/vpn-ipv6
                    leaf vpn-ipv6 {
                        type boolean;
                        default "false";
                        description "Support VPN IPv6 address family";
                    }

                    ///nokia-conf/configure/bmp/station/family/mcast-vpn-ipv4
                    leaf mcast-vpn-ipv4 {
                        type boolean;
                        default "false";
                        description "Support IPv4 VPN multicast address family";
                    }

                    ///nokia-conf/configure/bmp/station/family/mcast-vpn-ipv6
                    leaf mcast-vpn-ipv6 {
                        type boolean;
                        default "false";
                        description "Support IPv6 VPN multicast address family";
                    }

                    ///nokia-conf/configure/bmp/station/family/evpn
                    leaf evpn {
                        type boolean;
                        default "false";
                        description "Support EVPN address family";
                    }

                    ///nokia-conf/configure/bmp/station/family/l2-vpn
                    leaf l2-vpn {
                        type boolean;
                        default "false";
                        description "Support L2 VPN address family";
                    }

                    ///nokia-conf/configure/bmp/station/family/sr-policy-ipv4
                    leaf sr-policy-ipv4 {
                        type boolean;
                        default "false";
                        description "Support SR policy IPv4 address family";
                    }

                    ///nokia-conf/configure/bmp/station/family/sr-policy-ipv6
                    leaf sr-policy-ipv6 {
                        type boolean;
                        default "false";
                        description "Support SR policy IPv6 address family";
                    }

                } // container family

            } // list station

        } // container bmp

    } // grouping conf-bmp

}
