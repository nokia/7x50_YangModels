submodule nokia-state-card-fp {

    yang-version "1.1";

    belongs-to nokia-state { prefix "state"; }

    import ietf-yang-types                { prefix "yang"; }
    import nokia-sros-yang-extensions     { prefix "sros-ext"; }
    import nokia-types-card               { prefix "types-card"; }
    import nokia-types-qos                { prefix "types-qos"; }
    import nokia-types-sros               { prefix "types-sros"; }

    include nokia-state-qos;

    sros-ext:sros-major-release "rel23";
    organization "Nokia";
    contact
        "Nokia SR OS Support
         Web: <http://www.nokia.com>";
    description
        "Nokia YANG Data model with operational state for card forwarding plane on SR OS based routers.

         Copyright 2016 Nokia. All rights reserved. Reproduction of this document
         is authorized on the condition that the foregoing copyright notice is included.

         This nokia-state-card-fp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-30";

    grouping state-card-fp {
        ///nokia-state/state/card/fp
        list fp {
            key "fp-number";
            description "Enter the fp list instance";

            ///nokia-state/state/card/fp/fp-number
            leaf fp-number {
                type types-card:fp-id;
                description "Forwarding plane within the card";
            }

            ///nokia-state/state/card/fp/total-policy-accounting-in-use
            leaf total-policy-accounting-in-use {
                type uint32;
                description "Indicates the total number of statistics resources currently in use.";
            }

            ///nokia-state/state/card/fp/generation
            leaf generation {
                type types-card:fp-generation;
                description "Indicates the generation of the FP network processor.";
            }

            ///nokia-state/state/card/fp/core
            list core {
                key "core-number";
                description "Enter the core list instance";

                ///nokia-state/state/card/fp/core/core-number
                leaf core-number {
                    type uint32 {
                        range "0..1";
                    }
                    description
                        "The value which uniquely identifies the core within a
                         specific IOM card forwarding plane in the system.";
                }

                ///nokia-state/state/card/fp/core/resource-usage
                container resource-usage {
                    description "Enter the resource-usage context";

                    ///nokia-state/state/card/fp/core/resource-usage/dram
                    container dram {
                        description "Enter the dram context";

                        ///nokia-state/state/card/fp/core/resource-usage/dram/free-bdb
                        leaf free-bdb {
                            type yang:counter64;
                            description
                                "Indicates the number of free DRAM bundle descriptor buffers
                                 (BDB) on the core.";
                        }

                        ///nokia-state/state/card/fp/core/resource-usage/dram/minimum-free-bdb
                        leaf minimum-free-bdb {
                            type yang:counter64;
                            description
                                "Indicates the minimum number of free DRAM BDBs on the core since
                                 the last read from the device.";
                        }

                        ///nokia-state/state/card/fp/core/resource-usage/dram/lowest-free-bdb
                        leaf lowest-free-bdb {
                            type yang:counter64;
                            description
                                "Indicates the lowest number of free DRAM BDBs on the core
                                 since it was last polled.";
                        }

                        ///nokia-state/state/card/fp/core/resource-usage/dram/total-bdb
                        leaf total-bdb {
                            type yang:counter64;
                            description "Indicates the total number of DRAM BDBs on the core.";
                        }

                        ///nokia-state/state/card/fp/core/resource-usage/dram/bandwidth
                        container bandwidth {
                            description "Enter the bandwidth context";

                            ///nokia-state/state/card/fp/core/resource-usage/dram/bandwidth/max-consecutive-poll-blocked
                            leaf max-consecutive-poll-blocked {
                                type yang:counter64;
                                description
                                    "Indicates the number of DRAM bandwidth maximum consecutive polls
                                     blocked on the core.";
                            }

                            ///nokia-state/state/card/fp/core/resource-usage/dram/bandwidth/packet-rejects-last-poll
                            leaf packet-rejects-last-poll {
                                type yang:counter64;
                                description
                                    "Indicates the number of DRAM bandwidth packets that were rejected
                                     due to resource exhaustion since last poll on the core.";
                            }

                            ///nokia-state/state/card/fp/core/resource-usage/dram/bandwidth/total-packet-rejects
                            leaf total-packet-rejects {
                                type yang:counter64;
                                description
                                    "Indicates the cumulative total number of DRAM bandwidth packet
                                     rejects on the core.";
                            }

                        } // container bandwidth

                    } // container dram

                    ///nokia-state/state/card/fp/core/resource-usage/mesh-fabric-bandwidth
                    container mesh-fabric-bandwidth {
                        description "Enter the mesh-fabric-bandwidth context";

                        ///nokia-state/state/card/fp/core/resource-usage/mesh-fabric-bandwidth/assert-congestion-fp1
                        leaf assert-congestion-fp1 {
                            type yang:counter64;
                            description "Indicates the assert congestion count between this FP and FP1.";
                        }

                        ///nokia-state/state/card/fp/core/resource-usage/mesh-fabric-bandwidth/assert-congestion-fp2
                        leaf assert-congestion-fp2 {
                            type yang:counter64;
                            description "Indicates the assert congestion count between this FP and FP2.";
                        }

                        ///nokia-state/state/card/fp/core/resource-usage/mesh-fabric-bandwidth/assert-congestion-fp3
                        leaf assert-congestion-fp3 {
                            type yang:counter64;
                            description "Indicates the assert congestion count between this FP and FP3.";
                        }

                    } // container mesh-fabric-bandwidth

                    ///nokia-state/state/card/fp/core/resource-usage/processing-pipeline
                    container processing-pipeline {
                        description "Enter the processing-pipeline context";

                        ///nokia-state/state/card/fp/core/resource-usage/processing-pipeline/max-consecutive-poll-nif-prd-drops
                        leaf max-consecutive-poll-nif-prd-drops {
                            type yang:counter64;
                            description
                                "Indicates the the maximum number of core processing pipeline
                                 consecutive polls during NIF PRD drops on the core.";
                        }

                        ///nokia-state/state/card/fp/core/resource-usage/processing-pipeline/nif-prd-drops-last-poll
                        leaf nif-prd-drops-last-poll {
                            type yang:counter64;
                            description
                                "Indicates the number of core processing pipeline NIF PRD drops
                                 since the last poll on the core.";
                        }

                        ///nokia-state/state/card/fp/core/resource-usage/processing-pipeline/total-nif-prd-drops
                        leaf total-nif-prd-drops {
                            type yang:counter64;
                            description
                                "Indicates the cumulative total number of all core processing pipeline
                                 NIF PRD drops on the core.";
                        }

                    } // container processing-pipeline

                    ///nokia-state/state/card/fp/core/resource-usage/sram
                    container sram {
                        description "Enter the sram context";

                        ///nokia-state/state/card/fp/core/resource-usage/sram/free-buffer
                        leaf free-buffer {
                            type yang:counter64;
                            description "Indicates the number of free SRAM buffers on the core.";
                        }

                        ///nokia-state/state/card/fp/core/resource-usage/sram/minimum-free-buffer
                        leaf minimum-free-buffer {
                            type yang:counter64;
                            description
                                "Indicates the minimum number of free SRAM buffers on the core
                                 since the last read from the device.";
                        }

                        ///nokia-state/state/card/fp/core/resource-usage/sram/lowest-free-buffer
                        leaf lowest-free-buffer {
                            type yang:counter64;
                            description
                                "Indicates the lowest number of free SRAM buffers on the core
                                 since it was last polled.";
                        }

                        ///nokia-state/state/card/fp/core/resource-usage/sram/total-buffer
                        leaf total-buffer {
                            type yang:counter64;
                            description "Indicates the total number of SRAM buffers on the core.";
                        }

                        ///nokia-state/state/card/fp/core/resource-usage/sram/free-pdb
                        leaf free-pdb {
                            type yang:counter64;
                            description
                                "Indicates the number of free SRAM packet descriptor buffers
                                 (PDB) on the FP.";
                        }

                        ///nokia-state/state/card/fp/core/resource-usage/sram/minimum-free-pdb
                        leaf minimum-free-pdb {
                            type yang:counter64;
                            description
                                "Indicates the minimum number of free SRAM PDBs on the core
                                 since the last read from the device.";
                        }

                        ///nokia-state/state/card/fp/core/resource-usage/sram/lowest-free-pdb
                        leaf lowest-free-pdb {
                            type yang:counter64;
                            description
                                "Indicates the lowest number of free SRAM PDBs on the core
                                 since it was last polled.";
                        }

                        ///nokia-state/state/card/fp/core/resource-usage/sram/total-pdb
                        leaf total-pdb {
                            type yang:counter64;
                            description "Indicates the total number of SRAM PDBs on the core.";
                        }

                    } // container sram

                } // container resource-usage

            } // list core

            ///nokia-state/state/card/fp/egress
            container egress {
                description "Enter the egress context";

                ///nokia-state/state/card/fp/egress/burst-control-group
                list burst-control-group {
                    key "bcg-visitation-time";
                    description "Enter the burst-control-group list instance";

                    ///nokia-state/state/card/fp/egress/burst-control-group/bcg-visitation-time
                    leaf bcg-visitation-time {
                        type types-sros:named-item-255;
                        description
                            "The unique value which uniquely identifies the visitation time of the burst control
                             group within a specific IOM card in the system.";
                    }

                    ///nokia-state/state/card/fp/egress/burst-control-group/recalc-info
                    container recalc-info {
                        description "Enter the recalc-info context";

                        ///nokia-state/state/card/fp/egress/burst-control-group/recalc-info/num-queue
                        leaf num-queue {
                            type uint32;
                            description "The number of queues associsted to this burst control group.";
                        }

                        ///nokia-state/state/card/fp/egress/burst-control-group/recalc-info/at-risk
                        leaf at-risk {
                            type boolean;
                            description "The burst control group is at risk or not.";
                        }

                        ///nokia-state/state/card/fp/egress/burst-control-group/recalc-info/current
                        leaf current {
                            type string;
                            description "The burst control group worst seen current time.";
                        }

                        ///nokia-state/state/card/fp/egress/burst-control-group/recalc-info/worst-case
                        leaf worst-case {
                            type string;
                            description "The burst control group worst seen ever time.";
                        }

                        ///nokia-state/state/card/fp/egress/burst-control-group/recalc-info/avg-last-readings
                        leaf avg-last-readings {
                            type string;
                            description "The burst control group last seen ten readings.";
                        }

                        ///nokia-state/state/card/fp/egress/burst-control-group/recalc-info/avg-worst-seen-readings
                        leaf avg-worst-seen-readings {
                            type string;
                            description "The burst control group last ten worst seen readings.";
                        }

                        ///nokia-state/state/card/fp/egress/burst-control-group/recalc-info/worst-possible-ever
                        leaf worst-possible-ever {
                            type string;
                            description "The burst control group worst ever configuration at 100%% scheduling predicted readings.";
                        }

                        ///nokia-state/state/card/fp/egress/burst-control-group/recalc-info/worst-possible-current
                        leaf worst-possible-current {
                            type string;
                            description "The burst control group worst current map at 100%% scheduling predicted readings.";
                        }

                        ///nokia-state/state/card/fp/egress/burst-control-group/recalc-info/worst-provisioned-ever
                        leaf worst-provisioned-ever {
                            type string;
                            description "The burst control group worst ever configuration at provisioned predicted readings.";
                        }

                        ///nokia-state/state/card/fp/egress/burst-control-group/recalc-info/worst-provisioned-current
                        leaf worst-provisioned-current {
                            type string;
                            description "The burst control group worst current map at provisioned predicted readings.";
                        }

                    } // container recalc-info

                } // list burst-control-group

            } // container egress

            ///nokia-state/state/card/fp/hi-bw-mcast-src
            container hi-bw-mcast-src {
                description "Enable the hi-bw-mcast-src context";

                ///nokia-state/state/card/fp/hi-bw-mcast-src/tap-count
                leaf tap-count {
                    type uint32;
                    description
                        "Indicates the number of high bandwidth multicast traffic taps
                         on this forwarding plane.";
                }

            } // container hi-bw-mcast-src

            ///nokia-state/state/card/fp/ingress
            container ingress {
                description "Enter the ingress context";

                ///nokia-state/state/card/fp/ingress/access
                container access {
                    description "Enter the access context";

                    ///nokia-state/state/card/fp/ingress/access/queue-group
                    list queue-group {
                        key "queue-group-name instance-id";
                        description "Enter the queue-group list instance";

                        ///nokia-state/state/card/fp/ingress/access/queue-group/queue-group-name
                        leaf queue-group-name {
                            type leafref {
                                path "../../../../../../qos/queue-group-templates/ingress/queue-group/ingress-queue-group-name";
                            }
                            description "Queue group name";
                        }

                        ///nokia-state/state/card/fp/ingress/access/queue-group/instance-id
                        leaf instance-id {
                            type uint16 {
                                range "1..65535";
                            }
                            description "Instance ID";
                        }

                        ///nokia-state/state/card/fp/ingress/access/queue-group/policer-control-policy
                        container policer-control-policy {
                            description "Enter the policer-control-policy context";

                            ///nokia-state/state/card/fp/ingress/access/queue-group/policer-control-policy/arbiter
                            list arbiter {
                                key "arbiter-name";
                                description "Enter the arbiter list instance";

                                ///nokia-state/state/card/fp/ingress/access/queue-group/policer-control-policy/arbiter/arbiter-name
                                leaf arbiter-name {
                                    type types-sros:named-item;
                                    description "Arbiter name";
                                }

                                ///nokia-state/state/card/fp/ingress/access/queue-group/policer-control-policy/arbiter/statistics
                                container statistics {
                                    description "Enter the statistics context";

                                    ///nokia-state/state/card/fp/ingress/access/queue-group/policer-control-policy/arbiter/statistics/forwarded-packets
                                    leaf forwarded-packets {
                                        type yang:counter64;
                                        description "The number of forwarded packets.";
                                    }

                                    ///nokia-state/state/card/fp/ingress/access/queue-group/policer-control-policy/arbiter/statistics/forwarded-octets
                                    leaf forwarded-octets {
                                        type yang:counter64;
                                        description "The number of forwarded octets.";
                                    }

                                } // container statistics

                            } // list arbiter

                        } // container policer-control-policy

                        ///nokia-state/state/card/fp/ingress/access/queue-group/policer
                        list policer {
                            key "policer-id";
                            description "Enter the policer list instance";

                            ///nokia-state/state/card/fp/ingress/access/queue-group/policer/policer-id
                            leaf policer-id {
                                type types-qos:ingress-policer-id;
                                description "The unique identifier for the policer.";
                            }

                            ///nokia-state/state/card/fp/ingress/access/queue-group/policer/statistics
                            container statistics {
                                description "Enter the statistics context";

                                ///nokia-state/state/card/fp/ingress/access/queue-group/policer/statistics/stat-mode
                                choice stat-mode {
                                    ///nokia-state/state/card/fp/ingress/access/queue-group/policer/statistics/stat-mode/minimal
                                    case minimal {

                                        ///nokia-state/state/card/fp/ingress/access/queue-group/policer/statistics/stat-mode/minimal/minimal
                                        container minimal {
                                            description "Enter the minimal context";

                                            ///nokia-state/state/card/fp/ingress/access/queue-group/policer/statistics/stat-mode/minimal/minimal/all-offered-packets
                                            leaf all-offered-packets {
                                                type yang:counter64;
                                                description "The number of all the priority packets offered by the packet processor to traffic manager";
                                            }

                                            ///nokia-state/state/card/fp/ingress/access/queue-group/policer/statistics/stat-mode/minimal/minimal/all-offered-octets
                                            leaf all-offered-octets {
                                                type yang:counter64;
                                                description "The number of all the priority octets offered by the packet processor to traffic manager";
                                            }

                                            ///nokia-state/state/card/fp/ingress/access/queue-group/policer/statistics/stat-mode/minimal/minimal/all-dropped-packets
                                            leaf all-dropped-packets {
                                                type yang:counter64;
                                                description "The number of all the priority packets dropped by the packet processor to traffic manager";
                                            }

                                            ///nokia-state/state/card/fp/ingress/access/queue-group/policer/statistics/stat-mode/minimal/minimal/all-dropped-octets
                                            leaf all-dropped-octets {
                                                type yang:counter64;
                                                description "The number of all the priority octets dropped by the packet processor to traffic manager";
                                            }

                                            ///nokia-state/state/card/fp/ingress/access/queue-group/policer/statistics/stat-mode/minimal/minimal/all-forwarded-packets
                                            leaf all-forwarded-packets {
                                                type yang:counter64;
                                                description "The number of all the priority packets forwarded by the packet processor to traffic manager";
                                            }

                                            ///nokia-state/state/card/fp/ingress/access/queue-group/policer/statistics/stat-mode/minimal/minimal/all-forwarded-octets
                                            leaf all-forwarded-octets {
                                                type yang:counter64;
                                                description "The number of all the priority octets forwarded by the packet processor to traffic manager";
                                            }

                                        } // container minimal

                                    }
                                    ///nokia-state/state/card/fp/ingress/access/queue-group/policer/statistics/stat-mode/offered-profile-no-cir
                                    case offered-profile-no-cir {

                                        ///nokia-state/state/card/fp/ingress/access/queue-group/policer/statistics/stat-mode/offered-profile-no-cir/offered-profile-no-cir
                                        container offered-profile-no-cir {
                                            description "Enter the offered-profile-no-cir context";

                                            ///nokia-state/state/card/fp/ingress/access/queue-group/policer/statistics/stat-mode/offered-profile-no-cir/offered-profile-no-cir/in-profile-offered-packets
                                            leaf in-profile-offered-packets {
                                                type yang:counter64;
                                                description "The number of in-profile packets offered by the packet processor to traffic manager";
                                            }

                                            ///nokia-state/state/card/fp/ingress/access/queue-group/policer/statistics/stat-mode/offered-profile-no-cir/offered-profile-no-cir/in-profile-offered-octets
                                            leaf in-profile-offered-octets {
                                                type yang:counter64;
                                                description "The number of in-profile octets offered by the packet processor to traffic manager";
                                            }

                                            ///nokia-state/state/card/fp/ingress/access/queue-group/policer/statistics/stat-mode/offered-profile-no-cir/offered-profile-no-cir/out-profile-offered-packets
                                            leaf out-profile-offered-packets {
                                                type yang:counter64;
                                                description "The number of out-of-profile packets offered by the packet processor to traffic manager";
                                            }

                                            ///nokia-state/state/card/fp/ingress/access/queue-group/policer/statistics/stat-mode/offered-profile-no-cir/offered-profile-no-cir/out-profile-offered-octets
                                            leaf out-profile-offered-octets {
                                                type yang:counter64;
                                                description "The number of out-of-profile octets offered by the packet processor to traffic manager";
                                            }

                                            ///nokia-state/state/card/fp/ingress/access/queue-group/policer/statistics/stat-mode/offered-profile-no-cir/offered-profile-no-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-profile-no-cir/offered-profile-no-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-profile-no-cir/offered-profile-no-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-profile-no-cir/offered-profile-no-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-profile-no-cir/offered-profile-no-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-profile-no-cir/offered-profile-no-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-profile-no-cir/offered-profile-no-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-profile-no-cir/offered-profile-no-cir/out-profile-forwarded-octets
                                            leaf out-profile-forwarded-octets {
                                                type yang:counter64;
                                                description "The number of out-of-profile octets forwarded by the packet processor to traffic manager";
                                            }

                                        } // container offered-profile-no-cir

                                    }
                                    ///nokia-state/state/card/fp/ingress/access/queue-group/policer/statistics/stat-mode/offered-priority-no-cir
                                    case offered-priority-no-cir {

                                        ///nokia-state/state/card/fp/ingress/access/queue-group/policer/statistics/stat-mode/offered-priority-no-cir/offered-priority-no-cir
                                        container offered-priority-no-cir {
                                            description "Enter the offered-priority-no-cir context";

                                            ///nokia-state/state/card/fp/ingress/access/queue-group/policer/statistics/stat-mode/offered-priority-no-cir/offered-priority-no-cir/high-priority-offered-packets
                                            leaf high-priority-offered-packets {
                                                type yang:counter64;
                                                description "The number of high-priority packets offered by the packet processor to traffic manager";
                                            }

                                            ///nokia-state/state/card/fp/ingress/access/queue-group/policer/statistics/stat-mode/offered-priority-no-cir/offered-priority-no-cir/high-priority-offered-octets
                                            leaf high-priority-offered-octets {
                                                type yang:counter64;
                                                description "The number of high-priority octets offered by the packet processor to traffic manager";
                                            }

                                            ///nokia-state/state/card/fp/ingress/access/queue-group/policer/statistics/stat-mode/offered-priority-no-cir/offered-priority-no-cir/low-priority-offered-packets
                                            leaf low-priority-offered-packets {
                                                type yang:counter64;
                                                description "The number of low-priority packets offered by the packet processor to traffic manager";
                                            }

                                            ///nokia-state/state/card/fp/ingress/access/queue-group/policer/statistics/stat-mode/offered-priority-no-cir/offered-priority-no-cir/low-priority-offered-octets
                                            leaf low-priority-offered-octets {
                                                type yang:counter64;
                                                description "The number of low-priority octets offered by the packet processor to traffic manager";
                                            }

                                            ///nokia-state/state/card/fp/ingress/access/queue-group/policer/statistics/stat-mode/offered-priority-no-cir/offered-priority-no-cir/high-priority-dropped-packets
                                            leaf high-priority-dropped-packets {
                                                type yang:counter64;
                                                description "The number of high-priority packets dropped by the packet processor to traffic manager";
                                            }

                                            ///nokia-state/state/card/fp/ingress/access/queue-group/policer/statistics/stat-mode/offered-priority-no-cir/offered-priority-no-cir/high-priority-dropped-octets
                                            leaf high-priority-dropped-octets {
                                                type yang:counter64;
                                                description "The number of high-priority octets dropped by the packet processor to traffic manager";
                                            }

                                            ///nokia-state/state/card/fp/ingress/access/queue-group/policer/statistics/stat-mode/offered-priority-no-cir/offered-priority-no-cir/low-priority-dropped-packets
                                            leaf low-priority-dropped-packets {
                                                type yang:counter64;
                                                description "The number of low-priority packets dropped by the packet processor to traffic manager";
                                            }

                                            ///nokia-state/state/card/fp/ingress/access/queue-group/policer/statistics/stat-mode/offered-priority-no-cir/offered-priority-no-cir/low-priority-dropped-octets
                                            leaf low-priority-dropped-octets {
                                                type yang:counter64;
                                                description "The number of low-priority octets dropped by the packet processor to traffic manager";
                                            }

                                            ///nokia-state/state/card/fp/ingress/access/queue-group/policer/statistics/stat-mode/offered-priority-no-cir/offered-priority-no-cir/high-priority-forwarded-packets
                                            leaf high-priority-forwarded-packets {
                                                type yang:counter64;
                                                description "The number of high-priority packets forwarded by the packet processor to traffic manager";
                                            }

                                            ///nokia-state/state/card/fp/ingress/access/queue-group/policer/statistics/stat-mode/offered-priority-no-cir/offered-priority-no-cir/high-priority-forwarded-octets
                                            leaf high-priority-forwarded-octets {
                                                type yang:counter64;
                                                description "The number of high-priority octets forwarded by the packet processor to traffic manager";
                                            }

                                            ///nokia-state/state/card/fp/ingress/access/queue-group/policer/statistics/stat-mode/offered-priority-no-cir/offered-priority-no-cir/low-priority-forwarded-packets
                                            leaf low-priority-forwarded-packets {
                                                type yang:counter64;
                                                description "The number of low-priority packets forwarded by the packet processor to traffic manager";
                                            }

                                            ///nokia-state/state/card/fp/ingress/access/queue-group/policer/statistics/stat-mode/offered-priority-no-cir/offered-priority-no-cir/low-priority-forwarded-octets
                                            leaf low-priority-forwarded-octets {
                                                type yang:counter64;
                                                description "The number of low-priority octets forwarded by the packet processor to traffic manager";
                                            }

                                        } // container offered-priority-no-cir

                                    }
                                    ///nokia-state/state/card/fp/ingress/access/queue-group/policer/statistics/stat-mode/offered-profile-cir
                                    case offered-profile-cir {

                                        ///nokia-state/state/card/fp/ingress/access/queue-group/policer/statistics/stat-mode/offered-profile-cir/offered-profile-cir
                                        container offered-profile-cir {
                                            description "Enter the offered-profile-cir context";

                                            ///nokia-state/state/card/fp/ingress/access/queue-group/policer/statistics/stat-mode/offered-profile-cir/offered-profile-cir/in-profile-offered-packets
                                            leaf in-profile-offered-packets {
                                                type yang:counter64;
                                                description "The number of in-profile packets offered by the packet processor to traffic manager";
                                            }

                                            ///nokia-state/state/card/fp/ingress/access/queue-group/policer/statistics/stat-mode/offered-profile-cir/offered-profile-cir/in-profile-offered-octets
                                            leaf in-profile-offered-octets {
                                                type yang:counter64;
                                                description "The number of in-profile octets offered by the packet processor to traffic manager";
                                            }

                                            ///nokia-state/state/card/fp/ingress/access/queue-group/policer/statistics/stat-mode/offered-profile-cir/offered-profile-cir/out-profile-offered-packets
                                            leaf out-profile-offered-packets {
                                                type yang:counter64;
                                                description "The number of out-of-profile packets offered by the packet processor to traffic manager";
                                            }

                                            ///nokia-state/state/card/fp/ingress/access/queue-group/policer/statistics/stat-mode/offered-profile-cir/offered-profile-cir/out-profile-offered-octets
                                            leaf out-profile-offered-octets {
                                                type yang:counter64;
                                                description "The number of out-of-profile octets offered by the packet processor to traffic manager";
                                            }

                                            ///nokia-state/state/card/fp/ingress/access/queue-group/policer/statistics/stat-mode/offered-profile-cir/offered-profile-cir/uncolor-offered-packets
                                            leaf uncolor-offered-packets {
                                                type yang:counter64;
                                                description "The number of uncolor packets offered by the packet processor to traffic manager";
                                            }

                                            ///nokia-state/state/card/fp/ingress/access/queue-group/policer/statistics/stat-mode/offered-profile-cir/offered-profile-cir/uncolor-offered-octets
                                            leaf uncolor-offered-octets {
                                                type yang:counter64;
                                                description "The number of uncolor octets offered by the packet processor to traffic manager";
                                            }

                                            ///nokia-state/state/card/fp/ingress/access/queue-group/policer/statistics/stat-mode/offered-profile-cir/offered-profile-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-profile-cir/offered-profile-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-profile-cir/offered-profile-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-profile-cir/offered-profile-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-profile-cir/offered-profile-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-profile-cir/offered-profile-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-profile-cir/offered-profile-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-profile-cir/offered-profile-cir/out-profile-forwarded-octets
                                            leaf out-profile-forwarded-octets {
                                                type yang:counter64;
                                                description "The number of out-of-profile octets forwarded by the packet processor to traffic manager";
                                            }

                                        } // container offered-profile-cir

                                    }
                                    ///nokia-state/state/card/fp/ingress/access/queue-group/policer/statistics/stat-mode/offered-priority-cir
                                    case offered-priority-cir {

                                        ///nokia-state/state/card/fp/ingress/access/queue-group/policer/statistics/stat-mode/offered-priority-cir/offered-priority-cir
                                        container offered-priority-cir {
                                            description "Enter the offered-priority-cir context";

                                            ///nokia-state/state/card/fp/ingress/access/queue-group/policer/statistics/stat-mode/offered-priority-cir/offered-priority-cir/high-priority-offered-packets
                                            leaf high-priority-offered-packets {
                                                type yang:counter64;
                                                description "The number of high-priority packets offered by the packet processor to traffic manager";
                                            }

                                            ///nokia-state/state/card/fp/ingress/access/queue-group/policer/statistics/stat-mode/offered-priority-cir/offered-priority-cir/high-priority-offered-octets
                                            leaf high-priority-offered-octets {
                                                type yang:counter64;
                                                description "The number of high-priority octets offered by the packet processor to traffic manager";
                                            }

                                            ///nokia-state/state/card/fp/ingress/access/queue-group/policer/statistics/stat-mode/offered-priority-cir/offered-priority-cir/low-priority-offered-packets
                                            leaf low-priority-offered-packets {
                                                type yang:counter64;
                                                description "The number of low-priority packets offered by the packet processor to traffic manager";
                                            }

                                            ///nokia-state/state/card/fp/ingress/access/queue-group/policer/statistics/stat-mode/offered-priority-cir/offered-priority-cir/low-priority-offered-octets
                                            leaf low-priority-offered-octets {
                                                type yang:counter64;
                                                description "The number of low-priority octets offered by the packet processor to traffic manager";
                                            }

                                            ///nokia-state/state/card/fp/ingress/access/queue-group/policer/statistics/stat-mode/offered-priority-cir/offered-priority-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-priority-cir/offered-priority-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-priority-cir/offered-priority-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-priority-cir/offered-priority-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-priority-cir/offered-priority-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-priority-cir/offered-priority-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-priority-cir/offered-priority-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-priority-cir/offered-priority-cir/out-profile-forwarded-octets
                                            leaf out-profile-forwarded-octets {
                                                type yang:counter64;
                                                description "The number of out-of-profile octets forwarded by the packet processor to traffic manager";
                                            }

                                        } // container offered-priority-cir

                                    }
                                    ///nokia-state/state/card/fp/ingress/access/queue-group/policer/statistics/stat-mode/offered-total-cir
                                    case offered-total-cir {

                                        ///nokia-state/state/card/fp/ingress/access/queue-group/policer/statistics/stat-mode/offered-total-cir/offered-total-cir
                                        container offered-total-cir {
                                            description "Enter the offered-total-cir context";

                                            ///nokia-state/state/card/fp/ingress/access/queue-group/policer/statistics/stat-mode/offered-total-cir/offered-total-cir/all-offered-packets
                                            leaf all-offered-packets {
                                                type yang:counter64;
                                                description "The number of all the priority packets offered by the packet processor to traffic manager";
                                            }

                                            ///nokia-state/state/card/fp/ingress/access/queue-group/policer/statistics/stat-mode/offered-total-cir/offered-total-cir/all-offered-octets
                                            leaf all-offered-octets {
                                                type yang:counter64;
                                                description "The number of all the priority octets offered by the packet processor to traffic manager";
                                            }

                                            ///nokia-state/state/card/fp/ingress/access/queue-group/policer/statistics/stat-mode/offered-total-cir/offered-total-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-total-cir/offered-total-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-total-cir/offered-total-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-total-cir/offered-total-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-total-cir/offered-total-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-total-cir/offered-total-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-total-cir/offered-total-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-total-cir/offered-total-cir/out-profile-forwarded-octets
                                            leaf out-profile-forwarded-octets {
                                                type yang:counter64;
                                                description "The number of out-of-profile octets forwarded by the packet processor to traffic manager";
                                            }

                                        } // container offered-total-cir

                                    }
                                    ///nokia-state/state/card/fp/ingress/access/queue-group/policer/statistics/stat-mode/offered-limited-profile-cir
                                    case offered-limited-profile-cir {

                                        ///nokia-state/state/card/fp/ingress/access/queue-group/policer/statistics/stat-mode/offered-limited-profile-cir/offered-limited-profile-cir
                                        container offered-limited-profile-cir {
                                            description "Enter the offered-limited-profile-cir context";

                                            ///nokia-state/state/card/fp/ingress/access/queue-group/policer/statistics/stat-mode/offered-limited-profile-cir/offered-limited-profile-cir/out-profile-offered-packets
                                            leaf out-profile-offered-packets {
                                                type yang:counter64;
                                                description "The number of out-of-profile packets offered by the packet processor to traffic manager";
                                            }

                                            ///nokia-state/state/card/fp/ingress/access/queue-group/policer/statistics/stat-mode/offered-limited-profile-cir/offered-limited-profile-cir/out-profile-offered-octets
                                            leaf out-profile-offered-octets {
                                                type yang:counter64;
                                                description "The number of out-of-profile octets offered by the packet processor to traffic manager";
                                            }

                                            ///nokia-state/state/card/fp/ingress/access/queue-group/policer/statistics/stat-mode/offered-limited-profile-cir/offered-limited-profile-cir/uncolor-offered-packets
                                            leaf uncolor-offered-packets {
                                                type yang:counter64;
                                                description "The number of uncolor packets offered by the packet processor to traffic manager";
                                            }

                                            ///nokia-state/state/card/fp/ingress/access/queue-group/policer/statistics/stat-mode/offered-limited-profile-cir/offered-limited-profile-cir/uncolor-offered-octets
                                            leaf uncolor-offered-octets {
                                                type yang:counter64;
                                                description "The number of uncolor octets offered by the packet processor to traffic manager";
                                            }

                                            ///nokia-state/state/card/fp/ingress/access/queue-group/policer/statistics/stat-mode/offered-limited-profile-cir/offered-limited-profile-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-limited-profile-cir/offered-limited-profile-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-limited-profile-cir/offered-limited-profile-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-limited-profile-cir/offered-limited-profile-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-limited-profile-cir/offered-limited-profile-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-limited-profile-cir/offered-limited-profile-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-limited-profile-cir/offered-limited-profile-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-limited-profile-cir/offered-limited-profile-cir/out-profile-forwarded-octets
                                            leaf out-profile-forwarded-octets {
                                                type yang:counter64;
                                                description "The number of out-of-profile octets forwarded by the packet processor to traffic manager";
                                            }

                                        } // container offered-limited-profile-cir

                                    }
                                    ///nokia-state/state/card/fp/ingress/access/queue-group/policer/statistics/stat-mode/offered-profile-capped-cir
                                    case offered-profile-capped-cir {

                                        ///nokia-state/state/card/fp/ingress/access/queue-group/policer/statistics/stat-mode/offered-profile-capped-cir/offered-profile-capped-cir
                                        container offered-profile-capped-cir {
                                            description "Enter the offered-profile-capped-cir context";

                                            ///nokia-state/state/card/fp/ingress/access/queue-group/policer/statistics/stat-mode/offered-profile-capped-cir/offered-profile-capped-cir/in-profile-offered-packets
                                            leaf in-profile-offered-packets {
                                                type yang:counter64;
                                                description "The number of in-profile packets offered by the packet processor to traffic manager";
                                            }

                                            ///nokia-state/state/card/fp/ingress/access/queue-group/policer/statistics/stat-mode/offered-profile-capped-cir/offered-profile-capped-cir/in-profile-offered-octets
                                            leaf in-profile-offered-octets {
                                                type yang:counter64;
                                                description "The number of in-profile octets offered by the packet processor to traffic manager";
                                            }

                                            ///nokia-state/state/card/fp/ingress/access/queue-group/policer/statistics/stat-mode/offered-profile-capped-cir/offered-profile-capped-cir/out-profile-offered-packets
                                            leaf out-profile-offered-packets {
                                                type yang:counter64;
                                                description "The number of out-of-profile packets offered by the packet processor to traffic manager";
                                            }

                                            ///nokia-state/state/card/fp/ingress/access/queue-group/policer/statistics/stat-mode/offered-profile-capped-cir/offered-profile-capped-cir/out-profile-offered-octets
                                            leaf out-profile-offered-octets {
                                                type yang:counter64;
                                                description "The number of out-of-profile octets offered by the packet processor to traffic manager";
                                            }

                                            ///nokia-state/state/card/fp/ingress/access/queue-group/policer/statistics/stat-mode/offered-profile-capped-cir/offered-profile-capped-cir/uncolor-offered-packets
                                            leaf uncolor-offered-packets {
                                                type yang:counter64;
                                                description "The number of uncolor packets offered by the packet processor to traffic manager";
                                            }

                                            ///nokia-state/state/card/fp/ingress/access/queue-group/policer/statistics/stat-mode/offered-profile-capped-cir/offered-profile-capped-cir/uncolor-offered-octets
                                            leaf uncolor-offered-octets {
                                                type yang:counter64;
                                                description "The number of uncolor octets offered by the packet processor to traffic manager";
                                            }

                                            ///nokia-state/state/card/fp/ingress/access/queue-group/policer/statistics/stat-mode/offered-profile-capped-cir/offered-profile-capped-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-profile-capped-cir/offered-profile-capped-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-profile-capped-cir/offered-profile-capped-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-profile-capped-cir/offered-profile-capped-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-profile-capped-cir/offered-profile-capped-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-profile-capped-cir/offered-profile-capped-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-profile-capped-cir/offered-profile-capped-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-profile-capped-cir/offered-profile-capped-cir/out-profile-forwarded-octets
                                            leaf out-profile-forwarded-octets {
                                                type yang:counter64;
                                                description "The number of out-of-profile octets forwarded by the packet processor to traffic manager";
                                            }

                                        } // container offered-profile-capped-cir

                                    }
                                    ///nokia-state/state/card/fp/ingress/access/queue-group/policer/statistics/stat-mode/offered-limited-capped-cir
                                    case offered-limited-capped-cir {

                                        ///nokia-state/state/card/fp/ingress/access/queue-group/policer/statistics/stat-mode/offered-limited-capped-cir/offered-limited-capped-cir
                                        container offered-limited-capped-cir {
                                            description "Enter the offered-limited-capped-cir context";

                                            ///nokia-state/state/card/fp/ingress/access/queue-group/policer/statistics/stat-mode/offered-limited-capped-cir/offered-limited-capped-cir/in-profile-offered-packets
                                            leaf in-profile-offered-packets {
                                                type yang:counter64;
                                                description "The number of in-profile packets offered by the packet processor to traffic manager";
                                            }

                                            ///nokia-state/state/card/fp/ingress/access/queue-group/policer/statistics/stat-mode/offered-limited-capped-cir/offered-limited-capped-cir/in-profile-offered-octets
                                            leaf in-profile-offered-octets {
                                                type yang:counter64;
                                                description "The number of in-profile octets offered by the packet processor to traffic manager";
                                            }

                                            ///nokia-state/state/card/fp/ingress/access/queue-group/policer/statistics/stat-mode/offered-limited-capped-cir/offered-limited-capped-cir/in-profile-dropped-packets
                                            leaf in-profile-dropped-packets {
                                                type yang:counter64;
                                                description "The number of in-profile packets dropped by the packet processor to traffic manager";
                                            }

                                            ///nokia-state/state/card/fp/ingress/access/queue-group/policer/statistics/stat-mode/offered-limited-capped-cir/offered-limited-capped-cir/in-profile-dropped-octets
                                            leaf in-profile-dropped-octets {
                                                type yang:counter64;
                                                description "The number of in-profile octets dropped by the packet processor to traffic manager";
                                            }

                                            ///nokia-state/state/card/fp/ingress/access/queue-group/policer/statistics/stat-mode/offered-limited-capped-cir/offered-limited-capped-cir/out-profile-dropped-packets
                                            leaf out-profile-dropped-packets {
                                                type yang:counter64;
                                                description "The number of out-of-profile packets dropped by the packet processor to traffic manager";
                                            }

                                            ///nokia-state/state/card/fp/ingress/access/queue-group/policer/statistics/stat-mode/offered-limited-capped-cir/offered-limited-capped-cir/out-profile-dropped-octets
                                            leaf out-profile-dropped-octets {
                                                type yang:counter64;
                                                description "The number of out-of-profile octets dropped by the packet processor to traffic manager";
                                            }

                                            ///nokia-state/state/card/fp/ingress/access/queue-group/policer/statistics/stat-mode/offered-limited-capped-cir/offered-limited-capped-cir/in-profile-forwarded-packets
                                            leaf in-profile-forwarded-packets {
                                                type yang:counter64;
                                                description "The number of in-profile packets forwarded by the packet processor to traffic manager";
                                            }

                                            ///nokia-state/state/card/fp/ingress/access/queue-group/policer/statistics/stat-mode/offered-limited-capped-cir/offered-limited-capped-cir/in-profile-forwarded-octets
                                            leaf in-profile-forwarded-octets {
                                                type yang:counter64;
                                                description "The number of in-profile octets forwarded by the packet processor to traffic manager";
                                            }

                                            ///nokia-state/state/card/fp/ingress/access/queue-group/policer/statistics/stat-mode/offered-limited-capped-cir/offered-limited-capped-cir/out-profile-forwarded-packets
                                            leaf out-profile-forwarded-packets {
                                                type yang:counter64;
                                                description "The number of out-of-profile packets forwarded by the packet processor to traffic manager";
                                            }

                                            ///nokia-state/state/card/fp/ingress/access/queue-group/policer/statistics/stat-mode/offered-limited-capped-cir/offered-limited-capped-cir/out-profile-forwarded-octets
                                            leaf out-profile-forwarded-octets {
                                                type yang:counter64;
                                                description "The number of out-of-profile octets forwarded by the packet processor to traffic manager";
                                            }

                                            ///nokia-state/state/card/fp/ingress/access/queue-group/policer/statistics/stat-mode/offered-limited-capped-cir/offered-limited-capped-cir/uncolor-offered-packets
                                            leaf uncolor-offered-packets {
                                                type yang:counter64;
                                                description "The number of out-of-rofile packets offered by the packet processor to traffic manager";
                                            }

                                            ///nokia-state/state/card/fp/ingress/access/queue-group/policer/statistics/stat-mode/offered-limited-capped-cir/offered-limited-capped-cir/uncolor-offered-octets
                                            leaf uncolor-offered-octets {
                                                type yang:counter64;
                                                description "The number of out-of-profile octets offered by the packet processor to traffic manager";
                                            }

                                        } // container offered-limited-capped-cir

                                    }
                                }
                            } // container statistics

                            ///nokia-state/state/card/fp/ingress/access/queue-group/policer/hardware-policer
                            container hardware-policer {
                                description "Enter the hardware-policer context";

                                ///nokia-state/state/card/fp/ingress/access/queue-group/policer/hardware-policer/adapted-admin-cbs
                                leaf adapted-admin-cbs {
                                    type int64;
                                    units "bytes";
                                    description "Admin CBS.";
                                }

                                ///nokia-state/state/card/fp/ingress/access/queue-group/policer/hardware-policer/adapted-admin-mbs
                                leaf adapted-admin-mbs {
                                    type int64;
                                    units "bytes";
                                    description "Admin MBS.";
                                }

                                ///nokia-state/state/card/fp/ingress/access/queue-group/policer/hardware-policer/adapted-hp-only
                                leaf adapted-hp-only {
                                    type int64;
                                    units "bytes";
                                    description "Hi Prio Only.";
                                }

                                ///nokia-state/state/card/fp/ingress/access/queue-group/policer/hardware-policer/depth
                                leaf depth {
                                    type int64;
                                    units "bytes";
                                    description "Depth.";
                                }

                                ///nokia-state/state/card/fp/ingress/access/queue-group/policer/hardware-policer/operational-cir
                                leaf operational-cir {
                                    type types-qos:int32-max;
                                    description "Oper CIR.";
                                }

                                ///nokia-state/state/card/fp/ingress/access/queue-group/policer/hardware-policer/operational-fir
                                leaf operational-fir {
                                    type types-qos:int32-max;
                                    description "Oper FIR.";
                                }

                                ///nokia-state/state/card/fp/ingress/access/queue-group/policer/hardware-policer/operational-pir
                                leaf operational-pir {
                                    type types-qos:int32-max;
                                    description "Oper PIR.";
                                }

                            } // container hardware-policer

                        } // list policer

                    } // list queue-group

                } // container access

                ///nokia-state/state/card/fp/ingress/mcast-path-management
                container mcast-path-management {
                    description "Enter the mcast-path-management context";

                    ///nokia-state/state/card/fp/ingress/mcast-path-management/primary-in-use-bandwidth
                    leaf primary-in-use-bandwidth {
                        type uint32;
                        units "kilobps";
                        description
                            "Indicates the in use ingress multicast bandwidth for the primary
                             forwarding path.";
                    }

                    ///nokia-state/state/card/fp/ingress/mcast-path-management/secondary-in-use-bandwidth
                    leaf secondary-in-use-bandwidth {
                        type uint32;
                        units "kilobps";
                        description
                            "Indicates the in use ingress multicast bandwidth for the secondary
                             forwarding path.";
                    }

                    ///nokia-state/state/card/fp/ingress/mcast-path-management/blackhole-in-use-bandwidth
                    leaf blackhole-in-use-bandwidth {
                        type uint32;
                        units "kilobps";
                        description
                            "Indicates the bandwidth of the ingress multicast traffic that
                             is being black holed on the forwarding plane.";
                    }

                } // container mcast-path-management

                ///nokia-state/state/card/fp/ingress/network
                container network {
                    description "Enter the network context";

                    ///nokia-state/state/card/fp/ingress/network/queue-group
                    list queue-group {
                        key "queue-group-name instance-id";
                        description "Enter the queue-group list instance";

                        ///nokia-state/state/card/fp/ingress/network/queue-group/queue-group-name
                        leaf queue-group-name {
                            type leafref {
                                path "../../../../../../qos/queue-group-templates/ingress/queue-group/ingress-queue-group-name";
                            }
                            description "Queue group name";
                        }

                        ///nokia-state/state/card/fp/ingress/network/queue-group/instance-id
                        leaf instance-id {
                            type uint16 {
                                range "1..65535";
                            }
                            description "Instance ID";
                        }

                        ///nokia-state/state/card/fp/ingress/network/queue-group/policer-control-policy
                        container policer-control-policy {
                            description "Enter the policer-control-policy context";

                            ///nokia-state/state/card/fp/ingress/network/queue-group/policer-control-policy/arbiter
                            list arbiter {
                                key "arbiter-name";
                                description "Enter the arbiter list instance";

                                ///nokia-state/state/card/fp/ingress/network/queue-group/policer-control-policy/arbiter/arbiter-name
                                leaf arbiter-name {
                                    type types-sros:named-item;
                                    description "Arbiter name";
                                }

                                ///nokia-state/state/card/fp/ingress/network/queue-group/policer-control-policy/arbiter/statistics
                                container statistics {
                                    description "Enter the statistics context";

                                    ///nokia-state/state/card/fp/ingress/network/queue-group/policer-control-policy/arbiter/statistics/forwarded-packets
                                    leaf forwarded-packets {
                                        type yang:counter64;
                                        description "The number of forwarded packets.";
                                    }

                                    ///nokia-state/state/card/fp/ingress/network/queue-group/policer-control-policy/arbiter/statistics/forwarded-octets
                                    leaf forwarded-octets {
                                        type yang:counter64;
                                        description "The number of forwarded octets.";
                                    }

                                } // container statistics

                            } // list arbiter

                        } // container policer-control-policy

                        ///nokia-state/state/card/fp/ingress/network/queue-group/policer
                        list policer {
                            key "policer-id";
                            description "Enter the policer list instance";

                            ///nokia-state/state/card/fp/ingress/network/queue-group/policer/policer-id
                            leaf policer-id {
                                type types-qos:ingress-policer-id;
                                description "The unique identifier for the policer.";
                            }

                            ///nokia-state/state/card/fp/ingress/network/queue-group/policer/statistics
                            container statistics {
                                description "Enter the statistics context";

                                ///nokia-state/state/card/fp/ingress/network/queue-group/policer/statistics/stat-mode
                                choice stat-mode {
                                    ///nokia-state/state/card/fp/ingress/network/queue-group/policer/statistics/stat-mode/minimal
                                    case minimal {

                                        ///nokia-state/state/card/fp/ingress/network/queue-group/policer/statistics/stat-mode/minimal/minimal
                                        container minimal {
                                            description "Enter the minimal context";

                                            ///nokia-state/state/card/fp/ingress/network/queue-group/policer/statistics/stat-mode/minimal/minimal/all-offered-packets
                                            leaf all-offered-packets {
                                                type yang:counter64;
                                                description "The number of all the priority packets offered by the packet processor to traffic manager";
                                            }

                                            ///nokia-state/state/card/fp/ingress/network/queue-group/policer/statistics/stat-mode/minimal/minimal/all-offered-octets
                                            leaf all-offered-octets {
                                                type yang:counter64;
                                                description "The number of all the priority octets offered by the packet processor to traffic manager";
                                            }

                                            ///nokia-state/state/card/fp/ingress/network/queue-group/policer/statistics/stat-mode/minimal/minimal/all-dropped-packets
                                            leaf all-dropped-packets {
                                                type yang:counter64;
                                                description "The number of all the priority packets dropped by the packet processor to traffic manager";
                                            }

                                            ///nokia-state/state/card/fp/ingress/network/queue-group/policer/statistics/stat-mode/minimal/minimal/all-dropped-octets
                                            leaf all-dropped-octets {
                                                type yang:counter64;
                                                description "The number of all the priority octets dropped by the packet processor to traffic manager";
                                            }

                                            ///nokia-state/state/card/fp/ingress/network/queue-group/policer/statistics/stat-mode/minimal/minimal/all-forwarded-packets
                                            leaf all-forwarded-packets {
                                                type yang:counter64;
                                                description "The number of all the priority packets forwarded by the packet processor to traffic manager";
                                            }

                                            ///nokia-state/state/card/fp/ingress/network/queue-group/policer/statistics/stat-mode/minimal/minimal/all-forwarded-octets
                                            leaf all-forwarded-octets {
                                                type yang:counter64;
                                                description "The number of all the priority octets forwarded by the packet processor to traffic manager";
                                            }

                                        } // container minimal

                                    }
                                    ///nokia-state/state/card/fp/ingress/network/queue-group/policer/statistics/stat-mode/offered-profile-no-cir
                                    case offered-profile-no-cir {

                                        ///nokia-state/state/card/fp/ingress/network/queue-group/policer/statistics/stat-mode/offered-profile-no-cir/offered-profile-no-cir
                                        container offered-profile-no-cir {
                                            description "Enter the offered-profile-no-cir context";

                                            ///nokia-state/state/card/fp/ingress/network/queue-group/policer/statistics/stat-mode/offered-profile-no-cir/offered-profile-no-cir/in-profile-offered-packets
                                            leaf in-profile-offered-packets {
                                                type yang:counter64;
                                                description "The number of in-profile packets offered by the packet processor to traffic manager";
                                            }

                                            ///nokia-state/state/card/fp/ingress/network/queue-group/policer/statistics/stat-mode/offered-profile-no-cir/offered-profile-no-cir/in-profile-offered-octets
                                            leaf in-profile-offered-octets {
                                                type yang:counter64;
                                                description "The number of in-profile octets offered by the packet processor to traffic manager";
                                            }

                                            ///nokia-state/state/card/fp/ingress/network/queue-group/policer/statistics/stat-mode/offered-profile-no-cir/offered-profile-no-cir/out-profile-offered-packets
                                            leaf out-profile-offered-packets {
                                                type yang:counter64;
                                                description "The number of out-of-profile packets offered by the packet processor to traffic manager";
                                            }

                                            ///nokia-state/state/card/fp/ingress/network/queue-group/policer/statistics/stat-mode/offered-profile-no-cir/offered-profile-no-cir/out-profile-offered-octets
                                            leaf out-profile-offered-octets {
                                                type yang:counter64;
                                                description "The number of out-of-profile octets offered by the packet processor to traffic manager";
                                            }

                                            ///nokia-state/state/card/fp/ingress/network/queue-group/policer/statistics/stat-mode/offered-profile-no-cir/offered-profile-no-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-profile-no-cir/offered-profile-no-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-profile-no-cir/offered-profile-no-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-profile-no-cir/offered-profile-no-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-profile-no-cir/offered-profile-no-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-profile-no-cir/offered-profile-no-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-profile-no-cir/offered-profile-no-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-profile-no-cir/offered-profile-no-cir/out-profile-forwarded-octets
                                            leaf out-profile-forwarded-octets {
                                                type yang:counter64;
                                                description "The number of out-of-profile octets forwarded by the packet processor to traffic manager";
                                            }

                                        } // container offered-profile-no-cir

                                    }
                                    ///nokia-state/state/card/fp/ingress/network/queue-group/policer/statistics/stat-mode/offered-priority-no-cir
                                    case offered-priority-no-cir {

                                        ///nokia-state/state/card/fp/ingress/network/queue-group/policer/statistics/stat-mode/offered-priority-no-cir/offered-priority-no-cir
                                        container offered-priority-no-cir {
                                            description "Enter the offered-priority-no-cir context";

                                            ///nokia-state/state/card/fp/ingress/network/queue-group/policer/statistics/stat-mode/offered-priority-no-cir/offered-priority-no-cir/high-priority-offered-packets
                                            leaf high-priority-offered-packets {
                                                type yang:counter64;
                                                description "The number of high-priority packets offered by the packet processor to traffic manager";
                                            }

                                            ///nokia-state/state/card/fp/ingress/network/queue-group/policer/statistics/stat-mode/offered-priority-no-cir/offered-priority-no-cir/high-priority-offered-octets
                                            leaf high-priority-offered-octets {
                                                type yang:counter64;
                                                description "The number of high-priority octets offered by the packet processor to traffic manager";
                                            }

                                            ///nokia-state/state/card/fp/ingress/network/queue-group/policer/statistics/stat-mode/offered-priority-no-cir/offered-priority-no-cir/low-priority-offered-packets
                                            leaf low-priority-offered-packets {
                                                type yang:counter64;
                                                description "The number of low-priority packets offered by the packet processor to traffic manager";
                                            }

                                            ///nokia-state/state/card/fp/ingress/network/queue-group/policer/statistics/stat-mode/offered-priority-no-cir/offered-priority-no-cir/low-priority-offered-octets
                                            leaf low-priority-offered-octets {
                                                type yang:counter64;
                                                description "The number of low-priority octets offered by the packet processor to traffic manager";
                                            }

                                            ///nokia-state/state/card/fp/ingress/network/queue-group/policer/statistics/stat-mode/offered-priority-no-cir/offered-priority-no-cir/high-priority-dropped-packets
                                            leaf high-priority-dropped-packets {
                                                type yang:counter64;
                                                description "The number of high-priority packets dropped by the packet processor to traffic manager";
                                            }

                                            ///nokia-state/state/card/fp/ingress/network/queue-group/policer/statistics/stat-mode/offered-priority-no-cir/offered-priority-no-cir/high-priority-dropped-octets
                                            leaf high-priority-dropped-octets {
                                                type yang:counter64;
                                                description "The number of high-priority octets dropped by the packet processor to traffic manager";
                                            }

                                            ///nokia-state/state/card/fp/ingress/network/queue-group/policer/statistics/stat-mode/offered-priority-no-cir/offered-priority-no-cir/low-priority-dropped-packets
                                            leaf low-priority-dropped-packets {
                                                type yang:counter64;
                                                description "The number of low-priority packets dropped by the packet processor to traffic manager";
                                            }

                                            ///nokia-state/state/card/fp/ingress/network/queue-group/policer/statistics/stat-mode/offered-priority-no-cir/offered-priority-no-cir/low-priority-dropped-octets
                                            leaf low-priority-dropped-octets {
                                                type yang:counter64;
                                                description "The number of low-priority octets dropped by the packet processor to traffic manager";
                                            }

                                            ///nokia-state/state/card/fp/ingress/network/queue-group/policer/statistics/stat-mode/offered-priority-no-cir/offered-priority-no-cir/high-priority-forwarded-packets
                                            leaf high-priority-forwarded-packets {
                                                type yang:counter64;
                                                description "The number of high-priority packets forwarded by the packet processor to traffic manager";
                                            }

                                            ///nokia-state/state/card/fp/ingress/network/queue-group/policer/statistics/stat-mode/offered-priority-no-cir/offered-priority-no-cir/high-priority-forwarded-octets
                                            leaf high-priority-forwarded-octets {
                                                type yang:counter64;
                                                description "The number of high-priority octets forwarded by the packet processor to traffic manager";
                                            }

                                            ///nokia-state/state/card/fp/ingress/network/queue-group/policer/statistics/stat-mode/offered-priority-no-cir/offered-priority-no-cir/low-priority-forwarded-packets
                                            leaf low-priority-forwarded-packets {
                                                type yang:counter64;
                                                description "The number of low-priority packets forwarded by the packet processor to traffic manager";
                                            }

                                            ///nokia-state/state/card/fp/ingress/network/queue-group/policer/statistics/stat-mode/offered-priority-no-cir/offered-priority-no-cir/low-priority-forwarded-octets
                                            leaf low-priority-forwarded-octets {
                                                type yang:counter64;
                                                description "The number of low-priority octets forwarded by the packet processor to traffic manager";
                                            }

                                        } // container offered-priority-no-cir

                                    }
                                    ///nokia-state/state/card/fp/ingress/network/queue-group/policer/statistics/stat-mode/offered-profile-cir
                                    case offered-profile-cir {

                                        ///nokia-state/state/card/fp/ingress/network/queue-group/policer/statistics/stat-mode/offered-profile-cir/offered-profile-cir
                                        container offered-profile-cir {
                                            description "Enter the offered-profile-cir context";

                                            ///nokia-state/state/card/fp/ingress/network/queue-group/policer/statistics/stat-mode/offered-profile-cir/offered-profile-cir/in-profile-offered-packets
                                            leaf in-profile-offered-packets {
                                                type yang:counter64;
                                                description "The number of in-profile packets offered by the packet processor to traffic manager";
                                            }

                                            ///nokia-state/state/card/fp/ingress/network/queue-group/policer/statistics/stat-mode/offered-profile-cir/offered-profile-cir/in-profile-offered-octets
                                            leaf in-profile-offered-octets {
                                                type yang:counter64;
                                                description "The number of in-profile octets offered by the packet processor to traffic manager";
                                            }

                                            ///nokia-state/state/card/fp/ingress/network/queue-group/policer/statistics/stat-mode/offered-profile-cir/offered-profile-cir/out-profile-offered-packets
                                            leaf out-profile-offered-packets {
                                                type yang:counter64;
                                                description "The number of out-of-profile packets offered by the packet processor to traffic manager";
                                            }

                                            ///nokia-state/state/card/fp/ingress/network/queue-group/policer/statistics/stat-mode/offered-profile-cir/offered-profile-cir/out-profile-offered-octets
                                            leaf out-profile-offered-octets {
                                                type yang:counter64;
                                                description "The number of out-of-profile octets offered by the packet processor to traffic manager";
                                            }

                                            ///nokia-state/state/card/fp/ingress/network/queue-group/policer/statistics/stat-mode/offered-profile-cir/offered-profile-cir/uncolor-offered-packets
                                            leaf uncolor-offered-packets {
                                                type yang:counter64;
                                                description "The number of uncolor packets offered by the packet processor to traffic manager";
                                            }

                                            ///nokia-state/state/card/fp/ingress/network/queue-group/policer/statistics/stat-mode/offered-profile-cir/offered-profile-cir/uncolor-offered-octets
                                            leaf uncolor-offered-octets {
                                                type yang:counter64;
                                                description "The number of uncolor octets offered by the packet processor to traffic manager";
                                            }

                                            ///nokia-state/state/card/fp/ingress/network/queue-group/policer/statistics/stat-mode/offered-profile-cir/offered-profile-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-profile-cir/offered-profile-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-profile-cir/offered-profile-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-profile-cir/offered-profile-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-profile-cir/offered-profile-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-profile-cir/offered-profile-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-profile-cir/offered-profile-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-profile-cir/offered-profile-cir/out-profile-forwarded-octets
                                            leaf out-profile-forwarded-octets {
                                                type yang:counter64;
                                                description "The number of out-of-profile octets forwarded by the packet processor to traffic manager";
                                            }

                                        } // container offered-profile-cir

                                    }
                                    ///nokia-state/state/card/fp/ingress/network/queue-group/policer/statistics/stat-mode/offered-priority-cir
                                    case offered-priority-cir {

                                        ///nokia-state/state/card/fp/ingress/network/queue-group/policer/statistics/stat-mode/offered-priority-cir/offered-priority-cir
                                        container offered-priority-cir {
                                            description "Enter the offered-priority-cir context";

                                            ///nokia-state/state/card/fp/ingress/network/queue-group/policer/statistics/stat-mode/offered-priority-cir/offered-priority-cir/high-priority-offered-packets
                                            leaf high-priority-offered-packets {
                                                type yang:counter64;
                                                description "The number of high-priority packets offered by the packet processor to traffic manager";
                                            }

                                            ///nokia-state/state/card/fp/ingress/network/queue-group/policer/statistics/stat-mode/offered-priority-cir/offered-priority-cir/high-priority-offered-octets
                                            leaf high-priority-offered-octets {
                                                type yang:counter64;
                                                description "The number of high-priority octets offered by the packet processor to traffic manager";
                                            }

                                            ///nokia-state/state/card/fp/ingress/network/queue-group/policer/statistics/stat-mode/offered-priority-cir/offered-priority-cir/low-priority-offered-packets
                                            leaf low-priority-offered-packets {
                                                type yang:counter64;
                                                description "The number of low-priority packets offered by the packet processor to traffic manager";
                                            }

                                            ///nokia-state/state/card/fp/ingress/network/queue-group/policer/statistics/stat-mode/offered-priority-cir/offered-priority-cir/low-priority-offered-octets
                                            leaf low-priority-offered-octets {
                                                type yang:counter64;
                                                description "The number of low-priority octets offered by the packet processor to traffic manager";
                                            }

                                            ///nokia-state/state/card/fp/ingress/network/queue-group/policer/statistics/stat-mode/offered-priority-cir/offered-priority-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-priority-cir/offered-priority-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-priority-cir/offered-priority-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-priority-cir/offered-priority-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-priority-cir/offered-priority-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-priority-cir/offered-priority-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-priority-cir/offered-priority-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-priority-cir/offered-priority-cir/out-profile-forwarded-octets
                                            leaf out-profile-forwarded-octets {
                                                type yang:counter64;
                                                description "The number of out-of-profile octets forwarded by the packet processor to traffic manager";
                                            }

                                        } // container offered-priority-cir

                                    }
                                    ///nokia-state/state/card/fp/ingress/network/queue-group/policer/statistics/stat-mode/offered-total-cir
                                    case offered-total-cir {

                                        ///nokia-state/state/card/fp/ingress/network/queue-group/policer/statistics/stat-mode/offered-total-cir/offered-total-cir
                                        container offered-total-cir {
                                            description "Enter the offered-total-cir context";

                                            ///nokia-state/state/card/fp/ingress/network/queue-group/policer/statistics/stat-mode/offered-total-cir/offered-total-cir/all-offered-packets
                                            leaf all-offered-packets {
                                                type yang:counter64;
                                                description "The number of all the priority packets offered by the packet processor to traffic manager";
                                            }

                                            ///nokia-state/state/card/fp/ingress/network/queue-group/policer/statistics/stat-mode/offered-total-cir/offered-total-cir/all-offered-octets
                                            leaf all-offered-octets {
                                                type yang:counter64;
                                                description "The number of all the priority octets offered by the packet processor to traffic manager";
                                            }

                                            ///nokia-state/state/card/fp/ingress/network/queue-group/policer/statistics/stat-mode/offered-total-cir/offered-total-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-total-cir/offered-total-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-total-cir/offered-total-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-total-cir/offered-total-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-total-cir/offered-total-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-total-cir/offered-total-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-total-cir/offered-total-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-total-cir/offered-total-cir/out-profile-forwarded-octets
                                            leaf out-profile-forwarded-octets {
                                                type yang:counter64;
                                                description "The number of out-of-profile octets forwarded by the packet processor to traffic manager";
                                            }

                                        } // container offered-total-cir

                                    }
                                    ///nokia-state/state/card/fp/ingress/network/queue-group/policer/statistics/stat-mode/offered-limited-profile-cir
                                    case offered-limited-profile-cir {

                                        ///nokia-state/state/card/fp/ingress/network/queue-group/policer/statistics/stat-mode/offered-limited-profile-cir/offered-limited-profile-cir
                                        container offered-limited-profile-cir {
                                            description "Enter the offered-limited-profile-cir context";

                                            ///nokia-state/state/card/fp/ingress/network/queue-group/policer/statistics/stat-mode/offered-limited-profile-cir/offered-limited-profile-cir/out-profile-offered-packets
                                            leaf out-profile-offered-packets {
                                                type yang:counter64;
                                                description "The number of out-of-profile packets offered by the packet processor to traffic manager";
                                            }

                                            ///nokia-state/state/card/fp/ingress/network/queue-group/policer/statistics/stat-mode/offered-limited-profile-cir/offered-limited-profile-cir/out-profile-offered-octets
                                            leaf out-profile-offered-octets {
                                                type yang:counter64;
                                                description "The number of out-of-profile octets offered by the packet processor to traffic manager";
                                            }

                                            ///nokia-state/state/card/fp/ingress/network/queue-group/policer/statistics/stat-mode/offered-limited-profile-cir/offered-limited-profile-cir/uncolor-offered-packets
                                            leaf uncolor-offered-packets {
                                                type yang:counter64;
                                                description "The number of uncolor packets offered by the packet processor to traffic manager";
                                            }

                                            ///nokia-state/state/card/fp/ingress/network/queue-group/policer/statistics/stat-mode/offered-limited-profile-cir/offered-limited-profile-cir/uncolor-offered-octets
                                            leaf uncolor-offered-octets {
                                                type yang:counter64;
                                                description "The number of uncolor octets offered by the packet processor to traffic manager";
                                            }

                                            ///nokia-state/state/card/fp/ingress/network/queue-group/policer/statistics/stat-mode/offered-limited-profile-cir/offered-limited-profile-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-limited-profile-cir/offered-limited-profile-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-limited-profile-cir/offered-limited-profile-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-limited-profile-cir/offered-limited-profile-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-limited-profile-cir/offered-limited-profile-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-limited-profile-cir/offered-limited-profile-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-limited-profile-cir/offered-limited-profile-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-limited-profile-cir/offered-limited-profile-cir/out-profile-forwarded-octets
                                            leaf out-profile-forwarded-octets {
                                                type yang:counter64;
                                                description "The number of out-of-profile octets forwarded by the packet processor to traffic manager";
                                            }

                                        } // container offered-limited-profile-cir

                                    }
                                    ///nokia-state/state/card/fp/ingress/network/queue-group/policer/statistics/stat-mode/offered-profile-capped-cir
                                    case offered-profile-capped-cir {

                                        ///nokia-state/state/card/fp/ingress/network/queue-group/policer/statistics/stat-mode/offered-profile-capped-cir/offered-profile-capped-cir
                                        container offered-profile-capped-cir {
                                            description "Enter the offered-profile-capped-cir context";

                                            ///nokia-state/state/card/fp/ingress/network/queue-group/policer/statistics/stat-mode/offered-profile-capped-cir/offered-profile-capped-cir/in-profile-offered-packets
                                            leaf in-profile-offered-packets {
                                                type yang:counter64;
                                                description "The number of in-profile packets offered by the packet processor to traffic manager";
                                            }

                                            ///nokia-state/state/card/fp/ingress/network/queue-group/policer/statistics/stat-mode/offered-profile-capped-cir/offered-profile-capped-cir/in-profile-offered-octets
                                            leaf in-profile-offered-octets {
                                                type yang:counter64;
                                                description "The number of in-profile octets offered by the packet processor to traffic manager";
                                            }

                                            ///nokia-state/state/card/fp/ingress/network/queue-group/policer/statistics/stat-mode/offered-profile-capped-cir/offered-profile-capped-cir/out-profile-offered-packets
                                            leaf out-profile-offered-packets {
                                                type yang:counter64;
                                                description "The number of out-of-profile packets offered by the packet processor to traffic manager";
                                            }

                                            ///nokia-state/state/card/fp/ingress/network/queue-group/policer/statistics/stat-mode/offered-profile-capped-cir/offered-profile-capped-cir/out-profile-offered-octets
                                            leaf out-profile-offered-octets {
                                                type yang:counter64;
                                                description "The number of out-of-profile octets offered by the packet processor to traffic manager";
                                            }

                                            ///nokia-state/state/card/fp/ingress/network/queue-group/policer/statistics/stat-mode/offered-profile-capped-cir/offered-profile-capped-cir/uncolor-offered-packets
                                            leaf uncolor-offered-packets {
                                                type yang:counter64;
                                                description "The number of uncolor packets offered by the packet processor to traffic manager";
                                            }

                                            ///nokia-state/state/card/fp/ingress/network/queue-group/policer/statistics/stat-mode/offered-profile-capped-cir/offered-profile-capped-cir/uncolor-offered-octets
                                            leaf uncolor-offered-octets {
                                                type yang:counter64;
                                                description "The number of uncolor octets offered by the packet processor to traffic manager";
                                            }

                                            ///nokia-state/state/card/fp/ingress/network/queue-group/policer/statistics/stat-mode/offered-profile-capped-cir/offered-profile-capped-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-profile-capped-cir/offered-profile-capped-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-profile-capped-cir/offered-profile-capped-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-profile-capped-cir/offered-profile-capped-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-profile-capped-cir/offered-profile-capped-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-profile-capped-cir/offered-profile-capped-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-profile-capped-cir/offered-profile-capped-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-profile-capped-cir/offered-profile-capped-cir/out-profile-forwarded-octets
                                            leaf out-profile-forwarded-octets {
                                                type yang:counter64;
                                                description "The number of out-of-profile octets forwarded by the packet processor to traffic manager";
                                            }

                                        } // container offered-profile-capped-cir

                                    }
                                    ///nokia-state/state/card/fp/ingress/network/queue-group/policer/statistics/stat-mode/offered-limited-capped-cir
                                    case offered-limited-capped-cir {

                                        ///nokia-state/state/card/fp/ingress/network/queue-group/policer/statistics/stat-mode/offered-limited-capped-cir/offered-limited-capped-cir
                                        container offered-limited-capped-cir {
                                            description "Enter the offered-limited-capped-cir context";

                                            ///nokia-state/state/card/fp/ingress/network/queue-group/policer/statistics/stat-mode/offered-limited-capped-cir/offered-limited-capped-cir/in-profile-offered-packets
                                            leaf in-profile-offered-packets {
                                                type yang:counter64;
                                                description "The number of in-profile packets offered by the packet processor to traffic manager";
                                            }

                                            ///nokia-state/state/card/fp/ingress/network/queue-group/policer/statistics/stat-mode/offered-limited-capped-cir/offered-limited-capped-cir/in-profile-offered-octets
                                            leaf in-profile-offered-octets {
                                                type yang:counter64;
                                                description "The number of in-profile octets offered by the packet processor to traffic manager";
                                            }

                                            ///nokia-state/state/card/fp/ingress/network/queue-group/policer/statistics/stat-mode/offered-limited-capped-cir/offered-limited-capped-cir/in-profile-dropped-packets
                                            leaf in-profile-dropped-packets {
                                                type yang:counter64;
                                                description "The number of in-profile packets dropped by the packet processor to traffic manager";
                                            }

                                            ///nokia-state/state/card/fp/ingress/network/queue-group/policer/statistics/stat-mode/offered-limited-capped-cir/offered-limited-capped-cir/in-profile-dropped-octets
                                            leaf in-profile-dropped-octets {
                                                type yang:counter64;
                                                description "The number of in-profile octets dropped by the packet processor to traffic manager";
                                            }

                                            ///nokia-state/state/card/fp/ingress/network/queue-group/policer/statistics/stat-mode/offered-limited-capped-cir/offered-limited-capped-cir/out-profile-dropped-packets
                                            leaf out-profile-dropped-packets {
                                                type yang:counter64;
                                                description "The number of out-of-profile packets dropped by the packet processor to traffic manager";
                                            }

                                            ///nokia-state/state/card/fp/ingress/network/queue-group/policer/statistics/stat-mode/offered-limited-capped-cir/offered-limited-capped-cir/out-profile-dropped-octets
                                            leaf out-profile-dropped-octets {
                                                type yang:counter64;
                                                description "The number of out-of-profile octets dropped by the packet processor to traffic manager";
                                            }

                                            ///nokia-state/state/card/fp/ingress/network/queue-group/policer/statistics/stat-mode/offered-limited-capped-cir/offered-limited-capped-cir/in-profile-forwarded-packets
                                            leaf in-profile-forwarded-packets {
                                                type yang:counter64;
                                                description "The number of in-profile packets forwarded by the packet processor to traffic manager";
                                            }

                                            ///nokia-state/state/card/fp/ingress/network/queue-group/policer/statistics/stat-mode/offered-limited-capped-cir/offered-limited-capped-cir/in-profile-forwarded-octets
                                            leaf in-profile-forwarded-octets {
                                                type yang:counter64;
                                                description "The number of in-profile octets forwarded by the packet processor to traffic manager";
                                            }

                                            ///nokia-state/state/card/fp/ingress/network/queue-group/policer/statistics/stat-mode/offered-limited-capped-cir/offered-limited-capped-cir/out-profile-forwarded-packets
                                            leaf out-profile-forwarded-packets {
                                                type yang:counter64;
                                                description "The number of out-of-profile packets forwarded by the packet processor to traffic manager";
                                            }

                                            ///nokia-state/state/card/fp/ingress/network/queue-group/policer/statistics/stat-mode/offered-limited-capped-cir/offered-limited-capped-cir/out-profile-forwarded-octets
                                            leaf out-profile-forwarded-octets {
                                                type yang:counter64;
                                                description "The number of out-of-profile octets forwarded by the packet processor to traffic manager";
                                            }

                                            ///nokia-state/state/card/fp/ingress/network/queue-group/policer/statistics/stat-mode/offered-limited-capped-cir/offered-limited-capped-cir/uncolor-offered-packets
                                            leaf uncolor-offered-packets {
                                                type yang:counter64;
                                                description "The number of out-of-rofile packets offered by the packet processor to traffic manager";
                                            }

                                            ///nokia-state/state/card/fp/ingress/network/queue-group/policer/statistics/stat-mode/offered-limited-capped-cir/offered-limited-capped-cir/uncolor-offered-octets
                                            leaf uncolor-offered-octets {
                                                type yang:counter64;
                                                description "The number of out-of-profile octets offered by the packet processor to traffic manager";
                                            }

                                        } // container offered-limited-capped-cir

                                    }
                                }
                            } // container statistics

                            ///nokia-state/state/card/fp/ingress/network/queue-group/policer/hardware-policer
                            container hardware-policer {
                                description "Enter the hardware-policer context";

                                ///nokia-state/state/card/fp/ingress/network/queue-group/policer/hardware-policer/adapted-admin-cbs
                                leaf adapted-admin-cbs {
                                    type int64;
                                    units "bytes";
                                    description "Admin CBS.";
                                }

                                ///nokia-state/state/card/fp/ingress/network/queue-group/policer/hardware-policer/adapted-admin-mbs
                                leaf adapted-admin-mbs {
                                    type int64;
                                    units "bytes";
                                    description "Admin MBS.";
                                }

                                ///nokia-state/state/card/fp/ingress/network/queue-group/policer/hardware-policer/adapted-hp-only
                                leaf adapted-hp-only {
                                    type int64;
                                    units "bytes";
                                    description "Hi Prio Only.";
                                }

                                ///nokia-state/state/card/fp/ingress/network/queue-group/policer/hardware-policer/depth
                                leaf depth {
                                    type int64;
                                    units "bytes";
                                    description "Depth.";
                                }

                                ///nokia-state/state/card/fp/ingress/network/queue-group/policer/hardware-policer/operational-cir
                                leaf operational-cir {
                                    type types-qos:int32-max;
                                    description "Oper CIR.";
                                }

                                ///nokia-state/state/card/fp/ingress/network/queue-group/policer/hardware-policer/operational-fir
                                leaf operational-fir {
                                    type types-qos:int32-max;
                                    description "Oper FIR.";
                                }

                                ///nokia-state/state/card/fp/ingress/network/queue-group/policer/hardware-policer/operational-pir
                                leaf operational-pir {
                                    type types-qos:int32-max;
                                    description "Oper PIR.";
                                }

                            } // container hardware-policer

                        } // list policer

                    } // list queue-group

                    ///nokia-state/state/card/fp/ingress/network/queue
                    list queue {
                        key "queue-id";
                        description "Enter the queue list instance";

                        ///nokia-state/state/card/fp/ingress/network/queue/queue-id
                        leaf queue-id {
                            type types-qos:ingress-queue-id;
                            description "The unique identifier for the queue.";
                        }

                        ///nokia-state/state/card/fp/ingress/network/queue/hardware-queue
                        list hardware-queue {
                            key "source-tap-offset dest-card dest-fp dest-tap-offset";
                            description "Enter the hardware-queue list instance";

                            ///nokia-state/state/card/fp/ingress/network/queue/hardware-queue/source-tap-offset
                            leaf source-tap-offset {
                                type int32;
                                description "Source TAP.";
                            }

                            ///nokia-state/state/card/fp/ingress/network/queue/hardware-queue/dest-card
                            leaf dest-card {
                                type int32;
                                description "Card number";
                            }

                            ///nokia-state/state/card/fp/ingress/network/queue/hardware-queue/dest-fp
                            leaf dest-fp {
                                type int32;
                                description "FP number";
                            }

                            ///nokia-state/state/card/fp/ingress/network/queue/hardware-queue/dest-tap-offset
                            leaf dest-tap-offset {
                                type int32;
                                description "Destination TAP.";
                            }

                            ///nokia-state/state/card/fp/ingress/network/queue/hardware-queue/adapted-admin-mbs
                            leaf adapted-admin-mbs {
                                type int64;
                                units "bytes";
                                description "Admin MBS.";
                            }

                            ///nokia-state/state/card/fp/ingress/network/queue/hardware-queue/adapted-admin-cbs
                            leaf adapted-admin-cbs {
                                type types-qos:bytes;
                                units "bytes";
                                description "Admin CBS.";
                            }

                            ///nokia-state/state/card/fp/ingress/network/queue/hardware-queue/operational-mbs
                            leaf operational-mbs {
                                type int64;
                                units "bytes";
                                description "Oper MBS.";
                            }

                            ///nokia-state/state/card/fp/ingress/network/queue/hardware-queue/depth
                            leaf depth {
                                type union {
                                    type enumeration {
                                        enum max                            { value -1; }
                                    }
                                    type int64;
                                }
                                description "Depth CIR.";
                            }

                            ///nokia-state/state/card/fp/ingress/network/queue/hardware-queue/operational-cir
                            leaf operational-cir {
                                type union {
                                    type enumeration {
                                        enum max                            { value -1; }
                                    }
                                    type int64;
                                }
                                description "Oper CIR.";
                            }

                            ///nokia-state/state/card/fp/ingress/network/queue/hardware-queue/operational-fir
                            leaf operational-fir {
                                type union {
                                    type enumeration {
                                        enum max                            { value -1; }
                                    }
                                    type int64;
                                }
                                description "Oper FIR.";
                            }

                            ///nokia-state/state/card/fp/ingress/network/queue/hardware-queue/operational-pir
                            leaf operational-pir {
                                type union {
                                    type enumeration {
                                        enum max                            { value -1; }
                                    }
                                    type int64;
                                }
                                description "Oper PIR.";
                            }

                            ///nokia-state/state/card/fp/ingress/network/queue/hardware-queue/exceed-droptail
                            leaf exceed-droptail {
                                type union {
                                    type int64 {
                                        range "0..max";
                                    }
                                    type enumeration {
                                        enum auto                           { value -1; }
                                    }
                                }
                                description "Exceed droptail.";
                            }

                            ///nokia-state/state/card/fp/ingress/network/queue/hardware-queue/high-droptail
                            leaf high-droptail {
                                type union {
                                    type int64 {
                                        range "0..max";
                                    }
                                    type enumeration {
                                        enum auto                           { value -1; }
                                    }
                                }
                                description "High droptail.";
                            }

                            ///nokia-state/state/card/fp/ingress/network/queue/hardware-queue/high-plus-droptail
                            leaf high-plus-droptail {
                                type union {
                                    type int64 {
                                        range "0..max";
                                    }
                                    type enumeration {
                                        enum auto                           { value -1; }
                                    }
                                }
                                description "Highplus droptail.";
                            }

                            ///nokia-state/state/card/fp/ingress/network/queue/hardware-queue/low-droptail
                            leaf low-droptail {
                                type union {
                                    type int64 {
                                        range "0..max";
                                    }
                                    type enumeration {
                                        enum auto                           { value -1; }
                                    }
                                }
                                description "Low droptail.";
                            }

                            ///nokia-state/state/card/fp/ingress/network/queue/hardware-queue/operational-exceed-burst
                            leaf operational-exceed-burst {
                                type types-qos:int64-max;
                                description "Oper burst exceed.";
                            }

                            ///nokia-state/state/card/fp/ingress/network/queue/hardware-queue/operational-max-transmit-data-size
                            leaf operational-max-transmit-data-size {
                                type types-qos:int64-max;
                                description "Oper max transmit data size.";
                            }

                            ///nokia-state/state/card/fp/ingress/network/queue/hardware-queue/operational-burst-fir
                            leaf operational-burst-fir {
                                type types-qos:int64-max;
                                description "Oper burst FIR.";
                            }

                        } // list hardware-queue

                    } // list queue

                    ///nokia-state/state/card/fp/ingress/network/pool
                    list pool {
                        key "name";
                        description "Enter the pool list instance";

                        ///nokia-state/state/card/fp/ingress/network/pool/name
                        leaf name {
                            type types-sros:named-item;
                            description "Network ingress pool name for the FP";
                        }

                        ///nokia-state/state/card/fp/ingress/network/pool/pool-usage
                        container pool-usage {
                            description "Enter the pool-usage context";

                            ///nokia-state/state/card/fp/ingress/network/pool/pool-usage/total-pool-size
                            leaf total-pool-size {
                                type uint32;
                                units "kilobytes";
                                description "Total buffer pools size.";
                            }

                            ///nokia-state/state/card/fp/ingress/network/pool/pool-usage/total-pool-in-use
                            leaf total-pool-in-use {
                                type uint32;
                                units "kilobytes";
                                description "Total buffer pools size in use.";
                            }

                            ///nokia-state/state/card/fp/ingress/network/pool/pool-usage/shared-pool-size
                            leaf shared-pool-size {
                                type uint32;
                                units "kilobytes";
                                description "Total shared pools size.";
                            }

                            ///nokia-state/state/card/fp/ingress/network/pool/pool-usage/shared-pool-in-use
                            leaf shared-pool-in-use {
                                type uint32;
                                units "kilobytes";
                                description "Total shared pools size in use.";
                            }

                            ///nokia-state/state/card/fp/ingress/network/pool/pool-usage/reserved-pool-size
                            leaf reserved-pool-size {
                                type uint32;
                                units "kilobytes";
                                description "Total reserved pools size.";
                            }

                            ///nokia-state/state/card/fp/ingress/network/pool/pool-usage/reserved-pool-in-use
                            leaf reserved-pool-in-use {
                                type uint32;
                                units "kilobytes";
                                description "Total reserved pools size in use.";
                            }

                        } // container pool-usage


                    } // list pool

                } // container network

                ///nokia-state/state/card/fp/ingress/policy-accounting
                container policy-accounting {
                    description "Enter the policy-accounting context";

                    ///nokia-state/state/card/fp/ingress/policy-accounting/classes-in-use
                    leaf classes-in-use {
                        type uint32;
                        description "Indicates the total number of policy accounting class resources currently in use.";
                    }

                    ///nokia-state/state/card/fp/ingress/policy-accounting/policers-in-use
                    leaf policers-in-use {
                        type uint32;
                        description "Indicates the total number of policy accounting policer resources currently in use.";
                    }

                } // container policy-accounting

                ///nokia-state/state/card/fp/ingress/dist-cpu-protection
                container dist-cpu-protection {
                    description "Enter the dist-cpu-protection context";

                    ///nokia-state/state/card/fp/ingress/dist-cpu-protection/dynamic-policer
                    container dynamic-policer {
                        description "Enter the dynamic-policer context";

                        ///nokia-state/state/card/fp/ingress/dist-cpu-protection/dynamic-policer/in-use
                        leaf in-use {
                            type uint32;
                            description "Number of dynamic-policers in-use";
                        }

                        ///nokia-state/state/card/fp/ingress/dist-cpu-protection/dynamic-policer/high-water-mark-hit-count
                        leaf high-water-mark-hit-count {
                            type uint32;
                            description "High water-mark hit-count";
                        }

                        ///nokia-state/state/card/fp/ingress/dist-cpu-protection/dynamic-policer/high-water-mark-hit-time
                        leaf high-water-mark-hit-time {
                            type yang:date-and-time;
                            description "High water-mark hit-time";
                        }

                        ///nokia-state/state/card/fp/ingress/dist-cpu-protection/dynamic-policer/allocation-fail-count
                        leaf allocation-fail-count {
                            type uint32;
                            description "Count of allocation fails for dynamic-policers";
                        }

                    } // container dynamic-policer

                } // container dist-cpu-protection

                ///nokia-state/state/card/fp/ingress/burst-control-group
                list burst-control-group {
                    key "bcg-visitation-time";
                    description "Enter the burst-control-group list instance";

                    ///nokia-state/state/card/fp/ingress/burst-control-group/bcg-visitation-time
                    leaf bcg-visitation-time {
                        type types-sros:named-item-255;
                        description
                            "The unique value which uniquely identifies the visitation time of the burst control
                             group within a specific IOM card in the system.";
                    }

                    ///nokia-state/state/card/fp/ingress/burst-control-group/recalc-info
                    container recalc-info {
                        description "Enter the recalc-info context";

                        ///nokia-state/state/card/fp/ingress/burst-control-group/recalc-info/num-queue
                        leaf num-queue {
                            type uint32;
                            description "The number of queues associsted to this burst control group.";
                        }

                        ///nokia-state/state/card/fp/ingress/burst-control-group/recalc-info/at-risk
                        leaf at-risk {
                            type boolean;
                            description "The burst control group is at risk or not.";
                        }

                        ///nokia-state/state/card/fp/ingress/burst-control-group/recalc-info/current
                        leaf current {
                            type string;
                            description "The burst control group worst seen current time.";
                        }

                        ///nokia-state/state/card/fp/ingress/burst-control-group/recalc-info/worst-case
                        leaf worst-case {
                            type string;
                            description "The burst control group worst seen ever time.";
                        }

                        ///nokia-state/state/card/fp/ingress/burst-control-group/recalc-info/avg-last-readings
                        leaf avg-last-readings {
                            type string;
                            description "The burst control group last seen ten readings.";
                        }

                        ///nokia-state/state/card/fp/ingress/burst-control-group/recalc-info/avg-worst-seen-readings
                        leaf avg-worst-seen-readings {
                            type string;
                            description "The burst control group last ten worst seen readings.";
                        }

                        ///nokia-state/state/card/fp/ingress/burst-control-group/recalc-info/worst-possible-ever
                        leaf worst-possible-ever {
                            type string;
                            description "The burst control group worst ever configuration at 100%% scheduling predicted readings.";
                        }

                        ///nokia-state/state/card/fp/ingress/burst-control-group/recalc-info/worst-possible-current
                        leaf worst-possible-current {
                            type string;
                            description "The burst control group worst current map at 100%% scheduling predicted readings.";
                        }

                        ///nokia-state/state/card/fp/ingress/burst-control-group/recalc-info/worst-provisioned-ever
                        leaf worst-provisioned-ever {
                            type string;
                            description "The burst control group worst ever configuration at provisioned predicted readings.";
                        }

                        ///nokia-state/state/card/fp/ingress/burst-control-group/recalc-info/worst-provisioned-current
                        leaf worst-provisioned-current {
                            type string;
                            description "The burst control group worst current map at provisioned predicted readings.";
                        }

                    } // container recalc-info

                } // list burst-control-group

            } // container ingress

            ///nokia-state/state/card/fp/oversubscribed-resource
            list oversubscribed-resource {
                key "resource-type";
                description "Enter the oversubscribed-resource list instance";

                ///nokia-state/state/card/fp/oversubscribed-resource/resource-type
                leaf resource-type {
                    type enumeration {
                        enum sram-buf                       { value 1; }
                        enum sram-pdb                       { value 2; }
                        enum dram-bdb                       { value 3; }
                        enum dram-bandwidth                 { value 4; }
                        enum core-process-pipeline          { value 5; }
                        enum mesh-fabric-bandwidth          { value 6; }
                    }
                    description "Specifies the FP resource which may be oversubscribed.";
                }

                ///nokia-state/state/card/fp/oversubscribed-resource/detected
                leaf detected {
                    type uint32;
                    description
                        "Indicates the number of seconds it has been detected that the resource
                         has been oversubscribed.";
                }

            } // list oversubscribed-resource

            ///nokia-state/state/card/fp/statistics
            container statistics {
                description "Enter the statistics context";

                ///nokia-state/state/card/fp/statistics/ingress-fcs-error
                leaf ingress-fcs-error {
                    type yang:counter32;
                    description
                        "Indicates the number of times the complex experienced a FCS
                         error in the ingress direction since startup, last clear,
                         or card reboot.";
                }

                ///nokia-state/state/card/fp/statistics/ingress-fcs-error-time
                leaf ingress-fcs-error-time {
                    type yang:date-and-time;
                    description "Indicates the last time ingress-fcs-error incremented.";
                }

                ///nokia-state/state/card/fp/statistics/egress-fcs-error
                leaf egress-fcs-error {
                    type yang:counter32;
                    description
                        "Indicates the number of times the complex experienced a FCS
                         error in the egress direction since startup, last clear, or
                         card reboot.";
                }

                ///nokia-state/state/card/fp/statistics/egress-fcs-error-time
                leaf egress-fcs-error-time {
                    type yang:date-and-time;
                    description "Indicates the last time egress-fcs-error incremented.";
                }

                ///nokia-state/state/card/fp/statistics/memory-parity-error
                leaf memory-parity-error {
                    type yang:counter32;
                    description
                        "Indicates the number of times the complex experienced a memory
                         parity error since startup, last clear, or card reboot.";
                }

                ///nokia-state/state/card/fp/statistics/memory-parity-error-time
                leaf memory-parity-error-time {
                    type yang:date-and-time;
                    description "Indicates the last time memory-parity-error incremented.";
                }

                ///nokia-state/state/card/fp/statistics/cam-error
                leaf cam-error {
                    type yang:counter32;
                    description
                        "Indicates the number of times the complex experienced a CAM
                         error since startup, last clear, or card reboot.";
                }

                ///nokia-state/state/card/fp/statistics/cam-error-time
                leaf cam-error-time {
                    type yang:date-and-time;
                    description "Indicates the last time cam-error incremented.";
                }

                ///nokia-state/state/card/fp/statistics/buffer-memory-error
                leaf buffer-memory-error {
                    type yang:counter32;
                    description
                        "Indicates the number of times the complex experienced a buffer
                         memory error since startup, last clear, or card reboot.";
                }

                ///nokia-state/state/card/fp/statistics/buffer-memory-error-time
                leaf buffer-memory-error-time {
                    type yang:date-and-time;
                    description "Indicates the last time buffer-memory-error incremented.";
                }

                ///nokia-state/state/card/fp/statistics/statistics-memory-error
                leaf statistics-memory-error {
                    type yang:counter32;
                    description
                        "Indicates the number of times the complex experienced a
                         statistics memory error since startup, last clear, or card
                         reboot.";
                }

                ///nokia-state/state/card/fp/statistics/statistics-memory-error-time
                leaf statistics-memory-error-time {
                    type yang:date-and-time;
                    description "Indicates the last time statistics-memory-error incremented.";
                }

                ///nokia-state/state/card/fp/statistics/internal-memory-error
                leaf internal-memory-error {
                    type yang:counter32;
                    description
                        "Indicates the number of times the complex experienced an
                         internal memory error since startup, last clear, or card
                         reboot.";
                }

                ///nokia-state/state/card/fp/statistics/internal-memory-error-time
                leaf internal-memory-error-time {
                    type yang:date-and-time;
                    description "Indicates the last time internal-memory-error incremented.";
                }

                ///nokia-state/state/card/fp/statistics/internal-datapath-error
                leaf internal-datapath-error {
                    type yang:counter32;
                    description
                        "Indicates the number of times the complex experienced an
                         internal datapath error since startup, last clear, or card
                         reboot.";
                }

                ///nokia-state/state/card/fp/statistics/internal-datapath-error-time
                leaf internal-datapath-error-time {
                    type yang:date-and-time;
                    description "Indicates the last time internal-datapath-error incremented.";
                }

                ///nokia-state/state/card/fp/statistics/internal-datapath-cell-error
                leaf internal-datapath-cell-error {
                    type yang:counter32;
                    description
                        "Indicates the number of times the complex experienced an
                         internal datapath cell error since startup, last clear, or
                         card reboot.";
                }

                ///nokia-state/state/card/fp/statistics/internal-datapath-cell-error-time
                leaf internal-datapath-cell-error-time {
                    type yang:date-and-time;
                    description
                        "Indicates the last time internal-datapath-cell-error
                         incremented.";
                }

                ///nokia-state/state/card/fp/statistics/source-slots-egress-fcs-error
                leaf source-slots-egress-fcs-error {
                    type types-card:card-slot-bitmap;
                    description
                        "Indicates the source slots reported from the last time
                         egress-fcs-error incremented.";
                }

                ///nokia-state/state/card/fp/statistics/egress-encap-exceeded
                leaf egress-encap-exceeded {
                    type yang:counter64;
                    units "packets";
                    description
                        "Addition of egress encapsulation headers would have exceeded
                         the maximum frame size.";
                }

                ///nokia-state/state/card/fp/statistics/egress-mtu-exceeded
                leaf egress-mtu-exceeded {
                    type yang:counter64;
                    units "packets";
                    description
                        "Protocol supports packet fragmentation but fragmentation was
                         blocked (for example packet is IPv6 or packet is IPv4 and DF
                         set to one).";
                }

                ///nokia-state/state/card/fp/statistics/egress-frame-too-big-for-port
                leaf egress-frame-too-big-for-port {
                    type yang:counter64;
                    units "packets";
                    description
                        "Final check before transmitting has detected frame exceeded
                         the port MTU.";
                }

                ///nokia-state/state/card/fp/statistics/tchip-parity-error
                leaf tchip-parity-error {
                    type yang:counter32;
                    description
                        "Indicates the number of times the TChip experienced a
                         parity error since startup, last clear, or card reboot.";
                }

                ///nokia-state/state/card/fp/statistics/tchip-parity-error-time
                leaf tchip-parity-error-time {
                    type yang:date-and-time;
                    description "Indicates the last time tchip-parity-error incremented.";
                }

            } // container statistics

            ///nokia-state/state/card/fp/resource-usage
            container resource-usage {
                description "Enter the resource-usage context";

                ///nokia-state/state/card/fp/resource-usage/resource-oversubscribed
                leaf resource-oversubscribed {
                    type bits {
                        bit sram-buf                       { position 0; }
                        bit sram-pdb                       { position 1; }
                        bit dram-bdb                       { position 2; }
                        bit dram-bandwidth                 { position 3; }
                        bit core-processing-pipeline       { position 4; }
                        bit mesh-fabric-bandwidth          { position 5; }
                    }
                    description
                        "Indicates which resources are oversubscribed on this FP.
                         When no bits are set, none of the FP's resources are exhausted.";
                }

                ///nokia-state/state/card/fp/resource-usage/sap-ingress-qos-policies
                container sap-ingress-qos-policies {
                    description "Enter the sap-ingress-qos-policies context";

                    ///nokia-state/state/card/fp/resource-usage/sap-ingress-qos-policies/total
                    leaf total {
                        type yang:counter32;
                        description "The total number of resources supported on this FP.";
                    }

                    ///nokia-state/state/card/fp/resource-usage/sap-ingress-qos-policies/allocated
                    leaf allocated {
                        type yang:counter32;
                        description "The total number of resources that are currently allocated on this FP.";
                    }

                    ///nokia-state/state/card/fp/resource-usage/sap-ingress-qos-policies/free
                    leaf free {
                        type yang:counter32;
                        description "The total number of resources that are remaining free on this FP.";
                    }

                } // container sap-ingress-qos-policies

                ///nokia-state/state/card/fp/resource-usage/dynamic-egress-classification
                container dynamic-egress-classification {
                    description "Enter the dynamic-egress-classification context";

                    ///nokia-state/state/card/fp/resource-usage/dynamic-egress-classification/total
                    leaf total {
                        type yang:counter32;
                        description "The total number of resources supported on this FP.";
                    }

                    ///nokia-state/state/card/fp/resource-usage/dynamic-egress-classification/allocated
                    leaf allocated {
                        type yang:counter32;
                        description "The total number of resources that are currently allocated on this FP.";
                    }

                    ///nokia-state/state/card/fp/resource-usage/dynamic-egress-classification/free
                    leaf free {
                        type yang:counter32;
                        description "The total number of resources that are remaining free on this FP.";
                    }

                    ///nokia-state/state/card/fp/resource-usage/dynamic-egress-classification/in-use-by-sap-egress
                    container in-use-by-sap-egress {
                        description "Enter the in-use-by-sap-egress context";

                        ///nokia-state/state/card/fp/resource-usage/dynamic-egress-classification/in-use-by-sap-egress/allocated
                        leaf allocated {
                            type yang:counter32;
                            description "The total number of resources that are currently allocated on this FP.";
                        }

                    } // container in-use-by-sap-egress

                    ///nokia-state/state/card/fp/resource-usage/dynamic-egress-classification/in-use-by-network-egress
                    container in-use-by-network-egress {
                        description "Enter the in-use-by-network-egress context";

                        ///nokia-state/state/card/fp/resource-usage/dynamic-egress-classification/in-use-by-network-egress/allocated
                        leaf allocated {
                            type yang:counter32;
                            description "The total number of resources that are currently allocated on this FP.";
                        }

                    } // container in-use-by-network-egress

                } // container dynamic-egress-classification

                ///nokia-state/state/card/fp/resource-usage/ingress-queues
                container ingress-queues {
                    description "Enter the ingress-queues context";

                    ///nokia-state/state/card/fp/resource-usage/ingress-queues/total
                    leaf total {
                        type yang:counter32;
                        description "The total number of resources supported on this FP.";
                    }

                    ///nokia-state/state/card/fp/resource-usage/ingress-queues/allocated
                    leaf allocated {
                        type yang:counter32;
                        description "The total number of resources that are currently allocated on this FP.";
                    }

                    ///nokia-state/state/card/fp/resource-usage/ingress-queues/free
                    leaf free {
                        type yang:counter32;
                        description "The total number of resources that are remaining free on this FP.";
                    }

                } // container ingress-queues

                ///nokia-state/state/card/fp/resource-usage/egress-queues
                container egress-queues {
                    description "Enter the egress-queues context";

                    ///nokia-state/state/card/fp/resource-usage/egress-queues/total
                    leaf total {
                        type yang:counter32;
                        description "The total number of resources supported on this FP.";
                    }

                    ///nokia-state/state/card/fp/resource-usage/egress-queues/allocated
                    leaf allocated {
                        type yang:counter32;
                        description "The total number of resources that are currently allocated on this FP.";
                    }

                    ///nokia-state/state/card/fp/resource-usage/egress-queues/free
                    leaf free {
                        type yang:counter32;
                        description "The total number of resources that are remaining free on this FP.";
                    }

                } // container egress-queues

                ///nokia-state/state/card/fp/resource-usage/ingress-policers
                container ingress-policers {
                    description "Enter the ingress-policers context";

                    ///nokia-state/state/card/fp/resource-usage/ingress-policers/total
                    leaf total {
                        type yang:counter32;
                        description "The total number of resources supported on this FP.";
                    }

                    ///nokia-state/state/card/fp/resource-usage/ingress-policers/allocated
                    leaf allocated {
                        type yang:counter32;
                        description "The total number of resources that are currently allocated on this FP.";
                    }

                    ///nokia-state/state/card/fp/resource-usage/ingress-policers/free
                    leaf free {
                        type yang:counter32;
                        description "The total number of resources that are remaining free on this FP.";
                    }

                } // container ingress-policers

                ///nokia-state/state/card/fp/resource-usage/ingress-policer-stat-entries
                container ingress-policer-stat-entries {
                    description "Enter the ingress-policer-stat-entries context";

                    ///nokia-state/state/card/fp/resource-usage/ingress-policer-stat-entries/total
                    leaf total {
                        type yang:counter32;
                        description "The total number of resources supported on this FP.";
                    }

                    ///nokia-state/state/card/fp/resource-usage/ingress-policer-stat-entries/allocated
                    leaf allocated {
                        type yang:counter32;
                        description "The total number of resources that are currently allocated on this FP.";
                    }

                    ///nokia-state/state/card/fp/resource-usage/ingress-policer-stat-entries/free
                    leaf free {
                        type yang:counter32;
                        description "The total number of resources that are remaining free on this FP.";
                    }

                } // container ingress-policer-stat-entries

                ///nokia-state/state/card/fp/resource-usage/egress-policers
                container egress-policers {
                    description "Enter the egress-policers context";

                    ///nokia-state/state/card/fp/resource-usage/egress-policers/total
                    leaf total {
                        type yang:counter32;
                        description "The total number of resources supported on this FP.";
                    }

                    ///nokia-state/state/card/fp/resource-usage/egress-policers/allocated
                    leaf allocated {
                        type yang:counter32;
                        description "The total number of resources that are currently allocated on this FP.";
                    }

                    ///nokia-state/state/card/fp/resource-usage/egress-policers/free
                    leaf free {
                        type yang:counter32;
                        description "The total number of resources that are remaining free on this FP.";
                    }

                } // container egress-policers

                ///nokia-state/state/card/fp/resource-usage/egress-policer-stat-entries
                container egress-policer-stat-entries {
                    description "Enter the egress-policer-stat-entries context";

                    ///nokia-state/state/card/fp/resource-usage/egress-policer-stat-entries/total
                    leaf total {
                        type yang:counter32;
                        description "The total number of resources supported on this FP.";
                    }

                    ///nokia-state/state/card/fp/resource-usage/egress-policer-stat-entries/allocated
                    leaf allocated {
                        type yang:counter32;
                        description "The total number of resources that are currently allocated on this FP.";
                    }

                    ///nokia-state/state/card/fp/resource-usage/egress-policer-stat-entries/free
                    leaf free {
                        type yang:counter32;
                        description "The total number of resources that are remaining free on this FP.";
                    }

                } // container egress-policer-stat-entries

                ///nokia-state/state/card/fp/resource-usage/qos-ingress-root-arbiters
                container qos-ingress-root-arbiters {
                    description "Enter the qos-ingress-root-arbiters context";

                    ///nokia-state/state/card/fp/resource-usage/qos-ingress-root-arbiters/total
                    leaf total {
                        type yang:counter32;
                        description "The total number of resources supported on this FP.";
                    }

                    ///nokia-state/state/card/fp/resource-usage/qos-ingress-root-arbiters/allocated
                    leaf allocated {
                        type yang:counter32;
                        description "The total number of resources that are currently allocated on this FP.";
                    }

                    ///nokia-state/state/card/fp/resource-usage/qos-ingress-root-arbiters/free
                    leaf free {
                        type yang:counter32;
                        description "The total number of resources that are remaining free on this FP.";
                    }

                } // container qos-ingress-root-arbiters

                ///nokia-state/state/card/fp/resource-usage/qos-egress-root-arbiters
                container qos-egress-root-arbiters {
                    description "Enter the qos-egress-root-arbiters context";

                    ///nokia-state/state/card/fp/resource-usage/qos-egress-root-arbiters/total
                    leaf total {
                        type yang:counter32;
                        description "The total number of resources supported on this FP.";
                    }

                    ///nokia-state/state/card/fp/resource-usage/qos-egress-root-arbiters/allocated
                    leaf allocated {
                        type yang:counter32;
                        description "The total number of resources that are currently allocated on this FP.";
                    }

                    ///nokia-state/state/card/fp/resource-usage/qos-egress-root-arbiters/free
                    leaf free {
                        type yang:counter32;
                        description "The total number of resources that are remaining free on this FP.";
                    }

                } // container qos-egress-root-arbiters

                ///nokia-state/state/card/fp/resource-usage/egress-qos-bypass
                container egress-qos-bypass {
                    description "Enter the egress-qos-bypass context";

                    ///nokia-state/state/card/fp/resource-usage/egress-qos-bypass/total
                    leaf total {
                        type yang:counter32;
                        description "The total number of resources supported on this FP.";
                    }

                    ///nokia-state/state/card/fp/resource-usage/egress-qos-bypass/allocated
                    leaf allocated {
                        type yang:counter32;
                        description "The total number of resources that are currently allocated on this FP.";
                    }

                    ///nokia-state/state/card/fp/resource-usage/egress-qos-bypass/free
                    leaf free {
                        type yang:counter32;
                        description "The total number of resources that are remaining free on this FP.";
                    }

                } // container egress-qos-bypass

                ///nokia-state/state/card/fp/resource-usage/dynamic-queues
                container dynamic-queues {
                    description "Enter the dynamic-queues context";

                    ///nokia-state/state/card/fp/resource-usage/dynamic-queues/total
                    leaf total {
                        type yang:counter32;
                        description "The total number of resources supported on this FP.";
                    }

                    ///nokia-state/state/card/fp/resource-usage/dynamic-queues/allocated
                    leaf allocated {
                        type yang:counter32;
                        description "The total number of resources that are currently allocated on this FP.";
                    }

                    ///nokia-state/state/card/fp/resource-usage/dynamic-queues/free
                    leaf free {
                        type yang:counter32;
                        description "The total number of resources that are remaining free on this FP.";
                    }

                    ///nokia-state/state/card/fp/resource-usage/dynamic-queues/in-use-by-ingress
                    container in-use-by-ingress {
                        description "Enter the in-use-by-ingress context";

                        ///nokia-state/state/card/fp/resource-usage/dynamic-queues/in-use-by-ingress/allocated
                        leaf allocated {
                            type yang:counter32;
                            description "The total number of resources that are currently allocated on this FP.";
                        }

                    } // container in-use-by-ingress

                    ///nokia-state/state/card/fp/resource-usage/dynamic-queues/in-use-by-egress
                    container in-use-by-egress {
                        description "Enter the in-use-by-egress context";

                        ///nokia-state/state/card/fp/resource-usage/dynamic-queues/in-use-by-egress/allocated
                        leaf allocated {
                            type yang:counter32;
                            description "The total number of resources that are currently allocated on this FP.";
                        }

                    } // container in-use-by-egress

                } // container dynamic-queues

                ///nokia-state/state/card/fp/resource-usage/dynamic-policers
                container dynamic-policers {
                    description "Enter the dynamic-policers context";

                    ///nokia-state/state/card/fp/resource-usage/dynamic-policers/total
                    leaf total {
                        type yang:counter32;
                        description "The total number of resources supported on this FP.";
                    }

                    ///nokia-state/state/card/fp/resource-usage/dynamic-policers/allocated
                    leaf allocated {
                        type yang:counter32;
                        description "The total number of resources that are currently allocated on this FP.";
                    }

                    ///nokia-state/state/card/fp/resource-usage/dynamic-policers/free
                    leaf free {
                        type yang:counter32;
                        description "The total number of resources that are remaining free on this FP.";
                    }

                    ///nokia-state/state/card/fp/resource-usage/dynamic-policers/in-use-by-ingress
                    container in-use-by-ingress {
                        description "Enter the in-use-by-ingress context";

                        ///nokia-state/state/card/fp/resource-usage/dynamic-policers/in-use-by-ingress/allocated
                        leaf allocated {
                            type yang:counter32;
                            description "The total number of resources that are currently allocated on this FP.";
                        }

                    } // container in-use-by-ingress

                    ///nokia-state/state/card/fp/resource-usage/dynamic-policers/in-use-by-egress
                    container in-use-by-egress {
                        description "Enter the in-use-by-egress context";

                        ///nokia-state/state/card/fp/resource-usage/dynamic-policers/in-use-by-egress/allocated
                        leaf allocated {
                            type yang:counter32;
                            description "The total number of resources that are currently allocated on this FP.";
                        }

                    } // container in-use-by-egress

                } // container dynamic-policers

                ///nokia-state/state/card/fp/resource-usage/dynamic-policer-stat-entries
                container dynamic-policer-stat-entries {
                    description "Enter the dynamic-policer-stat-entries context";

                    ///nokia-state/state/card/fp/resource-usage/dynamic-policer-stat-entries/total
                    leaf total {
                        type yang:counter32;
                        description "The total number of resources supported on this FP.";
                    }

                    ///nokia-state/state/card/fp/resource-usage/dynamic-policer-stat-entries/allocated
                    leaf allocated {
                        type yang:counter32;
                        description "The total number of resources that are currently allocated on this FP.";
                    }

                    ///nokia-state/state/card/fp/resource-usage/dynamic-policer-stat-entries/free
                    leaf free {
                        type yang:counter32;
                        description "The total number of resources that are remaining free on this FP.";
                    }

                    ///nokia-state/state/card/fp/resource-usage/dynamic-policer-stat-entries/in-use-by-ingress
                    container in-use-by-ingress {
                        description "Enter the in-use-by-ingress context";

                        ///nokia-state/state/card/fp/resource-usage/dynamic-policer-stat-entries/in-use-by-ingress/allocated
                        leaf allocated {
                            type yang:counter32;
                            description "The total number of resources that are currently allocated on this FP.";
                        }

                    } // container in-use-by-ingress

                    ///nokia-state/state/card/fp/resource-usage/dynamic-policer-stat-entries/in-use-by-egress
                    container in-use-by-egress {
                        description "Enter the in-use-by-egress context";

                        ///nokia-state/state/card/fp/resource-usage/dynamic-policer-stat-entries/in-use-by-egress/allocated
                        leaf allocated {
                            type yang:counter32;
                            description "The total number of resources that are currently allocated on this FP.";
                        }

                    } // container in-use-by-egress

                } // container dynamic-policer-stat-entries

                ///nokia-state/state/card/fp/resource-usage/egress-user-queues
                container egress-user-queues {
                    description "Enter the egress-user-queues context";

                    ///nokia-state/state/card/fp/resource-usage/egress-user-queues/total
                    leaf total {
                        type yang:counter32;
                        description "The total number of resources supported on this FP.";
                    }

                    ///nokia-state/state/card/fp/resource-usage/egress-user-queues/allocated
                    leaf allocated {
                        type yang:counter32;
                        description "The total number of resources that are currently allocated on this FP.";
                    }

                    ///nokia-state/state/card/fp/resource-usage/egress-user-queues/free
                    leaf free {
                        type yang:counter32;
                        description "The total number of resources that are remaining free on this FP.";
                    }

                } // container egress-user-queues

                ///nokia-state/state/card/fp/resource-usage/egress-user-policers
                container egress-user-policers {
                    description "Enter the egress-user-policers context";

                    ///nokia-state/state/card/fp/resource-usage/egress-user-policers/total
                    leaf total {
                        type yang:counter32;
                        description "The total number of resources supported on this FP.";
                    }

                    ///nokia-state/state/card/fp/resource-usage/egress-user-policers/allocated
                    leaf allocated {
                        type yang:counter32;
                        description "The total number of resources that are currently allocated on this FP.";
                    }

                    ///nokia-state/state/card/fp/resource-usage/egress-user-policers/free
                    leaf free {
                        type yang:counter32;
                        description "The total number of resources that are remaining free on this FP.";
                    }

                } // container egress-user-policers

                ///nokia-state/state/card/fp/resource-usage/ingress-ip-acl-qos-entries
                container ingress-ip-acl-qos-entries {
                    status obsolete;
                    description "Enter the ingress-ip-acl-qos-entries context";

                    ///nokia-state/state/card/fp/resource-usage/ingress-ip-acl-qos-entries/total
                    leaf total {
                        status obsolete;
                        type yang:counter32;
                        description "The total number of resources supported on this FP.";
                    }

                    ///nokia-state/state/card/fp/resource-usage/ingress-ip-acl-qos-entries/allocated
                    leaf allocated {
                        status obsolete;
                        type yang:counter32;
                        description "The total number of resources that are currently allocated on this FP.";
                    }

                    ///nokia-state/state/card/fp/resource-usage/ingress-ip-acl-qos-entries/free
                    leaf free {
                        status obsolete;
                        type yang:counter32;
                        description "The total number of resources that are remaining free on this FP.";
                    }

                } // container ingress-ip-acl-qos-entries

                ///nokia-state/state/card/fp/resource-usage/ingress-ip-filter-entries
                container ingress-ip-filter-entries {
                    description "Enter the ingress-ip-filter-entries context";

                    ///nokia-state/state/card/fp/resource-usage/ingress-ip-filter-entries/total
                    leaf total {
                        type yang:counter32;
                        description "The total number of resources supported on this FP.";
                    }

                    ///nokia-state/state/card/fp/resource-usage/ingress-ip-filter-entries/allocated
                    leaf allocated {
                        type yang:counter32;
                        description "The total number of resources that are currently allocated on this FP.";
                    }

                    ///nokia-state/state/card/fp/resource-usage/ingress-ip-filter-entries/free
                    leaf free {
                        type yang:counter32;
                        description "The total number of resources that are remaining free on this FP.";
                    }

                } // container ingress-ip-filter-entries

                ///nokia-state/state/card/fp/resource-usage/ingress-ip-qos-entries
                container ingress-ip-qos-entries {
                    description "Enter the ingress-ip-qos-entries context";

                    ///nokia-state/state/card/fp/resource-usage/ingress-ip-qos-entries/total
                    leaf total {
                        type yang:counter32;
                        description "The total number of resources supported on this FP.";
                    }

                    ///nokia-state/state/card/fp/resource-usage/ingress-ip-qos-entries/allocated
                    leaf allocated {
                        type yang:counter32;
                        description "The total number of resources that are currently allocated on this FP.";
                    }

                    ///nokia-state/state/card/fp/resource-usage/ingress-ip-qos-entries/free
                    leaf free {
                        type yang:counter32;
                        description "The total number of resources that are remaining free on this FP.";
                    }

                } // container ingress-ip-qos-entries

                ///nokia-state/state/card/fp/resource-usage/ingress-ipv6-filter-entries
                container ingress-ipv6-filter-entries {
                    description "Enter the ingress-ipv6-filter-entries context";

                    ///nokia-state/state/card/fp/resource-usage/ingress-ipv6-filter-entries/total
                    leaf total {
                        type yang:counter32;
                        description "The total number of resources supported on this FP.";
                    }

                    ///nokia-state/state/card/fp/resource-usage/ingress-ipv6-filter-entries/allocated
                    leaf allocated {
                        type yang:counter32;
                        description "The total number of resources that are currently allocated on this FP.";
                    }

                    ///nokia-state/state/card/fp/resource-usage/ingress-ipv6-filter-entries/free
                    leaf free {
                        type yang:counter32;
                        description "The total number of resources that are remaining free on this FP.";
                    }

                } // container ingress-ipv6-filter-entries

                ///nokia-state/state/card/fp/resource-usage/ingress-ipv6-qos-entries
                container ingress-ipv6-qos-entries {
                    description "Enter the ingress-ipv6-qos-entries context";

                    ///nokia-state/state/card/fp/resource-usage/ingress-ipv6-qos-entries/total
                    leaf total {
                        type yang:counter32;
                        description "The total number of resources supported on this FP.";
                    }

                    ///nokia-state/state/card/fp/resource-usage/ingress-ipv6-qos-entries/allocated
                    leaf allocated {
                        type yang:counter32;
                        description "The total number of resources that are currently allocated on this FP.";
                    }

                    ///nokia-state/state/card/fp/resource-usage/ingress-ipv6-qos-entries/free
                    leaf free {
                        type yang:counter32;
                        description "The total number of resources that are remaining free on this FP.";
                    }

                } // container ingress-ipv6-qos-entries

                ///nokia-state/state/card/fp/resource-usage/egress-ip-acl-qos-entries
                container egress-ip-acl-qos-entries {
                    status obsolete;
                    description "Enter the egress-ip-acl-qos-entries context";

                    ///nokia-state/state/card/fp/resource-usage/egress-ip-acl-qos-entries/total
                    leaf total {
                        status obsolete;
                        type yang:counter32;
                        description "The total number of resources supported on this FP.";
                    }

                    ///nokia-state/state/card/fp/resource-usage/egress-ip-acl-qos-entries/allocated
                    leaf allocated {
                        status obsolete;
                        type yang:counter32;
                        description "The total number of resources that are currently allocated on this FP.";
                    }

                    ///nokia-state/state/card/fp/resource-usage/egress-ip-acl-qos-entries/free
                    leaf free {
                        status obsolete;
                        type yang:counter32;
                        description "The total number of resources that are remaining free on this FP.";
                    }

                } // container egress-ip-acl-qos-entries

                ///nokia-state/state/card/fp/resource-usage/egress-ip-filter-entries
                container egress-ip-filter-entries {
                    description "Enter the egress-ip-filter-entries context";

                    ///nokia-state/state/card/fp/resource-usage/egress-ip-filter-entries/total
                    leaf total {
                        type yang:counter32;
                        description "The total number of resources supported on this FP.";
                    }

                    ///nokia-state/state/card/fp/resource-usage/egress-ip-filter-entries/allocated
                    leaf allocated {
                        type yang:counter32;
                        description "The total number of resources that are currently allocated on this FP.";
                    }

                    ///nokia-state/state/card/fp/resource-usage/egress-ip-filter-entries/free
                    leaf free {
                        type yang:counter32;
                        description "The total number of resources that are remaining free on this FP.";
                    }

                } // container egress-ip-filter-entries

                ///nokia-state/state/card/fp/resource-usage/egress-ip-qos-entries
                container egress-ip-qos-entries {
                    description "Enter the egress-ip-qos-entries context";

                    ///nokia-state/state/card/fp/resource-usage/egress-ip-qos-entries/total
                    leaf total {
                        type yang:counter32;
                        description "The total number of resources supported on this FP.";
                    }

                    ///nokia-state/state/card/fp/resource-usage/egress-ip-qos-entries/allocated
                    leaf allocated {
                        type yang:counter32;
                        description "The total number of resources that are currently allocated on this FP.";
                    }

                    ///nokia-state/state/card/fp/resource-usage/egress-ip-qos-entries/free
                    leaf free {
                        type yang:counter32;
                        description "The total number of resources that are remaining free on this FP.";
                    }

                } // container egress-ip-qos-entries

                ///nokia-state/state/card/fp/resource-usage/egress-ipv6-filter-entries
                container egress-ipv6-filter-entries {
                    description "Enter the egress-ipv6-filter-entries context";

                    ///nokia-state/state/card/fp/resource-usage/egress-ipv6-filter-entries/total
                    leaf total {
                        type yang:counter32;
                        description "The total number of resources supported on this FP.";
                    }

                    ///nokia-state/state/card/fp/resource-usage/egress-ipv6-filter-entries/allocated
                    leaf allocated {
                        type yang:counter32;
                        description "The total number of resources that are currently allocated on this FP.";
                    }

                    ///nokia-state/state/card/fp/resource-usage/egress-ipv6-filter-entries/free
                    leaf free {
                        type yang:counter32;
                        description "The total number of resources that are remaining free on this FP.";
                    }

                } // container egress-ipv6-filter-entries

                ///nokia-state/state/card/fp/resource-usage/egress-ipv6-qos-entries
                container egress-ipv6-qos-entries {
                    description "Enter the egress-ipv6-qos-entries context";

                    ///nokia-state/state/card/fp/resource-usage/egress-ipv6-qos-entries/total
                    leaf total {
                        type yang:counter32;
                        description "The total number of resources supported on this FP.";
                    }

                    ///nokia-state/state/card/fp/resource-usage/egress-ipv6-qos-entries/allocated
                    leaf allocated {
                        type yang:counter32;
                        description "The total number of resources that are currently allocated on this FP.";
                    }

                    ///nokia-state/state/card/fp/resource-usage/egress-ipv6-qos-entries/free
                    leaf free {
                        type yang:counter32;
                        description "The total number of resources that are remaining free on this FP.";
                    }

                } // container egress-ipv6-qos-entries

                ///nokia-state/state/card/fp/resource-usage/ingress-ip-filter-policies
                container ingress-ip-filter-policies {
                    description "Enter the ingress-ip-filter-policies context";

                    ///nokia-state/state/card/fp/resource-usage/ingress-ip-filter-policies/total
                    leaf total {
                        type yang:counter32;
                        description "The total number of resources supported on this FP.";
                    }

                    ///nokia-state/state/card/fp/resource-usage/ingress-ip-filter-policies/allocated
                    leaf allocated {
                        type yang:counter32;
                        description "The total number of resources that are currently allocated on this FP.";
                    }

                    ///nokia-state/state/card/fp/resource-usage/ingress-ip-filter-policies/free
                    leaf free {
                        type yang:counter32;
                        description "The total number of resources that are remaining free on this FP.";
                    }

                } // container ingress-ip-filter-policies

                ///nokia-state/state/card/fp/resource-usage/ingress-ipv6-filter-policies
                container ingress-ipv6-filter-policies {
                    description "Enter the ingress-ipv6-filter-policies context";

                    ///nokia-state/state/card/fp/resource-usage/ingress-ipv6-filter-policies/total
                    leaf total {
                        type yang:counter32;
                        description "The total number of resources supported on this FP.";
                    }

                    ///nokia-state/state/card/fp/resource-usage/ingress-ipv6-filter-policies/allocated
                    leaf allocated {
                        type yang:counter32;
                        description "The total number of resources that are currently allocated on this FP.";
                    }

                    ///nokia-state/state/card/fp/resource-usage/ingress-ipv6-filter-policies/free
                    leaf free {
                        type yang:counter32;
                        description "The total number of resources that are remaining free on this FP.";
                    }

                } // container ingress-ipv6-filter-policies

                ///nokia-state/state/card/fp/resource-usage/egress-ip-filter-policies
                container egress-ip-filter-policies {
                    description "Enter the egress-ip-filter-policies context";

                    ///nokia-state/state/card/fp/resource-usage/egress-ip-filter-policies/total
                    leaf total {
                        type yang:counter32;
                        description "The total number of resources supported on this FP.";
                    }

                    ///nokia-state/state/card/fp/resource-usage/egress-ip-filter-policies/allocated
                    leaf allocated {
                        type yang:counter32;
                        description "The total number of resources that are currently allocated on this FP.";
                    }

                    ///nokia-state/state/card/fp/resource-usage/egress-ip-filter-policies/free
                    leaf free {
                        type yang:counter32;
                        description "The total number of resources that are remaining free on this FP.";
                    }

                } // container egress-ip-filter-policies

                ///nokia-state/state/card/fp/resource-usage/egress-ipv6-filter-policies
                container egress-ipv6-filter-policies {
                    description "Enter the egress-ipv6-filter-policies context";

                    ///nokia-state/state/card/fp/resource-usage/egress-ipv6-filter-policies/total
                    leaf total {
                        type yang:counter32;
                        description "The total number of resources supported on this FP.";
                    }

                    ///nokia-state/state/card/fp/resource-usage/egress-ipv6-filter-policies/allocated
                    leaf allocated {
                        type yang:counter32;
                        description "The total number of resources that are currently allocated on this FP.";
                    }

                    ///nokia-state/state/card/fp/resource-usage/egress-ipv6-filter-policies/free
                    leaf free {
                        type yang:counter32;
                        description "The total number of resources that are remaining free on this FP.";
                    }

                } // container egress-ipv6-filter-policies

                ///nokia-state/state/card/fp/resource-usage/sap-ingqgrp-redirlst-entries
                container sap-ingqgrp-redirlst-entries {
                    description "Enter the sap-ingqgrp-redirlst-entries context";

                    ///nokia-state/state/card/fp/resource-usage/sap-ingqgrp-redirlst-entries/total
                    leaf total {
                        type yang:counter32;
                        description "The total number of resources supported on this FP.";
                    }

                    ///nokia-state/state/card/fp/resource-usage/sap-ingqgrp-redirlst-entries/allocated
                    leaf allocated {
                        type yang:counter32;
                        description "The total number of resources that are currently allocated on this FP.";
                    }

                    ///nokia-state/state/card/fp/resource-usage/sap-ingqgrp-redirlst-entries/free
                    leaf free {
                        type yang:counter32;
                        description "The total number of resources that are remaining free on this FP.";
                    }

                } // container sap-ingqgrp-redirlst-entries

                ///nokia-state/state/card/fp/resource-usage/dynamic-service-entries
                container dynamic-service-entries {
                    description "Enter the dynamic-service-entries context";

                    ///nokia-state/state/card/fp/resource-usage/dynamic-service-entries/total
                    leaf total {
                        type yang:counter32;
                        description "The total number of resources supported on this FP.";
                    }

                    ///nokia-state/state/card/fp/resource-usage/dynamic-service-entries/allocated
                    leaf allocated {
                        type yang:counter32;
                        description "The total number of resources that are currently allocated on this FP.";
                    }

                    ///nokia-state/state/card/fp/resource-usage/dynamic-service-entries/free
                    leaf free {
                        type yang:counter32;
                        description "The total number of resources that are remaining free on this FP.";
                    }

                    ///nokia-state/state/card/fp/resource-usage/dynamic-service-entries/encap-group-members
                    container encap-group-members {
                        description "Enter the encap-group-members context";

                        ///nokia-state/state/card/fp/resource-usage/dynamic-service-entries/encap-group-members/total
                        leaf total {
                            type yang:counter32;
                            description "The total number of resources supported on this FP.";
                        }

                        ///nokia-state/state/card/fp/resource-usage/dynamic-service-entries/encap-group-members/allocated
                        leaf allocated {
                            type yang:counter32;
                            description "The total number of resources that are currently allocated on this FP.";
                        }

                        ///nokia-state/state/card/fp/resource-usage/dynamic-service-entries/encap-group-members/free
                        leaf free {
                            type yang:counter32;
                            description "The total number of resources that are remaining free on this FP.";
                        }

                    } // container encap-group-members

                    ///nokia-state/state/card/fp/resource-usage/dynamic-service-entries/egress-network-queue-group-mappings
                    container egress-network-queue-group-mappings {
                        description "Enter the egress-network-queue-group-mappings context";

                        ///nokia-state/state/card/fp/resource-usage/dynamic-service-entries/egress-network-queue-group-mappings/total
                        leaf total {
                            type yang:counter32;
                            description "The total number of resources supported on this FP.";
                        }

                        ///nokia-state/state/card/fp/resource-usage/dynamic-service-entries/egress-network-queue-group-mappings/allocated
                        leaf allocated {
                            type yang:counter32;
                            description "The total number of resources that are currently allocated on this FP.";
                        }

                        ///nokia-state/state/card/fp/resource-usage/dynamic-service-entries/egress-network-queue-group-mappings/free
                        leaf free {
                            type yang:counter32;
                            description "The total number of resources that are remaining free on this FP.";
                        }

                    } // container egress-network-queue-group-mappings

                    ///nokia-state/state/card/fp/resource-usage/dynamic-service-entries/sapinst-egrqgrp-redirlst-entries
                    container sapinst-egrqgrp-redirlst-entries {
                        description "Enter the sapinst-egrqgrp-redirlst-entries context";

                        ///nokia-state/state/card/fp/resource-usage/dynamic-service-entries/sapinst-egrqgrp-redirlst-entries/total
                        leaf total {
                            type yang:counter32;
                            description "The total number of resources supported on this FP.";
                        }

                        ///nokia-state/state/card/fp/resource-usage/dynamic-service-entries/sapinst-egrqgrp-redirlst-entries/allocated
                        leaf allocated {
                            type yang:counter32;
                            description "The total number of resources that are currently allocated on this FP.";
                        }

                        ///nokia-state/state/card/fp/resource-usage/dynamic-service-entries/sapinst-egrqgrp-redirlst-entries/free
                        leaf free {
                            type yang:counter32;
                            description "The total number of resources that are remaining free on this FP.";
                        }

                    } // container sapinst-egrqgrp-redirlst-entries

                } // container dynamic-service-entries

                ///nokia-state/state/card/fp/resource-usage/dynamic-wred-pools
                container dynamic-wred-pools {
                    description "Enter the dynamic-wred-pools context";

                    ///nokia-state/state/card/fp/resource-usage/dynamic-wred-pools/total
                    leaf total {
                        type yang:counter32;
                        description "The total number of resources supported on this FP.";
                    }

                    ///nokia-state/state/card/fp/resource-usage/dynamic-wred-pools/allocated
                    leaf allocated {
                        type yang:counter32;
                        description "The total number of resources that are currently allocated on this FP.";
                    }

                    ///nokia-state/state/card/fp/resource-usage/dynamic-wred-pools/free
                    leaf free {
                        type yang:counter32;
                        description "The total number of resources that are remaining free on this FP.";
                    }

                } // container dynamic-wred-pools

                ///nokia-state/state/card/fp/resource-usage/egress-hs-turbo-queue-group
                container egress-hs-turbo-queue-group {
                    description "Enter the egress-hs-turbo-queue-group context";

                    ///nokia-state/state/card/fp/resource-usage/egress-hs-turbo-queue-group/total
                    leaf total {
                        type yang:counter32;
                        description "The total number of resources supported on this FP.";
                    }

                    ///nokia-state/state/card/fp/resource-usage/egress-hs-turbo-queue-group/allocated
                    leaf allocated {
                        type yang:counter32;
                        description "The total number of resources that are currently allocated on this FP.";
                    }

                    ///nokia-state/state/card/fp/resource-usage/egress-hs-turbo-queue-group/free
                    leaf free {
                        type yang:counter32;
                        description "The total number of resources that are remaining free on this FP.";
                    }

                } // container egress-hs-turbo-queue-group

                ///nokia-state/state/card/fp/resource-usage/egress-hs-queue-group
                container egress-hs-queue-group {
                    description "Enter the egress-hs-queue-group context";

                    ///nokia-state/state/card/fp/resource-usage/egress-hs-queue-group/total
                    leaf total {
                        type yang:counter32;
                        description "The total number of resources supported on this FP.";
                    }

                    ///nokia-state/state/card/fp/resource-usage/egress-hs-queue-group/allocated
                    leaf allocated {
                        type yang:counter32;
                        description "The total number of resources that are currently allocated on this FP.";
                    }

                    ///nokia-state/state/card/fp/resource-usage/egress-hs-queue-group/free
                    leaf free {
                        type yang:counter32;
                        description "The total number of resources that are remaining free on this FP.";
                    }

                } // container egress-hs-queue-group

                ///nokia-state/state/card/fp/resource-usage/hs-primary-shapers
                container hs-primary-shapers {
                    description "Enter the hs-primary-shapers context";

                    ///nokia-state/state/card/fp/resource-usage/hs-primary-shapers/total
                    leaf total {
                        type yang:counter32;
                        description "The total number of resources supported on this FP.";
                    }

                    ///nokia-state/state/card/fp/resource-usage/hs-primary-shapers/allocated
                    leaf allocated {
                        type yang:counter32;
                        description "The total number of resources that are currently allocated on this FP.";
                    }

                    ///nokia-state/state/card/fp/resource-usage/hs-primary-shapers/free
                    leaf free {
                        type yang:counter32;
                        description "The total number of resources that are remaining free on this FP.";
                    }

                    ///nokia-state/state/card/fp/resource-usage/hs-primary-shapers/hs-explicit-primary-shapers
                    container hs-explicit-primary-shapers {
                        description "Enter the hs-explicit-primary-shapers context";

                        ///nokia-state/state/card/fp/resource-usage/hs-primary-shapers/hs-explicit-primary-shapers/allocated
                        leaf allocated {
                            type yang:counter32;
                            description "The total number of resources that are currently allocated on this FP";
                        }

                    } // container hs-explicit-primary-shapers

                    ///nokia-state/state/card/fp/resource-usage/hs-primary-shapers/hs-managed-primary-shapers
                    container hs-managed-primary-shapers {
                        description "Enter the hs-managed-primary-shapers context";

                        ///nokia-state/state/card/fp/resource-usage/hs-primary-shapers/hs-managed-primary-shapers/allocated
                        leaf allocated {
                            type yang:counter32;
                            description "The total number of resources that are currently allocated on this FP";
                        }

                    } // container hs-managed-primary-shapers

                } // container hs-primary-shapers

                ///nokia-state/state/card/fp/resource-usage/hs-secondary-shapers
                container hs-secondary-shapers {
                    description "Enter the hs-secondary-shapers context";

                    ///nokia-state/state/card/fp/resource-usage/hs-secondary-shapers/total
                    leaf total {
                        type yang:counter32;
                        description "The total number of resources supported on this FP.";
                    }

                    ///nokia-state/state/card/fp/resource-usage/hs-secondary-shapers/allocated
                    leaf allocated {
                        type yang:counter32;
                        description "The total number of resources that are currently allocated on this FP.";
                    }

                    ///nokia-state/state/card/fp/resource-usage/hs-secondary-shapers/free
                    leaf free {
                        type yang:counter32;
                        description "The total number of resources that are remaining free on this FP.";
                    }

                } // container hs-secondary-shapers

                ///nokia-state/state/card/fp/resource-usage/fast-depth-monitored-queues
                container fast-depth-monitored-queues {
                    description "Enter the fast-depth-monitored-queues context";

                    ///nokia-state/state/card/fp/resource-usage/fast-depth-monitored-queues/total
                    leaf total {
                        type yang:counter32;
                        description "The total number of resources supported on this FP.";
                    }

                    ///nokia-state/state/card/fp/resource-usage/fast-depth-monitored-queues/allocated
                    leaf allocated {
                        type yang:counter32;
                        description "The total number of resources that are currently allocated on this FP.";
                    }

                    ///nokia-state/state/card/fp/resource-usage/fast-depth-monitored-queues/free
                    leaf free {
                        type yang:counter32;
                        description "The total number of resources that are remaining free on this FP.";
                    }

                } // container fast-depth-monitored-queues

                ///nokia-state/state/card/fp/resource-usage/assigned-non-shaper-queues
                container assigned-non-shaper-queues {
                    description "Enter the assigned-non-shaper-queues context";

                    ///nokia-state/state/card/fp/resource-usage/assigned-non-shaper-queues/total
                    leaf total {
                        type yang:counter32;
                        description "The total number of resources supported on this FP.";
                    }

                    ///nokia-state/state/card/fp/resource-usage/assigned-non-shaper-queues/allocated
                    leaf allocated {
                        type yang:counter32;
                        description "The total number of resources that are currently allocated on this FP.";
                    }

                    ///nokia-state/state/card/fp/resource-usage/assigned-non-shaper-queues/free
                    leaf free {
                        type yang:counter32;
                        description "The total number of resources that are remaining free on this FP.";
                    }

                } // container assigned-non-shaper-queues








                ///nokia-state/state/card/fp/resource-usage/hw-aggregate-shaper-qset-size8
                container hw-aggregate-shaper-qset-size8 {
                    description "Enter the hw-aggregate-shaper-qset-size8 context";

                    ///nokia-state/state/card/fp/resource-usage/hw-aggregate-shaper-qset-size8/total
                    leaf total {
                        type yang:counter32;
                        description "The total number of resources supported on this FP.";
                    }

                    ///nokia-state/state/card/fp/resource-usage/hw-aggregate-shaper-qset-size8/allocated
                    leaf allocated {
                        type yang:counter32;
                        description "The total number of resources that are currently allocated on this FP.";
                    }

                    ///nokia-state/state/card/fp/resource-usage/hw-aggregate-shaper-qset-size8/free
                    leaf free {
                        type yang:counter32;
                        description "The total number of resources that are remaining free on this FP.";
                    }

                } // container hw-aggregate-shaper-qset-size8

                ///nokia-state/state/card/fp/resource-usage/hw-aggregate-shapers
                container hw-aggregate-shapers {
                    description "Enter the hw-aggregate-shapers context";

                    ///nokia-state/state/card/fp/resource-usage/hw-aggregate-shapers/total
                    leaf total {
                        type yang:counter32;
                        description "The total number of resources supported on this FP.";
                    }

                    ///nokia-state/state/card/fp/resource-usage/hw-aggregate-shapers/allocated
                    leaf allocated {
                        type yang:counter32;
                        description "The total number of resources that are currently allocated on this FP.";
                    }

                    ///nokia-state/state/card/fp/resource-usage/hw-aggregate-shapers/free
                    leaf free {
                        type yang:counter32;
                        description "The total number of resources that are remaining free on this FP.";
                    }

                } // container hw-aggregate-shapers

                ///nokia-state/state/card/fp/resource-usage/hw-aggregate-shaper-schedulers
                container hw-aggregate-shaper-schedulers {
                    description "Enter the hw-aggregate-shaper-schedulers context";

                    ///nokia-state/state/card/fp/resource-usage/hw-aggregate-shaper-schedulers/total
                    leaf total {
                        type yang:counter32;
                        description "The total number of resources supported on this FP.";
                    }

                    ///nokia-state/state/card/fp/resource-usage/hw-aggregate-shaper-schedulers/allocated
                    leaf allocated {
                        type yang:counter32;
                        description "The total number of resources that are currently allocated on this FP.";
                    }

                    ///nokia-state/state/card/fp/resource-usage/hw-aggregate-shaper-schedulers/free
                    leaf free {
                        type yang:counter32;
                        description "The total number of resources that are remaining free on this FP.";
                    }

                } // container hw-aggregate-shaper-schedulers

                ///nokia-state/state/card/fp/resource-usage/hw-aggregate-shaper-qset-size
                container hw-aggregate-shaper-qset-size {
                    description "Enter the hw-aggregate-shaper-qset-size context";

                    ///nokia-state/state/card/fp/resource-usage/hw-aggregate-shaper-qset-size/total
                    leaf total {
                        type yang:counter32;
                        description "The total number of resources supported on this FP.";
                    }

                    ///nokia-state/state/card/fp/resource-usage/hw-aggregate-shaper-qset-size/allocated
                    leaf allocated {
                        type yang:counter32;
                        description "The total number of resources that are currently allocated on this FP.";
                    }

                    ///nokia-state/state/card/fp/resource-usage/hw-aggregate-shaper-qset-size/free
                    leaf free {
                        type yang:counter32;
                        description "The total number of resources that are remaining free on this FP.";
                    }

                } // container hw-aggregate-shaper-qset-size

                ///nokia-state/state/card/fp/resource-usage/hw-aggregate-shaper-def-qset-size
                container hw-aggregate-shaper-def-qset-size {
                    description "Enter the hw-aggregate-shaper-def-qset-size context";

                    ///nokia-state/state/card/fp/resource-usage/hw-aggregate-shaper-def-qset-size/saps
                    leaf saps {
                        type uint32;
                        description
                            "The default queue set size for this sap on this FP when
                             hardware aggregate shaper is enabled";
                    }

                    ///nokia-state/state/card/fp/resource-usage/hw-aggregate-shaper-def-qset-size/subscribers
                    leaf subscribers {
                        type uint32;
                        description
                            "The default queue set size for this subscribers on this FP when
                             hardware aggregate shaper is enabled";
                    }

                    ///nokia-state/state/card/fp/resource-usage/hw-aggregate-shaper-def-qset-size/queue-groups
                    leaf queue-groups {
                        type uint32;
                        description
                            "The default queue set size for this queue groups on this FP when
                             hardware aggregate shaper is enabled";
                    }

                } // container hw-aggregate-shaper-def-qset-size

                ///nokia-state/state/card/fp/resource-usage/fdb
                container fdb {
                    description "Enter the fdb context";

                    ///nokia-state/state/card/fp/resource-usage/fdb/total
                    leaf total {
                        type yang:counter32;
                        description "The total number of resources supported on this FP.";
                    }

                    ///nokia-state/state/card/fp/resource-usage/fdb/allocated
                    leaf allocated {
                        type yang:counter32;
                        description "The total number of resources that are currently allocated on this FP.";
                    }

                    ///nokia-state/state/card/fp/resource-usage/fdb/free
                    leaf free {
                        type yang:counter32;
                        description "The total number of resources that are remaining free on this FP.";
                    }

                } // container fdb

                ///nokia-state/state/card/fp/resource-usage/port-forwarding-ids
                container port-forwarding-ids {
                    description "Enter the port-forwarding-ids context";

                    ///nokia-state/state/card/fp/resource-usage/port-forwarding-ids/total
                    leaf total {
                        type yang:counter32;
                        description "The total number of resources supported on this FP.";
                    }

                    ///nokia-state/state/card/fp/resource-usage/port-forwarding-ids/allocated
                    leaf allocated {
                        type yang:counter32;
                        description "The total number of resources that are currently allocated on this FP.";
                    }

                    ///nokia-state/state/card/fp/resource-usage/port-forwarding-ids/free
                    leaf free {
                        type yang:counter32;
                        description "The total number of resources that are remaining free on this FP.";
                    }

                } // container port-forwarding-ids

                ///nokia-state/state/card/fp/resource-usage/ixr
                container ixr {
                    description "Enter the ixr context";

                    ///nokia-state/state/card/fp/resource-usage/ixr/egress-global-lif-map
                    container egress-global-lif-map {
                        description "Enter the egress-global-lif-map context";

                        ///nokia-state/state/card/fp/resource-usage/ixr/egress-global-lif-map/total
                        leaf total {
                            type yang:counter32;
                            description "The total number of resources.";
                        }

                        ///nokia-state/state/card/fp/resource-usage/ixr/egress-global-lif-map/allocated
                        leaf allocated {
                            type yang:counter32;
                            description "The number of resources that are currently allocated.";
                        }

                        ///nokia-state/state/card/fp/resource-usage/ixr/egress-global-lif-map/free
                        leaf free {
                            type yang:counter32;
                            description "The number of free resources that are currently available.";
                        }

                    } // container egress-global-lif-map

                    ///nokia-state/state/card/fp/resource-usage/ixr/ingress-decapsulation
                    container ingress-decapsulation {
                        description "Enter the ingress-decapsulation context";

                        ///nokia-state/state/card/fp/resource-usage/ixr/ingress-decapsulation/ingress-termination-a
                        container ingress-termination-a {
                            description "Enter the ingress-termination-a context";

                            ///nokia-state/state/card/fp/resource-usage/ixr/ingress-decapsulation/ingress-termination-a/total
                            leaf total {
                                type yang:counter32;
                                description "The total number of resources.";
                            }

                            ///nokia-state/state/card/fp/resource-usage/ixr/ingress-decapsulation/ingress-termination-a/allocated
                            leaf allocated {
                                type yang:counter32;
                                description "The number of resources that are currently allocated.";
                            }

                            ///nokia-state/state/card/fp/resource-usage/ixr/ingress-decapsulation/ingress-termination-a/free
                            leaf free {
                                type yang:counter32;
                                description "The number of free resources that are currently available.";
                            }

                        } // container ingress-termination-a

                        ///nokia-state/state/card/fp/resource-usage/ixr/ingress-decapsulation/ingress-termination-b
                        container ingress-termination-b {
                            description "Enter the ingress-termination-b context";

                            ///nokia-state/state/card/fp/resource-usage/ixr/ingress-decapsulation/ingress-termination-b/total
                            leaf total {
                                type yang:counter32;
                                description "The total number of resources.";
                            }

                            ///nokia-state/state/card/fp/resource-usage/ixr/ingress-decapsulation/ingress-termination-b/allocated
                            leaf allocated {
                                type yang:counter32;
                                description "The number of resources that are currently allocated.";
                            }

                            ///nokia-state/state/card/fp/resource-usage/ixr/ingress-decapsulation/ingress-termination-b/free
                            leaf free {
                                type yang:counter32;
                                description "The number of free resources that are currently available.";
                            }

                        } // container ingress-termination-b

                        ///nokia-state/state/card/fp/resource-usage/ixr/ingress-decapsulation/ingress-endpoint-1
                        container ingress-endpoint-1 {
                            description "Enter the ingress-endpoint-1 context";

                            ///nokia-state/state/card/fp/resource-usage/ixr/ingress-decapsulation/ingress-endpoint-1/total
                            leaf total {
                                type yang:counter32;
                                description "The total number of resources.";
                            }

                            ///nokia-state/state/card/fp/resource-usage/ixr/ingress-decapsulation/ingress-endpoint-1/allocated
                            leaf allocated {
                                type yang:counter32;
                                description "The number of resources that are currently allocated.";
                            }

                            ///nokia-state/state/card/fp/resource-usage/ixr/ingress-decapsulation/ingress-endpoint-1/free
                            leaf free {
                                type yang:counter32;
                                description "The number of free resources that are currently available.";
                            }

                        } // container ingress-endpoint-1

                        ///nokia-state/state/card/fp/resource-usage/ixr/ingress-decapsulation/ingress-endpoint-2
                        container ingress-endpoint-2 {
                            description "Enter the ingress-endpoint-2 context";

                            ///nokia-state/state/card/fp/resource-usage/ixr/ingress-decapsulation/ingress-endpoint-2/total
                            leaf total {
                                type yang:counter32;
                                description "The total number of resources.";
                            }

                            ///nokia-state/state/card/fp/resource-usage/ixr/ingress-decapsulation/ingress-endpoint-2/allocated
                            leaf allocated {
                                type yang:counter32;
                                description "The number of resources that are currently allocated.";
                            }

                            ///nokia-state/state/card/fp/resource-usage/ixr/ingress-decapsulation/ingress-endpoint-2/free
                            leaf free {
                                type yang:counter32;
                                description "The number of free resources that are currently available.";
                            }

                        } // container ingress-endpoint-2

                        ///nokia-state/state/card/fp/resource-usage/ixr/ingress-decapsulation/ingress-endpoint-3
                        container ingress-endpoint-3 {
                            description "Enter the ingress-endpoint-3 context";

                            ///nokia-state/state/card/fp/resource-usage/ixr/ingress-decapsulation/ingress-endpoint-3/total
                            leaf total {
                                type yang:counter32;
                                description "The total number of resources.";
                            }

                            ///nokia-state/state/card/fp/resource-usage/ixr/ingress-decapsulation/ingress-endpoint-3/allocated
                            leaf allocated {
                                type yang:counter32;
                                description "The number of resources that are currently allocated.";
                            }

                            ///nokia-state/state/card/fp/resource-usage/ixr/ingress-decapsulation/ingress-endpoint-3/free
                            leaf free {
                                type yang:counter32;
                                description "The number of free resources that are currently available.";
                            }

                        } // container ingress-endpoint-3

                    } // container ingress-decapsulation

                    ///nokia-state/state/card/fp/resource-usage/ixr/egress-encapsulation
                    container egress-encapsulation {
                        description "Enter the egress-encapsulation context";

                        ///nokia-state/state/card/fp/resource-usage/ixr/egress-encapsulation/banks
                        container banks {
                            description "Enter the banks context";

                            ///nokia-state/state/card/fp/resource-usage/ixr/egress-encapsulation/banks/total
                            leaf total {
                                type yang:counter32;
                                description "The total number of resources.";
                            }

                            ///nokia-state/state/card/fp/resource-usage/ixr/egress-encapsulation/banks/allocated
                            leaf allocated {
                                type yang:counter32;
                                description "The number of resources that are currently allocated.";
                            }

                            ///nokia-state/state/card/fp/resource-usage/ixr/egress-encapsulation/banks/free
                            leaf free {
                                type yang:counter32;
                                description "The number of free resources that are currently available.";
                            }

                            ///nokia-state/state/card/fp/resource-usage/ixr/egress-encapsulation/banks/routed
                            container routed {
                                description "Enter the routed context";

                                ///nokia-state/state/card/fp/resource-usage/ixr/egress-encapsulation/banks/routed/allocated
                                leaf allocated {
                                    type yang:counter32;
                                    description "The number of resources that are currently allocated.";
                                }

                            } // container routed

                            ///nokia-state/state/card/fp/resource-usage/ixr/egress-encapsulation/banks/tdm
                            container tdm {
                                description "Enter the tdm context";

                                ///nokia-state/state/card/fp/resource-usage/ixr/egress-encapsulation/banks/tdm/allocated
                                leaf allocated {
                                    type yang:counter32;
                                    description "The number of resources that are currently allocated.";
                                }

                            } // container tdm

                            ///nokia-state/state/card/fp/resource-usage/ixr/egress-encapsulation/banks/port-vlan-translation
                            container port-vlan-translation {
                                description "Enter the port-vlan-translation context";

                                ///nokia-state/state/card/fp/resource-usage/ixr/egress-encapsulation/banks/port-vlan-translation/allocated
                                leaf allocated {
                                    type yang:counter32;
                                    description "The number of resources that are currently allocated.";
                                }

                            } // container port-vlan-translation

                            ///nokia-state/state/card/fp/resource-usage/ixr/egress-encapsulation/banks/arp
                            container arp {
                                description "Enter the arp context";

                                ///nokia-state/state/card/fp/resource-usage/ixr/egress-encapsulation/banks/arp/allocated
                                leaf allocated {
                                    type yang:counter32;
                                    description "The number of resources that are currently allocated.";
                                }

                            } // container arp

                            ///nokia-state/state/card/fp/resource-usage/ixr/egress-encapsulation/banks/label-push
                            container label-push {
                                description "Enter the label-push context";

                                ///nokia-state/state/card/fp/resource-usage/ixr/egress-encapsulation/banks/label-push/allocated
                                leaf allocated {
                                    type yang:counter32;
                                    description "The number of resources that are currently allocated.";
                                }

                            } // container label-push

                            ///nokia-state/state/card/fp/resource-usage/ixr/egress-encapsulation/banks/label-swap-push
                            container label-swap-push {
                                description "Enter the label-swap-push context";

                                ///nokia-state/state/card/fp/resource-usage/ixr/egress-encapsulation/banks/label-swap-push/allocated
                                leaf allocated {
                                    type yang:counter32;
                                    description "The number of resources that are currently allocated.";
                                }

                            } // container label-swap-push

                            ///nokia-state/state/card/fp/resource-usage/ixr/egress-encapsulation/banks/port-vlan-translation-ext
                            container port-vlan-translation-ext {
                                description "Enter the port-vlan-translation-ext context";

                                ///nokia-state/state/card/fp/resource-usage/ixr/egress-encapsulation/banks/port-vlan-translation-ext/allocated
                                leaf allocated {
                                    type yang:counter32;
                                    description "The number of resources that are currently allocated.";
                                }

                            } // container port-vlan-translation-ext

                            ///nokia-state/state/card/fp/resource-usage/ixr/egress-encapsulation/banks/arp-ext
                            container arp-ext {
                                description "Enter the arp-ext context";

                                ///nokia-state/state/card/fp/resource-usage/ixr/egress-encapsulation/banks/arp-ext/allocated
                                leaf allocated {
                                    type yang:counter32;
                                    description "The number of resources that are currently allocated.";
                                }

                            } // container arp-ext

                            ///nokia-state/state/card/fp/resource-usage/ixr/egress-encapsulation/banks/label-push-ext
                            container label-push-ext {
                                description "Enter the label-push-ext context";

                                ///nokia-state/state/card/fp/resource-usage/ixr/egress-encapsulation/banks/label-push-ext/allocated
                                leaf allocated {
                                    type yang:counter32;
                                    description "The number of resources that are currently allocated.";
                                }

                            } // container label-push-ext

                            ///nokia-state/state/card/fp/resource-usage/ixr/egress-encapsulation/banks/label-swap-push-ext
                            container label-swap-push-ext {
                                description "Enter the label-swap-push-ext context";

                                ///nokia-state/state/card/fp/resource-usage/ixr/egress-encapsulation/banks/label-swap-push-ext/allocated
                                leaf allocated {
                                    type yang:counter32;
                                    description "The number of resources that are currently allocated.";
                                }

                            } // container label-swap-push-ext

                        } // container banks

                        ///nokia-state/state/card/fp/resource-usage/ixr/egress-encapsulation/entries
                        container entries {
                            description "Enter the entries context";

                            ///nokia-state/state/card/fp/resource-usage/ixr/egress-encapsulation/entries/total
                            leaf total {
                                type yang:counter32;
                                description "The total number of resources.";
                            }

                            ///nokia-state/state/card/fp/resource-usage/ixr/egress-encapsulation/entries/allocated
                            leaf allocated {
                                type yang:counter32;
                                description "The number of resources that are currently allocated.";
                            }

                            ///nokia-state/state/card/fp/resource-usage/ixr/egress-encapsulation/entries/free
                            leaf free {
                                type yang:counter32;
                                description "The number of free resources that are currently available.";
                            }

                            ///nokia-state/state/card/fp/resource-usage/ixr/egress-encapsulation/entries/routed
                            container routed {
                                description "Enter the routed context";

                                ///nokia-state/state/card/fp/resource-usage/ixr/egress-encapsulation/entries/routed/total
                                leaf total {
                                    type yang:counter32;
                                    description "The total number of resources.";
                                }

                                ///nokia-state/state/card/fp/resource-usage/ixr/egress-encapsulation/entries/routed/allocated
                                leaf allocated {
                                    type yang:counter32;
                                    description "The number of resources that are currently allocated.";
                                }

                                ///nokia-state/state/card/fp/resource-usage/ixr/egress-encapsulation/entries/routed/free
                                leaf free {
                                    type yang:counter32;
                                    description "The number of free resources that are currently available.";
                                }

                            } // container routed

                            ///nokia-state/state/card/fp/resource-usage/ixr/egress-encapsulation/entries/tdm
                            container tdm {
                                description "Enter the tdm context";

                                ///nokia-state/state/card/fp/resource-usage/ixr/egress-encapsulation/entries/tdm/total
                                leaf total {
                                    type yang:counter32;
                                    description "The total number of resources.";
                                }

                                ///nokia-state/state/card/fp/resource-usage/ixr/egress-encapsulation/entries/tdm/allocated
                                leaf allocated {
                                    type yang:counter32;
                                    description "The number of resources that are currently allocated.";
                                }

                                ///nokia-state/state/card/fp/resource-usage/ixr/egress-encapsulation/entries/tdm/free
                                leaf free {
                                    type yang:counter32;
                                    description "The number of free resources that are currently available.";
                                }

                            } // container tdm

                            ///nokia-state/state/card/fp/resource-usage/ixr/egress-encapsulation/entries/port-vlan-translation
                            container port-vlan-translation {
                                description "Enter the port-vlan-translation context";

                                ///nokia-state/state/card/fp/resource-usage/ixr/egress-encapsulation/entries/port-vlan-translation/total
                                leaf total {
                                    type yang:counter32;
                                    description "The total number of resources.";
                                }

                                ///nokia-state/state/card/fp/resource-usage/ixr/egress-encapsulation/entries/port-vlan-translation/allocated
                                leaf allocated {
                                    type yang:counter32;
                                    description "The number of resources that are currently allocated.";
                                }

                                ///nokia-state/state/card/fp/resource-usage/ixr/egress-encapsulation/entries/port-vlan-translation/free
                                leaf free {
                                    type yang:counter32;
                                    description "The number of free resources that are currently available.";
                                }

                            } // container port-vlan-translation

                            ///nokia-state/state/card/fp/resource-usage/ixr/egress-encapsulation/entries/arp
                            container arp {
                                description "Enter the arp context";

                                ///nokia-state/state/card/fp/resource-usage/ixr/egress-encapsulation/entries/arp/total
                                leaf total {
                                    type yang:counter32;
                                    description "The total number of resources.";
                                }

                                ///nokia-state/state/card/fp/resource-usage/ixr/egress-encapsulation/entries/arp/allocated
                                leaf allocated {
                                    type yang:counter32;
                                    description "The number of resources that are currently allocated.";
                                }

                                ///nokia-state/state/card/fp/resource-usage/ixr/egress-encapsulation/entries/arp/free
                                leaf free {
                                    type yang:counter32;
                                    description "The number of free resources that are currently available.";
                                }

                            } // container arp

                            ///nokia-state/state/card/fp/resource-usage/ixr/egress-encapsulation/entries/label-push
                            container label-push {
                                description "Enter the label-push context";

                                ///nokia-state/state/card/fp/resource-usage/ixr/egress-encapsulation/entries/label-push/total
                                leaf total {
                                    type yang:counter32;
                                    description "The total number of resources.";
                                }

                                ///nokia-state/state/card/fp/resource-usage/ixr/egress-encapsulation/entries/label-push/allocated
                                leaf allocated {
                                    type yang:counter32;
                                    description "The number of resources that are currently allocated.";
                                }

                                ///nokia-state/state/card/fp/resource-usage/ixr/egress-encapsulation/entries/label-push/free
                                leaf free {
                                    type yang:counter32;
                                    description "The number of free resources that are currently available.";
                                }

                            } // container label-push

                            ///nokia-state/state/card/fp/resource-usage/ixr/egress-encapsulation/entries/label-swap-push
                            container label-swap-push {
                                description "Enter the label-swap-push context";

                                ///nokia-state/state/card/fp/resource-usage/ixr/egress-encapsulation/entries/label-swap-push/total
                                leaf total {
                                    type yang:counter32;
                                    description "The total number of resources.";
                                }

                                ///nokia-state/state/card/fp/resource-usage/ixr/egress-encapsulation/entries/label-swap-push/allocated
                                leaf allocated {
                                    type yang:counter32;
                                    description "The number of resources that are currently allocated.";
                                }

                                ///nokia-state/state/card/fp/resource-usage/ixr/egress-encapsulation/entries/label-swap-push/free
                                leaf free {
                                    type yang:counter32;
                                    description "The number of free resources that are currently available.";
                                }

                            } // container label-swap-push

                            ///nokia-state/state/card/fp/resource-usage/ixr/egress-encapsulation/entries/port-vlan-translation-ext
                            container port-vlan-translation-ext {
                                description "Enter the port-vlan-translation-ext context";

                                ///nokia-state/state/card/fp/resource-usage/ixr/egress-encapsulation/entries/port-vlan-translation-ext/total
                                leaf total {
                                    type yang:counter32;
                                    description "The total number of resources.";
                                }

                                ///nokia-state/state/card/fp/resource-usage/ixr/egress-encapsulation/entries/port-vlan-translation-ext/allocated
                                leaf allocated {
                                    type yang:counter32;
                                    description "The number of resources that are currently allocated.";
                                }

                                ///nokia-state/state/card/fp/resource-usage/ixr/egress-encapsulation/entries/port-vlan-translation-ext/free
                                leaf free {
                                    type yang:counter32;
                                    description "The number of free resources that are currently available.";
                                }

                            } // container port-vlan-translation-ext

                            ///nokia-state/state/card/fp/resource-usage/ixr/egress-encapsulation/entries/arp-ext
                            container arp-ext {
                                description "Enter the arp-ext context";

                                ///nokia-state/state/card/fp/resource-usage/ixr/egress-encapsulation/entries/arp-ext/total
                                leaf total {
                                    type yang:counter32;
                                    description "The total number of resources.";
                                }

                                ///nokia-state/state/card/fp/resource-usage/ixr/egress-encapsulation/entries/arp-ext/allocated
                                leaf allocated {
                                    type yang:counter32;
                                    description "The number of resources that are currently allocated.";
                                }

                                ///nokia-state/state/card/fp/resource-usage/ixr/egress-encapsulation/entries/arp-ext/free
                                leaf free {
                                    type yang:counter32;
                                    description "The number of free resources that are currently available.";
                                }

                            } // container arp-ext

                            ///nokia-state/state/card/fp/resource-usage/ixr/egress-encapsulation/entries/label-push-ext
                            container label-push-ext {
                                description "Enter the label-push-ext context";

                                ///nokia-state/state/card/fp/resource-usage/ixr/egress-encapsulation/entries/label-push-ext/total
                                leaf total {
                                    type yang:counter32;
                                    description "The total number of resources.";
                                }

                                ///nokia-state/state/card/fp/resource-usage/ixr/egress-encapsulation/entries/label-push-ext/allocated
                                leaf allocated {
                                    type yang:counter32;
                                    description "The number of resources that are currently allocated.";
                                }

                                ///nokia-state/state/card/fp/resource-usage/ixr/egress-encapsulation/entries/label-push-ext/free
                                leaf free {
                                    type yang:counter32;
                                    description "The number of free resources that are currently available.";
                                }

                            } // container label-push-ext

                            ///nokia-state/state/card/fp/resource-usage/ixr/egress-encapsulation/entries/label-swap-push-ext
                            container label-swap-push-ext {
                                description "Enter the label-swap-push-ext context";

                                ///nokia-state/state/card/fp/resource-usage/ixr/egress-encapsulation/entries/label-swap-push-ext/total
                                leaf total {
                                    type yang:counter32;
                                    description "The total number of resources.";
                                }

                                ///nokia-state/state/card/fp/resource-usage/ixr/egress-encapsulation/entries/label-swap-push-ext/allocated
                                leaf allocated {
                                    type yang:counter32;
                                    description "The number of resources that are currently allocated.";
                                }

                                ///nokia-state/state/card/fp/resource-usage/ixr/egress-encapsulation/entries/label-swap-push-ext/free
                                leaf free {
                                    type yang:counter32;
                                    description "The number of free resources that are currently available.";
                                }

                            } // container label-swap-push-ext

                        } // container entries

                    } // container egress-encapsulation

                    ///nokia-state/state/card/fp/resource-usage/ixr/egress-encapsulation-extension
                    container egress-encapsulation-extension {
                        description "Enter the egress-encapsulation-extension context";

                        ///nokia-state/state/card/fp/resource-usage/ixr/egress-encapsulation-extension/banks
                        container banks {
                            description "Enter the banks context";

                            ///nokia-state/state/card/fp/resource-usage/ixr/egress-encapsulation-extension/banks/total
                            leaf total {
                                type yang:counter32;
                                description "The total number of resources.";
                            }

                            ///nokia-state/state/card/fp/resource-usage/ixr/egress-encapsulation-extension/banks/allocated
                            leaf allocated {
                                type yang:counter32;
                                description "The number of resources that are currently allocated.";
                            }

                            ///nokia-state/state/card/fp/resource-usage/ixr/egress-encapsulation-extension/banks/free
                            leaf free {
                                type yang:counter32;
                                description "The number of free resources that are currently available.";
                            }

                            ///nokia-state/state/card/fp/resource-usage/ixr/egress-encapsulation-extension/banks/port-vlan-translation
                            container port-vlan-translation {
                                description "Enter the port-vlan-translation context";

                                ///nokia-state/state/card/fp/resource-usage/ixr/egress-encapsulation-extension/banks/port-vlan-translation/allocated
                                leaf allocated {
                                    type yang:counter32;
                                    description "The number of resources that are currently allocated.";
                                }

                            } // container port-vlan-translation

                            ///nokia-state/state/card/fp/resource-usage/ixr/egress-encapsulation-extension/banks/arp
                            container arp {
                                description "Enter the arp context";

                                ///nokia-state/state/card/fp/resource-usage/ixr/egress-encapsulation-extension/banks/arp/allocated
                                leaf allocated {
                                    type yang:counter32;
                                    description "The number of resources that are currently allocated.";
                                }

                            } // container arp

                            ///nokia-state/state/card/fp/resource-usage/ixr/egress-encapsulation-extension/banks/label-push
                            container label-push {
                                description "Enter the label-push context";

                                ///nokia-state/state/card/fp/resource-usage/ixr/egress-encapsulation-extension/banks/label-push/allocated
                                leaf allocated {
                                    type yang:counter32;
                                    description "The number of resources that are currently allocated.";
                                }

                            } // container label-push

                            ///nokia-state/state/card/fp/resource-usage/ixr/egress-encapsulation-extension/banks/label-swap-push
                            container label-swap-push {
                                description "Enter the label-swap-push context";

                                ///nokia-state/state/card/fp/resource-usage/ixr/egress-encapsulation-extension/banks/label-swap-push/allocated
                                leaf allocated {
                                    type yang:counter32;
                                    description "The number of resources that are currently allocated.";
                                }

                            } // container label-swap-push

                        } // container banks

                        ///nokia-state/state/card/fp/resource-usage/ixr/egress-encapsulation-extension/entries
                        container entries {
                            description "Enter the entries context";

                            ///nokia-state/state/card/fp/resource-usage/ixr/egress-encapsulation-extension/entries/total
                            leaf total {
                                type yang:counter32;
                                description "The total number of resources.";
                            }

                            ///nokia-state/state/card/fp/resource-usage/ixr/egress-encapsulation-extension/entries/allocated
                            leaf allocated {
                                type yang:counter32;
                                description "The number of resources that are currently allocated.";
                            }

                            ///nokia-state/state/card/fp/resource-usage/ixr/egress-encapsulation-extension/entries/free
                            leaf free {
                                type yang:counter32;
                                description "The number of free resources that are currently available.";
                            }

                            ///nokia-state/state/card/fp/resource-usage/ixr/egress-encapsulation-extension/entries/port-vlan-translation
                            container port-vlan-translation {
                                description "Enter the port-vlan-translation context";

                                ///nokia-state/state/card/fp/resource-usage/ixr/egress-encapsulation-extension/entries/port-vlan-translation/total
                                leaf total {
                                    type yang:counter32;
                                    description "The total number of resources.";
                                }

                                ///nokia-state/state/card/fp/resource-usage/ixr/egress-encapsulation-extension/entries/port-vlan-translation/allocated
                                leaf allocated {
                                    type yang:counter32;
                                    description "The number of resources that are currently allocated.";
                                }

                                ///nokia-state/state/card/fp/resource-usage/ixr/egress-encapsulation-extension/entries/port-vlan-translation/free
                                leaf free {
                                    type yang:counter32;
                                    description "The number of free resources that are currently available.";
                                }

                            } // container port-vlan-translation

                            ///nokia-state/state/card/fp/resource-usage/ixr/egress-encapsulation-extension/entries/arp
                            container arp {
                                description "Enter the arp context";

                                ///nokia-state/state/card/fp/resource-usage/ixr/egress-encapsulation-extension/entries/arp/total
                                leaf total {
                                    type yang:counter32;
                                    description "The total number of resources.";
                                }

                                ///nokia-state/state/card/fp/resource-usage/ixr/egress-encapsulation-extension/entries/arp/allocated
                                leaf allocated {
                                    type yang:counter32;
                                    description "The number of resources that are currently allocated.";
                                }

                                ///nokia-state/state/card/fp/resource-usage/ixr/egress-encapsulation-extension/entries/arp/free
                                leaf free {
                                    type yang:counter32;
                                    description "The number of free resources that are currently available.";
                                }

                            } // container arp

                            ///nokia-state/state/card/fp/resource-usage/ixr/egress-encapsulation-extension/entries/label-push
                            container label-push {
                                description "Enter the label-push context";

                                ///nokia-state/state/card/fp/resource-usage/ixr/egress-encapsulation-extension/entries/label-push/total
                                leaf total {
                                    type yang:counter32;
                                    description "The total number of resources.";
                                }

                                ///nokia-state/state/card/fp/resource-usage/ixr/egress-encapsulation-extension/entries/label-push/allocated
                                leaf allocated {
                                    type yang:counter32;
                                    description "The number of resources that are currently allocated.";
                                }

                                ///nokia-state/state/card/fp/resource-usage/ixr/egress-encapsulation-extension/entries/label-push/free
                                leaf free {
                                    type yang:counter32;
                                    description "The number of free resources that are currently available.";
                                }

                            } // container label-push

                            ///nokia-state/state/card/fp/resource-usage/ixr/egress-encapsulation-extension/entries/label-swap-push
                            container label-swap-push {
                                description "Enter the label-swap-push context";

                                ///nokia-state/state/card/fp/resource-usage/ixr/egress-encapsulation-extension/entries/label-swap-push/total
                                leaf total {
                                    type yang:counter32;
                                    description "The total number of resources.";
                                }

                                ///nokia-state/state/card/fp/resource-usage/ixr/egress-encapsulation-extension/entries/label-swap-push/allocated
                                leaf allocated {
                                    type yang:counter32;
                                    description "The number of resources that are currently allocated.";
                                }

                                ///nokia-state/state/card/fp/resource-usage/ixr/egress-encapsulation-extension/entries/label-swap-push/free
                                leaf free {
                                    type yang:counter32;
                                    description "The number of free resources that are currently available.";
                                }

                            } // container label-swap-push

                        } // container entries

                    } // container egress-encapsulation-extension

                } // container ixr

            } // container resource-usage

            ///nokia-state/state/card/fp/tap
            list tap {
                key "tap-number";
                description "Enter the tap list instance";

                ///nokia-state/state/card/fp/tap/tap-number
                leaf tap-number {
                    type uint32 {
                        range "1..8";
                    }
                    description
                        "The unique value which uniquely identifies the tap number of the tap corresponding
                         to the forwarding plane within a specific IOM card in the system.";
                }

                ///nokia-state/state/card/fp/tap/ingress
                container ingress {
                    description "Enter the ingress context";

                    ///nokia-state/state/card/fp/tap/ingress/per-egress-dst
                    list per-egress-dst {
                        key "dst-card-number dst-fp-number dst-tap-number";
                        description "Enter the per-egress-dst list instance";

                        ///nokia-state/state/card/fp/tap/ingress/per-egress-dst/dst-card-number
                        leaf dst-card-number {
                            type types-card:iom-card-slot;
                            description "The unique value which identifies this destination IOM slot within a chassis in the system.";
                        }

                        ///nokia-state/state/card/fp/tap/ingress/per-egress-dst/dst-fp-number
                        leaf dst-fp-number {
                            type uint32 {
                                range "1..12";
                            }
                            description
                                "The unique value which uniquely identifies the destination forwarding plane within
                                 a specific IOM card in the system.";
                        }

                        ///nokia-state/state/card/fp/tap/ingress/per-egress-dst/dst-tap-number
                        leaf dst-tap-number {
                            type uint32 {
                                range "1..8";
                            }
                            description
                                "The unique value which uniquely identifies the destination number of the tap corresponding
                                 to the forwarding plane within a specific IOM card in the system.";
                        }

                        ///nokia-state/state/card/fp/tap/ingress/per-egress-dst/statistics
                        container statistics {
                            description "Enter the statistics context";

                            ///nokia-state/state/card/fp/tap/ingress/per-egress-dst/statistics/expedite-forwarded-packets
                            leaf expedite-forwarded-packets {
                                type yang:counter64;
                                description "The number of expedited forwarded packets.";
                            }

                            ///nokia-state/state/card/fp/tap/ingress/per-egress-dst/statistics/expedite-forwarded-octets
                            leaf expedite-forwarded-octets {
                                type yang:counter64;
                                description "The number of expedited forwarded octets.";
                            }

                            ///nokia-state/state/card/fp/tap/ingress/per-egress-dst/statistics/best-effort-forwarded-packets
                            leaf best-effort-forwarded-packets {
                                type yang:counter64;
                                description "The number of best effort forwarded packets.";
                            }

                            ///nokia-state/state/card/fp/tap/ingress/per-egress-dst/statistics/best-effort-forwarded-octets
                            leaf best-effort-forwarded-octets {
                                type yang:counter64;
                                description "The number of best effort forwarded octets.";
                            }

                        } // container statistics

                    } // list per-egress-dst

                } // container ingress

            } // list tap

        } // list fp

    } // grouping state-card-fp

}
