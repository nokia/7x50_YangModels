submodule nokia-state-testoam-service-activation-testhead {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-log                { prefix "types-log"; }
    import nokia-types-oam                { prefix "types-oam"; }
    import nokia-types-sros               { prefix "types-sros"; }

    include nokia-state-eth-cfm;

    sros-ext:sros-major-release "rel23";
    organization "Nokia";
    contact
        "Nokia SR OS Support
         Web: <http://www.nokia.com>";
    description
        "Nokia YANG Data model with operational state for OAM Service Activation Tests (Y.1564) on SR OS based routers.

         Copyright 2016 Nokia. All rights reserved. Reproduction of this document
         is authorized on the condition that the foregoing copyright notice is included.

         This nokia-state-testoam-service-activation-testhead YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-05-30";

    grouping state-testoam-service-activation-testhead {
        ///nokia-state/state/test-oam/service-activation-testhead
        container service-activation-testhead {
            description "Enable the service-activation-testhead context";

            ///nokia-state/state/test-oam/service-activation-testhead/service-test
            list service-test {
                key "test-name";
                description "Enter the service-test list instance";

                ///nokia-state/state/test-oam/service-activation-testhead/service-test/test-name
                leaf test-name {
                    type types-sros:named-item-64;
                    description "Service activation test name";
                }

            } // list service-test

            ///nokia-state/state/test-oam/service-activation-testhead/statistics
            container statistics {
                description "Enter the statistics context";

                ///nokia-state/state/test-oam/service-activation-testhead/statistics/service-test
                list service-test {
                    key "test-name test-run";
                    description "Enter the service-test list instance";

                    ///nokia-state/state/test-oam/service-activation-testhead/statistics/service-test/test-name
                    leaf test-name {
                        type types-sros:named-item-64;
                        description "The name of the Service Activation Test";
                    }

                    ///nokia-state/state/test-oam/service-activation-testhead/statistics/service-test/test-run
                    leaf test-run {
                        type uint32 {
                            range "1..4294967295";
                        }
                        description "The run number of the OAM Service Activation service-test run to be read";
                    }

                    ///nokia-state/state/test-oam/service-activation-testhead/statistics/service-test/description
                    leaf description {
                        type types-sros:description;
                        description "Configure the description of the service test";
                    }

                    ///nokia-state/state/test-oam/service-activation-testhead/statistics/service-test/accounting-policy
                    leaf accounting-policy {
                        type types-log:log-policy-id;
                        description "Configure the accounting policy, used to record results for the service test";
                    }

                    ///nokia-state/state/test-oam/service-activation-testhead/statistics/service-test/oper-state
                    leaf oper-state {
                        type types-oam:sath-statistics-test-run-oper-state;
                        description "Indicates the operational state of the service-test run";
                    }

                    ///nokia-state/state/test-oam/service-activation-testhead/statistics/service-test/accounting-oper-state
                    leaf accounting-oper-state {
                        type enumeration {
                            enum none                           { value 1; }
                            enum ready-to-send                  { value 2; }
                            enum sent                           { value 3; }
                            enum unable-to-send                 { value 4; }
                        }
                        description
                            "Indicates the operational status of the transfer of the service-test run's results
                             to the accounting log";
                    }

                    ///nokia-state/state/test-oam/service-activation-testhead/statistics/service-test/time-start
                    leaf time-start {
                        type types-oam:sath-test-time-start;
                        description "Indicates the start time (in UTC) of the specified service-test run";
                    }

                    ///nokia-state/state/test-oam/service-activation-testhead/statistics/service-test/time-end
                    leaf time-end {
                        type types-oam:sath-test-time-end;
                        description "Indicates the end time (in UTC) of the specified service-test run";
                    }

                    ///nokia-state/state/test-oam/service-activation-testhead/statistics/service-test/service-test-completion-notification
                    leaf service-test-completion-notification {
                        type boolean;
                        description "Enable SNMP trap generation upon test completion";
                    }

                    ///nokia-state/state/test-oam/service-activation-testhead/statistics/service-test/stream-run-type
                    leaf stream-run-type {
                        type enumeration {
                            enum sequential                     { value 1; }
                            enum parallel                       { value 2; }
                        }
                        description "Service stream run order";
                    }

                    ///nokia-state/state/test-oam/service-activation-testhead/statistics/service-test/test-duration
                    container test-duration {
                        description "Enter the test-duration context";

                        ///nokia-state/state/test-oam/service-activation-testhead/statistics/service-test/test-duration/cir
                        container cir {
                            description "Enter the cir context";

                            ///nokia-state/state/test-oam/service-activation-testhead/statistics/service-test/test-duration/cir/minutes-seconds
                            leaf minutes-seconds {
                                type types-oam:sath-mm-ss-string;
                                description "Duration of the service test CIR tests";
                            }

                        } // container cir

                        ///nokia-state/state/test-oam/service-activation-testhead/statistics/service-test/test-duration/cir-pir
                        container cir-pir {
                            description "Enter the cir-pir context";

                            ///nokia-state/state/test-oam/service-activation-testhead/statistics/service-test/test-duration/cir-pir/minutes-seconds
                            leaf minutes-seconds {
                                type types-oam:sath-mm-ss-string;
                                description "Duration of the service test CIR-PIR tests";
                            }

                        } // container cir-pir

                        ///nokia-state/state/test-oam/service-activation-testhead/statistics/service-test/test-duration/policing
                        container policing {
                            description "Enter the policing context";

                            ///nokia-state/state/test-oam/service-activation-testhead/statistics/service-test/test-duration/policing/minutes-seconds
                            leaf minutes-seconds {
                                type types-oam:sath-mm-ss-string;
                                description "Duration of policing tests belonging to the test";
                            }

                        } // container policing

                        ///nokia-state/state/test-oam/service-activation-testhead/statistics/service-test/test-duration/performance
                        container performance {
                            description "Enter the performance context";

                            ///nokia-state/state/test-oam/service-activation-testhead/statistics/service-test/test-duration/performance/hours-minutes-seconds
                            leaf hours-minutes-seconds {
                                type types-oam:sath-hh-mm-ss-string;
                                description "Duration of performance tests belonging to the test";
                            }

                        } // container performance

                    } // container test-duration

                    ///nokia-state/state/test-oam/service-activation-testhead/statistics/service-test/service-stream
                    list service-stream {
                        key "stream-id";
                        description "Enter the service-stream list instance";

                        ///nokia-state/state/test-oam/service-activation-testhead/statistics/service-test/service-stream/stream-id
                        leaf stream-id {
                            type uint32 {
                                range "1..8";
                            }
                            description "The number of the service stream to be configured or read";
                        }

                        ///nokia-state/state/test-oam/service-activation-testhead/statistics/service-test/service-stream/description
                        leaf description {
                            type types-sros:description;
                            description "Configure the description of the service test";
                        }

                        ///nokia-state/state/test-oam/service-activation-testhead/statistics/service-test/service-stream/oper-state
                        leaf oper-state {
                            type types-oam:sath-statistics-test-run-oper-state;
                            description "Indicates the operational state of the service stream run";
                        }

                        ///nokia-state/state/test-oam/service-activation-testhead/statistics/service-test/service-stream/sap
                        leaf sap {
                            type string {
                                length "0..32";
                            }
                            description
                                "Indicates the Service Access Point (SAP) which hosts the Eth-CFM MEP, Domain, and
                                 Association configured for the service stream";
                        }

                        ///nokia-state/state/test-oam/service-activation-testhead/statistics/service-test/service-stream/router-instance
                        leaf router-instance {
                            type types-sros:named-item-or-empty;
                            description
                                "Indicates the router which hosts the Eth-CFM MEP, Domain, and
                                 Association configured for the service stream";
                        }

                        ///nokia-state/state/test-oam/service-activation-testhead/statistics/service-test/service-stream/router-interface
                        leaf router-interface {
                            type types-sros:named-item-or-empty;
                            description
                                "Indicates the router interface which hosts the Eth-CFM MEP, Domain, and
                                 Association configured for the service stream";
                        }

                        ///nokia-state/state/test-oam/service-activation-testhead/statistics/service-test/service-stream/source-port
                        leaf source-port {
                            type types-sros:named-item-or-empty;
                            description
                                "Indicates the port which hosts the Eth-CFM MEP, Domain, and
                                 Association configured for the service stream";
                        }

                        ///nokia-state/state/test-oam/service-activation-testhead/statistics/service-test/service-stream/src-mac
                        leaf src-mac {
                            type yang:mac-address;
                            description
                                "Indicates the source MAC address for the service stream

                                 00:00:00:00:00:00 is returned if a source MAC address is not available";
                        }

                        ///nokia-state/state/test-oam/service-activation-testhead/statistics/service-test/service-stream/acceptance-criteria-template
                        leaf acceptance-criteria-template {
                            type types-sros:named-item-64;
                            description "Configure the acceptance criteria template for the service stream";
                        }

                        ///nokia-state/state/test-oam/service-activation-testhead/statistics/service-test/service-stream/rate-cir
                        leaf rate-cir {
                            type uint32 {
                                range "0..400000000";
                            }
                            units "kilobps";
                            description "CIR packet transmit rate for the service stream";
                        }

                        ///nokia-state/state/test-oam/service-activation-testhead/statistics/service-test/service-stream/rate-pir
                        leaf rate-pir {
                            type uint32 {
                                range "0..400000000";
                            }
                            units "kilobps";
                            description "PIR packet transmit rate for the service stream";
                        }

                        ///nokia-state/state/test-oam/service-activation-testhead/statistics/service-test/service-stream/service-stream-completion-notification
                        leaf service-stream-completion-notification {
                            type boolean;
                            description "Enable SNMP trap generation upon test completion";
                        }

                        ///nokia-state/state/test-oam/service-activation-testhead/statistics/service-test/service-stream/size-a
                        leaf size-a {
                            type uint32 {
                                range "64..9212";
                            }
                            units "bytes";
                            description "Size-a";
                        }

                        ///nokia-state/state/test-oam/service-activation-testhead/statistics/service-test/service-stream/size-b
                        leaf size-b {
                            type uint32 {
                                range "64..9212";
                            }
                            units "bytes";
                            description "Size-b";
                        }

                        ///nokia-state/state/test-oam/service-activation-testhead/statistics/service-test/service-stream/size-c
                        leaf size-c {
                            type uint32 {
                                range "64..9212";
                            }
                            units "bytes";
                            description "Size-c";
                        }

                        ///nokia-state/state/test-oam/service-activation-testhead/statistics/service-test/service-stream/size-d
                        leaf size-d {
                            type uint32 {
                                range "64..9212";
                            }
                            units "bytes";
                            description "Size-d";
                        }

                        ///nokia-state/state/test-oam/service-activation-testhead/statistics/service-test/service-stream/size-e
                        leaf size-e {
                            type uint32 {
                                range "64..9212";
                            }
                            units "bytes";
                            description "Size-e";
                        }

                        ///nokia-state/state/test-oam/service-activation-testhead/statistics/service-test/service-stream/size-f
                        leaf size-f {
                            type uint32 {
                                range "64..9212";
                            }
                            units "bytes";
                            description "Size-f";
                        }

                        ///nokia-state/state/test-oam/service-activation-testhead/statistics/service-test/service-stream/size-g
                        leaf size-g {
                            type uint32 {
                                range "64..9212";
                            }
                            units "bytes";
                            description "Size-g";
                        }

                        ///nokia-state/state/test-oam/service-activation-testhead/statistics/service-test/service-stream/size-h
                        leaf size-h {
                            type uint32 {
                                range "64..9212";
                            }
                            units "bytes";
                            description "Size-h";
                        }

                        ///nokia-state/state/test-oam/service-activation-testhead/statistics/service-test/service-stream/size-u
                        leaf size-u {
                            type uint32 {
                                range "64..9212";
                            }
                            units "bytes";
                            description "Size-u";
                        }

                        ///nokia-state/state/test-oam/service-activation-testhead/statistics/service-test/service-stream/cir-threshold
                        leaf cir-threshold {
                            type uint32 {
                                range "0..400000000";
                            }
                            units "kilobps";
                            description
                                "Indicates the value of
                                 /test-oam/service-activation-testhead/acceptance-criteria-template/cir-threshold
                                 when the test run started";
                        }

                        ///nokia-state/state/test-oam/service-activation-testhead/statistics/service-test/service-stream/pir-threshold
                        leaf pir-threshold {
                            type uint32 {
                                range "0..400000000";
                            }
                            units "kilobps";
                            description
                                "Indicates the value of
                                 /test-oam/service-activation-testhead/acceptance-criteria-template/pir-threshold
                                 when the test run started";
                        }

                        ///nokia-state/state/test-oam/service-activation-testhead/statistics/service-test/service-stream/loss-threshold
                        leaf loss-threshold {
                            type types-oam:sath-loss-percent-union;
                            description
                                "Indicates the value of
                                 /test-oam/service-activation-testhead/acceptance-criteria-template/loss-threshold
                                 when the test run started";
                        }

                        ///nokia-state/state/test-oam/service-activation-testhead/statistics/service-test/service-stream/loss-threshold-policing
                        leaf loss-threshold-policing {
                            type types-oam:sath-loss-percent-union;
                            description
                                "Indicates the value of
                                 /test-oam/service-activation-testhead/acceptance-criteria-template/loss-threshold-policing
                                 when the test run started";
                        }

                        ///nokia-state/state/test-oam/service-activation-testhead/statistics/service-test/service-stream/delay-threshold
                        leaf delay-threshold {
                            type uint32 {
                                range "0..100000000";
                            }
                            units "microseconds";
                            description
                                "Indicates the value of
                                 /test-oam/service-activation-testhead/acceptance-criteria-template/delay-threshold
                                 when the test run started";
                        }

                        ///nokia-state/state/test-oam/service-activation-testhead/statistics/service-test/service-stream/delay-var-threshold
                        leaf delay-var-threshold {
                            type uint32 {
                                range "0..100000000";
                            }
                            units "microseconds";
                            description
                                "Indicates the value of
                                 /test-oam/service-activation-testhead/acceptance-criteria-template/delay-var-threshold
                                 when the test run started";
                        }

                        ///nokia-state/state/test-oam/service-activation-testhead/statistics/service-test/service-stream/m-factor
                        leaf m-factor {
                            type uint32 {
                                range "0..400000000";
                            }
                            units "kilobps";
                            description
                                "Indicates the value of
                                 /test-oam/service-activation-testhead/acceptance-criteria-template/m-factor
                                 when the test run started";
                        }

                        ///nokia-state/state/test-oam/service-activation-testhead/statistics/service-test/service-stream/frame-mix
                        container frame-mix {
                            description "Enter the frame-mix context";

                            ///nokia-state/state/test-oam/service-activation-testhead/statistics/service-test/service-stream/frame-mix/frame-size-template
                            leaf frame-size-template {
                                type types-sros:named-item-64;
                                description "Configure the frame size template for the service stream";
                            }

                            ///nokia-state/state/test-oam/service-activation-testhead/statistics/service-test/service-stream/frame-mix/sequence
                            leaf sequence {
                                type string {
                                    length "1..16";
                                }
                                description "Configure the sequence of frame sizes for the service stream";
                            }

                        } // container frame-mix

                        ///nokia-state/state/test-oam/service-activation-testhead/statistics/service-test/service-stream/test-types
                        container test-types {
                            description "Enter the test-types context";

                            ///nokia-state/state/test-oam/service-activation-testhead/statistics/service-test/service-stream/test-types/cir
                            leaf cir {
                                type boolean;
                                description "Enable running a CIR test for the service stream";
                            }

                            ///nokia-state/state/test-oam/service-activation-testhead/statistics/service-test/service-stream/test-types/cir-pir
                            leaf cir-pir {
                                type boolean;
                                description "Enable running a CIR-PIR test for the service stream";
                            }

                            ///nokia-state/state/test-oam/service-activation-testhead/statistics/service-test/service-stream/test-types/policing
                            leaf policing {
                                type boolean;
                                description "Run a policing test for the service stream";
                            }

                            ///nokia-state/state/test-oam/service-activation-testhead/statistics/service-test/service-stream/test-types/performance
                            leaf performance {
                                type boolean;
                                description "Run a performance test for the service stream";
                            }

                        } // container test-types

                        ///nokia-state/state/test-oam/service-activation-testhead/statistics/service-test/service-stream/frame-payload
                        container frame-payload {
                            description "Enter the frame-payload context";

                            ///nokia-state/state/test-oam/service-activation-testhead/statistics/service-test/service-stream/frame-payload/data-pattern
                            container data-pattern {
                                description "Enter the data-pattern context";

                                ///nokia-state/state/test-oam/service-activation-testhead/statistics/service-test/service-stream/frame-payload/data-pattern/repeat
                                leaf repeat {
                                    type types-sros:hex-string-or-uint;
                                    description "Repeated 4-byte pattern to pad each packet sent";
                                }

                            } // container data-pattern

                            ///nokia-state/state/test-oam/service-activation-testhead/statistics/service-test/service-stream/frame-payload/ethernet
                            container ethernet {
                                description "Enter the ethernet context";

                                ///nokia-state/state/test-oam/service-activation-testhead/statistics/service-test/service-stream/frame-payload/ethernet/dst-mac
                                leaf dst-mac {
                                    type types-sros:mac-unicast-address-no-zero;
                                    description "Destination MAC address of Ethernet frames";
                                }

                                ///nokia-state/state/test-oam/service-activation-testhead/statistics/service-test/service-stream/frame-payload/ethernet/eth-cfm
                                container eth-cfm {
                                    description "Enter the eth-cfm context";

                                    ///nokia-state/state/test-oam/service-activation-testhead/statistics/service-test/service-stream/frame-payload/ethernet/eth-cfm/source
                                    container source {
                                        description "Enter the source context";

                                        ///nokia-state/state/test-oam/service-activation-testhead/statistics/service-test/service-stream/frame-payload/ethernet/eth-cfm/source/mep-id
                                        leaf mep-id {
                                            type types-eth-cfm:mep-id-type;
                                            description "Source Ethernet maintenance association end point";
                                        }

                                        ///nokia-state/state/test-oam/service-activation-testhead/statistics/service-test/service-stream/frame-payload/ethernet/eth-cfm/source/md-admin-name
                                        leaf md-admin-name {
                                            type leafref {
                                                path "../../../../../../../../../../eth-cfm/domain/md-admin-name";
                                            }
                                            description "Source Ethernet maintenance domain name";
                                        }

                                        ///nokia-state/state/test-oam/service-activation-testhead/statistics/service-test/service-stream/frame-payload/ethernet/eth-cfm/source/ma-admin-name
                                        leaf ma-admin-name {
                                            type leafref {
                                                path "../../../../../../../../../../eth-cfm/domain[md-admin-name=current()/../md-admin-name]/association/ma-admin-name";
                                            }
                                            description "Source Ethernet maintenance association name";
                                        }

                                    } // container source

                                } // container eth-cfm

                                ///nokia-state/state/test-oam/service-activation-testhead/statistics/service-test/service-stream/frame-payload/ethernet/s-tag
                                container s-tag {
                                    description "Enter the s-tag context";

                                    ///nokia-state/state/test-oam/service-activation-testhead/statistics/service-test/service-stream/frame-payload/ethernet/s-tag/dot1p
                                    leaf dot1p {
                                        type uint32 {
                                            range "0..7";
                                        }
                                        description "PCP of Ethernet frames for service stream";
                                    }

                                    ///nokia-state/state/test-oam/service-activation-testhead/statistics/service-test/service-stream/frame-payload/ethernet/s-tag/discard-eligible
                                    leaf discard-eligible {
                                        type boolean;
                                        description "Enable marking of the DEI bit in the VLAN header";
                                    }

                                } // container s-tag

                                ///nokia-state/state/test-oam/service-activation-testhead/statistics/service-test/service-stream/frame-payload/ethernet/c-tag
                                container c-tag {
                                    description "Enter the c-tag context";

                                    ///nokia-state/state/test-oam/service-activation-testhead/statistics/service-test/service-stream/frame-payload/ethernet/c-tag/dot1p
                                    leaf dot1p {
                                        type uint32 {
                                            range "0..7";
                                        }
                                        description "PCP of Ethernet frames for service stream";
                                    }

                                    ///nokia-state/state/test-oam/service-activation-testhead/statistics/service-test/service-stream/frame-payload/ethernet/c-tag/discard-eligible
                                    leaf discard-eligible {
                                        type boolean;
                                        description "Enable marking of the DEI bit in the VLAN header";
                                    }

                                } // container c-tag

                            } // container ethernet

                        } // container frame-payload

                        ///nokia-state/state/test-oam/service-activation-testhead/statistics/service-test/service-stream/test-results
                        list test-results {
                            key "test-type";
                            description "Enter the test-results list instance";

                            ///nokia-state/state/test-oam/service-activation-testhead/statistics/service-test/service-stream/test-results/test-type
                            leaf test-type {
                                type enumeration {
                                    enum cir                            { value 1; }
                                    enum cir-pir                        { value 2; }
                                    enum policing                       { value 3; }
                                    enum performance                    { value 4; }
                                }
                                description "The test type to be read";
                            }

                            ///nokia-state/state/test-oam/service-activation-testhead/statistics/service-test/service-stream/test-results/oper-state
                            leaf oper-state {
                                type types-oam:sath-statistics-test-run-oper-state;
                                description "Indicates the operational state of the test run";
                            }

                            ///nokia-state/state/test-oam/service-activation-testhead/statistics/service-test/service-stream/test-results/time-start
                            leaf time-start {
                                type types-oam:sath-test-time-start;
                                description "Indicates the start time (in UTC) of the test run";
                            }

                            ///nokia-state/state/test-oam/service-activation-testhead/statistics/service-test/service-stream/test-results/time-end
                            leaf time-end {
                                type types-oam:sath-test-time-end;
                                description "Indicates the end time (in UTC) of the test run";
                            }

                            ///nokia-state/state/test-oam/service-activation-testhead/statistics/service-test/service-stream/test-results/time-left
                            leaf time-left {
                                type uint32;
                                units "seconds";
                                description "Indicates the execution time remaining for the test run";
                            }

                            ///nokia-state/state/test-oam/service-activation-testhead/statistics/service-test/service-stream/test-results/oper-status-throughput
                            leaf oper-status-throughput {
                                type types-oam:sath-statistics-test-oper-state;
                                description
                                    "Indicates the test run's operational status, with respect to the throughput
                                     acceptance criteria";
                            }

                            ///nokia-state/state/test-oam/service-activation-testhead/statistics/service-test/service-stream/test-results/oper-status-frame-loss-ratio
                            leaf oper-status-frame-loss-ratio {
                                type types-oam:sath-statistics-test-oper-state;
                                description
                                    "Indicates the test run's operational status, with respect to the FLR acceptance
                                     criteria";
                            }

                            ///nokia-state/state/test-oam/service-activation-testhead/statistics/service-test/service-stream/test-results/oper-status-delay
                            leaf oper-status-delay {
                                type types-oam:sath-statistics-test-oper-state;
                                description
                                    "Indicates the test run's operational status, with respect to the delay acceptance
                                     criteria";
                            }

                            ///nokia-state/state/test-oam/service-activation-testhead/statistics/service-test/service-stream/test-results/oper-status-delay-var
                            leaf oper-status-delay-var {
                                type types-oam:sath-statistics-test-oper-state;
                                description
                                    "Indicates the test run's operational status, with respect to the delay variation
                                     acceptance criteria";
                            }

                            ///nokia-state/state/test-oam/service-activation-testhead/statistics/service-test/service-stream/test-results/measured-delay-min
                            leaf measured-delay-min {
                                type int32;
                                units "microseconds";
                                description "Indicates the minimum delay measured for the test run";
                            }

                            ///nokia-state/state/test-oam/service-activation-testhead/statistics/service-test/service-stream/test-results/measured-delay-max
                            leaf measured-delay-max {
                                type int32;
                                units "microseconds";
                                description "Indicates the maximum delay measured for the test run";
                            }

                            ///nokia-state/state/test-oam/service-activation-testhead/statistics/service-test/service-stream/test-results/measured-delay-avg
                            leaf measured-delay-avg {
                                type int32;
                                units "microseconds";
                                description "Indicates the average delay measured for the test run";
                            }

                            ///nokia-state/state/test-oam/service-activation-testhead/statistics/service-test/service-stream/test-results/measured-delay-var-min
                            leaf measured-delay-var-min {
                                type int32;
                                units "microseconds";
                                description "Indicates the minimum delay variation measured for the test run";
                            }

                            ///nokia-state/state/test-oam/service-activation-testhead/statistics/service-test/service-stream/test-results/measured-delay-var-max
                            leaf measured-delay-var-max {
                                type int32;
                                units "microseconds";
                                description "Indicates the maximum delay variation measured for the test run";
                            }

                            ///nokia-state/state/test-oam/service-activation-testhead/statistics/service-test/service-stream/test-results/measured-delay-var-avg
                            leaf measured-delay-var-avg {
                                type int32;
                                units "microseconds";
                                description "Indicates the average delay variation measured for the test run";
                            }

                            ///nokia-state/state/test-oam/service-activation-testhead/statistics/service-test/service-stream/test-results/measured-throughput
                            leaf measured-throughput {
                                type uint32;
                                units "kilobps";
                                description "Indicates the measured throughput for the test run";
                            }

                            ///nokia-state/state/test-oam/service-activation-testhead/statistics/service-test/service-stream/test-results/measured-frame-loss-ratio
                            leaf measured-frame-loss-ratio {
                                type types-oam:sath-loss-percent-decimal64;
                                units "percent";
                                description "Indicates the measured FLR for the test run";
                            }

                            ///nokia-state/state/test-oam/service-activation-testhead/statistics/service-test/service-stream/test-results/measured-frame-tx
                            leaf measured-frame-tx {
                                type yang:counter64;
                                units "frames";
                                description "Indicates the number of frames transmitted during the test run";
                            }

                            ///nokia-state/state/test-oam/service-activation-testhead/statistics/service-test/service-stream/test-results/measured-frame-rx
                            leaf measured-frame-rx {
                                type yang:counter64;
                                units "frames";
                                description "Indicates the number of frames received during the test run";
                            }

                        } // list test-results

                    } // list service-stream

                } // list service-test

            } // container statistics

        } // container service-activation-testhead

    } // grouping state-testoam-service-activation-testhead

}
