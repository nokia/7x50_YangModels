submodule nokia-conf-port-eth-access {

    yang-version "1.1";

    belongs-to nokia-conf { prefix "conf"; }

    import nokia-sros-yang-extensions     { prefix "sros-ext"; }
    import nokia-types-qos                { prefix "types-qos"; }
    import nokia-types-services           { prefix "types-services"; }
    import nokia-types-sros               { prefix "types-sros"; }
    import nokia-types-subscriber-mgmt    { prefix "types-submgt"; }

    include nokia-conf-groups;
    include nokia-conf-log;
    include nokia-conf-qos;

    sros-ext:sros-major-release "rel23";
    organization "Nokia";
    contact
        "Nokia SR OS Support
         Web: <http://www.nokia.com>";
    description
        "Nokia YANG Data model to configure access capabilities for ethernet ports on SR OS based routers.

         Copyright 2016 Nokia. All rights reserved. Reproduction of this document
         is authorized on the condition that the foregoing copyright notice is included.

         This nokia-conf-port-eth-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-15";

    grouping conf-port-eth-access {
        ///nokia-conf/configure/port/ethernet/access
        container access {
            description "Enter the access context";

            ///nokia-conf/configure/port/ethernet/access/bandwidth
            leaf bandwidth {
                type uint64 {
                    range "1..6400000000";
                }
                units "kilobps";
                description "Administrative bandwidth assigned to Ethernet ports";
            }

            ///nokia-conf/configure/port/ethernet/access/booking-factor
            leaf booking-factor {
                type uint32 {
                    range "1..1000";
                }
                default "100";
                description "Booking factor applied to the Ethernet port";
            }

            ///nokia-conf/configure/port/ethernet/access/accounting-policy
            leaf accounting-policy {
                type leafref {
                    path "../../../../log/accounting-policy/policy-id";
                }
                description "Accounting policy for the Ethernet port access queue";
            }

            ///nokia-conf/configure/port/ethernet/access/collect-stats
            leaf collect-stats {
                type boolean;
                default "false";
                description "Allow collection of statistics on the queue";
            }

            ///nokia-conf/configure/port/ethernet/access/apply-groups
            leaf-list apply-groups {
                type leafref {
                    path "../../../../groups/group/name";
                }
                max-elements 8;
                ordered-by user;
                description "Apply a configuration group at this level";
            }

            ///nokia-conf/configure/port/ethernet/access/apply-groups-exclude
            leaf-list apply-groups-exclude {
                type leafref {
                    path "../../../../groups/group/name";
                }
                max-elements 8;
                ordered-by user;
                description "Exclude a configuration group at this level";
            }

            ///nokia-conf/configure/port/ethernet/access/egress
            container egress {
                description "Enter the egress context";

                ///nokia-conf/configure/port/ethernet/access/egress/queue-group
                list queue-group {
                    key "queue-group-name instance-id";
                    description "Enter the queue-group list instance";

                    ///nokia-conf/configure/port/ethernet/access/egress/queue-group/queue-group-name
                    leaf queue-group-name {
                        type leafref {
                            path "../../../../../../qos/queue-group-templates/egress/queue-group/egress-queue-group-name";
                        }
                        description "Queue group name";
                    }

                    ///nokia-conf/configure/port/ethernet/access/egress/queue-group/instance-id
                    leaf instance-id {
                        type uint16 {
                            range "1..65535";
                        }
                        description "Instance ID for the egress queue group";
                    }

                    ///nokia-conf/configure/port/ethernet/access/egress/queue-group/accounting-policy
                    leaf accounting-policy {
                        type leafref {
                            path "../../../../../../log/accounting-policy/policy-id";
                        }
                        description "Accounting policy for the Ethernet port";
                    }

                    ///nokia-conf/configure/port/ethernet/access/egress/queue-group/collect-stats
                    leaf collect-stats {
                        type boolean;
                        default "false";
                        description "Collect accounting and statistical data";
                    }

                    ///nokia-conf/configure/port/ethernet/access/egress/queue-group/description
                    leaf description {
                        type types-sros:description;
                        description "Text description";
                    }

                    ///nokia-conf/configure/port/ethernet/access/egress/queue-group/hs-turbo
                    leaf hs-turbo {
                        type boolean;
                        default "false";
                        description "Enable HS turbo queues for higher throughput";
                    }

                    ///nokia-conf/configure/port/ethernet/access/egress/queue-group/apply-groups
                    leaf-list apply-groups {
                        type leafref {
                            path "../../../../../../groups/group/name";
                        }
                        max-elements 8;
                        ordered-by user;
                        description "Apply a configuration group at this level";
                    }

                    ///nokia-conf/configure/port/ethernet/access/egress/queue-group/apply-groups-exclude
                    leaf-list apply-groups-exclude {
                        type leafref {
                            path "../../../../../../groups/group/name";
                        }
                        max-elements 8;
                        ordered-by user;
                        description "Exclude a configuration group at this level";
                    }

                    ///nokia-conf/configure/port/ethernet/access/egress/queue-group/aggregate-rate
                    container aggregate-rate {
                        description "Enter the aggregate-rate context";

                        ///nokia-conf/configure/port/ethernet/access/egress/queue-group/aggregate-rate/queue-frame-based-accounting
                        leaf queue-frame-based-accounting {
                            type boolean;
                            default "false";
                            description "Enable frame-based accounting on policers and queues";
                        }

                        ///nokia-conf/configure/port/ethernet/access/egress/queue-group/aggregate-rate/limit-unused-bandwidth
                        leaf limit-unused-bandwidth {
                            type boolean;
                            default "false";
                            description "Control unused bandwidth";
                        }

                        ///nokia-conf/configure/port/ethernet/access/egress/queue-group/aggregate-rate/rate
                        leaf rate {
                            type union {
                                type uint32 {
                                    range "1..3200000000";
                                }
                                type enumeration {
                                    enum max                            { value -1; }
                                }
                            }
                            units "kilobps";
                            default "max";
                            description "Aggregate rate for all queues";
                        }

                    } // container aggregate-rate

                    ///nokia-conf/configure/port/ethernet/access/egress/queue-group/host-match
                    container host-match {
                        description "Enter the host-match context";

                        ///nokia-conf/configure/port/ethernet/access/egress/queue-group/host-match/int-dest-id
                        list int-dest-id {
                            key "destination-string";
                            description "Add a list entry for int-dest-id";

                            ///nokia-conf/configure/port/ethernet/access/egress/queue-group/host-match/int-dest-id/destination-string
                            leaf destination-string {
                                type types-submgt:int-dest-id;
                                description "Host match destination ID";
                            }

                        } // list int-dest-id

                    } // container host-match

                    ///nokia-conf/configure/port/ethernet/access/egress/queue-group/queue-overrides
                    container queue-overrides {
                        description "Enter the queue-overrides context";

                        ///nokia-conf/configure/port/ethernet/access/egress/queue-group/queue-overrides/queue
                        list queue {
                            key "queue-id";
                            description "Enter the queue list instance";

                            ///nokia-conf/configure/port/ethernet/access/egress/queue-group/queue-overrides/queue/queue-id
                            leaf queue-id {
                                type leafref {
                                    path "../../../../../../../../qos/queue-group-templates/egress/queue-group[egress-queue-group-name=current()/../../../queue-group-name]/queue/queue-id";
                                }
                                description "Queue ID";
                            }

                            ///nokia-conf/configure/port/ethernet/access/egress/queue-group/queue-overrides/queue/cbs
                            leaf cbs {
                                type types-qos:burst-size-override;
                                units "kilobytes";
                                description "CBS for the template queue";
                            }

                            ///nokia-conf/configure/port/ethernet/access/egress/queue-group/queue-overrides/queue/mbs
                            leaf mbs {
                                type types-qos:queue-burst-size-override;
                                units "bytes";
                                description "MBS for the template queue";
                            }

                            ///nokia-conf/configure/port/ethernet/access/egress/queue-group/queue-overrides/queue/monitor-depth
                            leaf monitor-depth {
                                status obsolete;
                                type boolean;
                                default "false";
                                description "Enable queue depth monitoring";
                            }

                            ///nokia-conf/configure/port/ethernet/access/egress/queue-group/queue-overrides/queue/burst-limit
                            leaf burst-limit {
                                type types-qos:burst-limit-override;
                                description "Override for the shaping burst size for the queue";
                            }

                            ///nokia-conf/configure/port/ethernet/access/egress/queue-group/queue-overrides/queue/apply-groups
                            leaf-list apply-groups {
                                type leafref {
                                    path "../../../../../../../../groups/group/name";
                                }
                                max-elements 8;
                                ordered-by user;
                                description "Apply a configuration group at this level";
                            }

                            ///nokia-conf/configure/port/ethernet/access/egress/queue-group/queue-overrides/queue/apply-groups-exclude
                            leaf-list apply-groups-exclude {
                                type leafref {
                                    path "../../../../../../../../groups/group/name";
                                }
                                max-elements 8;
                                ordered-by user;
                                description "Exclude a configuration group at this level";
                            }

                            ///nokia-conf/configure/port/ethernet/access/egress/queue-group/queue-overrides/queue/queue-override-rate
                            choice queue-override-rate {
                                default "rate";
                                ///nokia-conf/configure/port/ethernet/access/egress/queue-group/queue-overrides/queue/queue-override-rate/percent-rate
                                case percent-rate {

                                    ///nokia-conf/configure/port/ethernet/access/egress/queue-group/queue-overrides/queue/queue-override-rate/percent-rate/percent-rate
                                    container percent-rate {
                                        description "Enter the percent-rate context";

                                        ///nokia-conf/configure/port/ethernet/access/egress/queue-group/queue-overrides/queue/queue-override-rate/percent-rate/percent-rate/cir
                                        leaf cir {
                                            type types-qos:cir-percent-override;
                                            units "percent";
                                            description "CIR for the queue";
                                        }

                                        ///nokia-conf/configure/port/ethernet/access/egress/queue-group/queue-overrides/queue/queue-override-rate/percent-rate/percent-rate/pir
                                        leaf pir {
                                            type types-qos:pir-percent-override;
                                            units "percent";
                                            description "PIR for the queue";
                                        }

                                    } // container percent-rate

                                }
                                ///nokia-conf/configure/port/ethernet/access/egress/queue-group/queue-overrides/queue/queue-override-rate/rate
                                case rate {

                                    ///nokia-conf/configure/port/ethernet/access/egress/queue-group/queue-overrides/queue/queue-override-rate/rate/rate
                                    container rate {
                                        description "Enter the rate context";

                                        ///nokia-conf/configure/port/ethernet/access/egress/queue-group/queue-overrides/queue/queue-override-rate/rate/rate/cir
                                        leaf cir {
                                            type types-qos:queue-cir-rate-override;
                                            units "kilobps";
                                            description "CIR for the queue";
                                        }

                                        ///nokia-conf/configure/port/ethernet/access/egress/queue-group/queue-overrides/queue/queue-override-rate/rate/rate/pir
                                        leaf pir {
                                            type types-qos:queue-pir-rate-override;
                                            units "kilobps";
                                            description "PIR for the queue";
                                        }

                                    } // container rate

                                }
                            }
                            ///nokia-conf/configure/port/ethernet/access/egress/queue-group/queue-overrides/queue/adaptation-rule
                            container adaptation-rule {
                                description "Enter the adaptation-rule context";

                                ///nokia-conf/configure/port/ethernet/access/egress/queue-group/queue-overrides/queue/adaptation-rule/cir
                                leaf cir {
                                    type types-qos:adaptation-rule-override;
                                    description "Constraint used when deriving the operational CIR value";
                                }

                                ///nokia-conf/configure/port/ethernet/access/egress/queue-group/queue-overrides/queue/adaptation-rule/pir
                                leaf pir {
                                    type types-qos:adaptation-rule-override;
                                    description "Constraint used when deriving the operational PIR value";
                                }

                            } // container adaptation-rule

                            ///nokia-conf/configure/port/ethernet/access/egress/queue-group/queue-overrides/queue/drop-tail
                            container drop-tail {
                                description "Enter the drop-tail context";

                                ///nokia-conf/configure/port/ethernet/access/egress/queue-group/queue-overrides/queue/drop-tail/low
                                container low {
                                    description "Enter the low context";

                                    ///nokia-conf/configure/port/ethernet/access/egress/queue-group/queue-overrides/queue/drop-tail/low/percent-reduction-from-mbs
                                    leaf percent-reduction-from-mbs {
                                        type types-qos:burst-percent-or-default-override;
                                        description "Percentage reduction from the MBS for a queue drop tail";
                                    }

                                } // container low

                            } // container drop-tail

                            ///nokia-conf/configure/port/ethernet/access/egress/queue-group/queue-overrides/queue/parent
                            container parent {
                                description "Enter the parent context";

                                ///nokia-conf/configure/port/ethernet/access/egress/queue-group/queue-overrides/queue/parent/cir-weight
                                leaf cir-weight {
                                    type types-qos:weight-override;
                                    description "CIR that overrides the parent for the queue group";
                                }

                                ///nokia-conf/configure/port/ethernet/access/egress/queue-group/queue-overrides/queue/parent/weight
                                leaf weight {
                                    type types-qos:weight-override;
                                    description "PIR that overrides the parent for the queue group";
                                }

                            } // container parent

                            ///nokia-conf/configure/port/ethernet/access/egress/queue-group/queue-overrides/queue/monitor-queue-depth
                            container monitor-queue-depth {
                                presence "Enable the monitor-queue-depth context";
                                description "Enable the monitor-queue-depth context";

                                ///nokia-conf/configure/port/ethernet/access/egress/queue-group/queue-overrides/queue/monitor-queue-depth/fast-polling
                                leaf fast-polling {
                                    type boolean;
                                    default "false";
                                    description "Enable fast polling of the queue depth";
                                }

                                ///nokia-conf/configure/port/ethernet/access/egress/queue-group/queue-overrides/queue/monitor-queue-depth/violation-threshold
                                leaf violation-threshold {
                                    type decimal64 {
                                        range "0.01..99.99";
                                        fraction-digits 2;
                                    }
                                    description "Threshold for queue depth before violation is raised";
                                }

                            } // container monitor-queue-depth

                        } // list queue

                    } // container queue-overrides

                    ///nokia-conf/configure/port/ethernet/access/egress/queue-group/scheduler-policy
                    container scheduler-policy {
                        description "Enter the scheduler-policy context";

                        ///nokia-conf/configure/port/ethernet/access/egress/queue-group/scheduler-policy/policy-name
                        leaf policy-name {
                            type leafref {
                                path "../../../../../../../qos/scheduler-policy/scheduler-policy-name";
                            }
                            description "Scheduler policy name";
                        }

                        ///nokia-conf/configure/port/ethernet/access/egress/queue-group/scheduler-policy/overrides
                        container overrides {
                            description "Enter the overrides context";

                            ///nokia-conf/configure/port/ethernet/access/egress/queue-group/scheduler-policy/overrides/scheduler
                            list scheduler {
                                key "scheduler-name";
                                description "Enter the scheduler list instance";

                                ///nokia-conf/configure/port/ethernet/access/egress/queue-group/scheduler-policy/overrides/scheduler/scheduler-name
                                leaf scheduler-name {
                                    type types-sros:named-item;
                                    description "Scheduler name";
                                }

                                ///nokia-conf/configure/port/ethernet/access/egress/queue-group/scheduler-policy/overrides/scheduler/apply-groups
                                leaf-list apply-groups {
                                    type leafref {
                                        path "../../../../../../../../../groups/group/name";
                                    }
                                    max-elements 8;
                                    ordered-by user;
                                    description "Apply a configuration group at this level";
                                }

                                ///nokia-conf/configure/port/ethernet/access/egress/queue-group/scheduler-policy/overrides/scheduler/apply-groups-exclude
                                leaf-list apply-groups-exclude {
                                    type leafref {
                                        path "../../../../../../../../../groups/group/name";
                                    }
                                    max-elements 8;
                                    ordered-by user;
                                    description "Exclude a configuration group at this level";
                                }

                                ///nokia-conf/configure/port/ethernet/access/egress/queue-group/scheduler-policy/overrides/scheduler/parent
                                container parent {
                                    description "Enter the parent context";

                                    ///nokia-conf/configure/port/ethernet/access/egress/queue-group/scheduler-policy/overrides/scheduler/parent/cir-weight
                                    leaf cir-weight {
                                        type types-qos:weight-override;
                                        description "CIR that overrides the parent";
                                    }

                                    ///nokia-conf/configure/port/ethernet/access/egress/queue-group/scheduler-policy/overrides/scheduler/parent/weight
                                    leaf weight {
                                        type types-qos:weight-override;
                                        description "PIR that overrides the parent";
                                    }

                                } // container parent

                                ///nokia-conf/configure/port/ethernet/access/egress/queue-group/scheduler-policy/overrides/scheduler/rate
                                container rate {
                                    description "Enter the rate context";

                                    ///nokia-conf/configure/port/ethernet/access/egress/queue-group/scheduler-policy/overrides/scheduler/rate/cir
                                    leaf cir {
                                        type types-qos:sched-cir-rate-ovr;
                                        units "kilobps";
                                        description "CIR for the scheduler";
                                    }

                                    ///nokia-conf/configure/port/ethernet/access/egress/queue-group/scheduler-policy/overrides/scheduler/rate/pir
                                    leaf pir {
                                        type types-qos:sched-pir-rate-ovr;
                                        units "kilobps";
                                        description "PIR for the scheduler";
                                    }

                                } // container rate

                            } // list scheduler

                        } // container overrides

                    } // container scheduler-policy

                } // list queue-group

                ///nokia-conf/configure/port/ethernet/access/egress/virtual-port
                list virtual-port {
                    key "vport-name";
                    description "Enter the virtual-port list instance";

                    ///nokia-conf/configure/port/ethernet/access/egress/virtual-port/vport-name
                    leaf vport-name {
                        type types-sros:named-item;
                        description "Vport scheduling node name";
                    }

                    ///nokia-conf/configure/port/ethernet/access/egress/virtual-port/description
                    leaf description {
                        type types-sros:description;
                        description "Text description";
                    }

                    ///nokia-conf/configure/port/ethernet/access/egress/virtual-port/monitor-port-scheduler
                    leaf monitor-port-scheduler {
                        type boolean;
                        default "false";
                        description "Enable congestion monitoring on egress port scheduler";
                    }

                    ///nokia-conf/configure/port/ethernet/access/egress/virtual-port/multicast-hqos-adjustment
                    leaf multicast-hqos-adjustment {
                        type boolean;
                        default "false";
                        description "Apply HQoS Adjustment (egress rate modification)";
                    }

                    ///nokia-conf/configure/port/ethernet/access/egress/virtual-port/port-scheduler-policy
                    leaf port-scheduler-policy {
                        type leafref {
                            path "../../../../../../qos/port-scheduler-policy/name";
                        }
                        description "Port scheduler policy name";
                    }

                    ///nokia-conf/configure/port/ethernet/access/egress/virtual-port/hw-agg-shaper-scheduler-policy
                    leaf hw-agg-shaper-scheduler-policy {
                        type leafref {
                            path "../../../../../../qos/hw-agg-shaper-scheduler-policy/name";
                        }
                        description "Hardware aggregate shaper scheduler policy to apply";
                    }

                    ///nokia-conf/configure/port/ethernet/access/egress/virtual-port/monitor-hw-agg-shaper-scheduler
                    leaf monitor-hw-agg-shaper-scheduler {
                        type boolean;
                        default "false";
                        description "Enable monitoring hardware aggregate shaper scheduler";
                    }

                    ///nokia-conf/configure/port/ethernet/access/egress/virtual-port/apply-groups
                    leaf-list apply-groups {
                        type leafref {
                            path "../../../../../../groups/group/name";
                        }
                        max-elements 8;
                        ordered-by user;
                        description "Apply a configuration group at this level";
                    }

                    ///nokia-conf/configure/port/ethernet/access/egress/virtual-port/apply-groups-exclude
                    leaf-list apply-groups-exclude {
                        type leafref {
                            path "../../../../../../groups/group/name";
                        }
                        max-elements 8;
                        ordered-by user;
                        description "Exclude a configuration group at this level";
                    }

                    ///nokia-conf/configure/port/ethernet/access/egress/virtual-port/aggregate-rate
                    container aggregate-rate {
                        description "Enter the aggregate-rate context";

                        ///nokia-conf/configure/port/ethernet/access/egress/virtual-port/aggregate-rate/limit-unused-bandwidth
                        leaf limit-unused-bandwidth {
                            type boolean;
                            default "false";
                            description "Control unused bandwidth";
                        }

                        ///nokia-conf/configure/port/ethernet/access/egress/virtual-port/aggregate-rate/rate
                        leaf rate {
                            type union {
                                type int64 {
                                    range "1..6400000000";
                                }
                                type enumeration {
                                    enum max                            { value -1; }
                                }
                            }
                            units "kilobps";
                            default "max";
                            description "Enforced aggregate rate for the queue";
                        }

                    } // container aggregate-rate

                    ///nokia-conf/configure/port/ethernet/access/egress/virtual-port/host-match
                    container host-match {
                        description "Enter the host-match context";

                        ///nokia-conf/configure/port/ethernet/access/egress/virtual-port/host-match/int-dest-id
                        list int-dest-id {
                            key "destination-string";
                            description "Add a list entry for int-dest-id";

                            ///nokia-conf/configure/port/ethernet/access/egress/virtual-port/host-match/int-dest-id/destination-string
                            leaf destination-string {
                                type types-submgt:int-dest-id;
                                description "Host match destination ID";
                            }

                        } // list int-dest-id

                    } // container host-match

                    ///nokia-conf/configure/port/ethernet/access/egress/virtual-port/scheduler-policy
                    container scheduler-policy {
                        description "Enter the scheduler-policy context";

                        ///nokia-conf/configure/port/ethernet/access/egress/virtual-port/scheduler-policy/policy-name
                        leaf policy-name {
                            type leafref {
                                path "../../../../../../../qos/scheduler-policy/scheduler-policy-name";
                            }
                            description "Egress scheduler policy";
                        }

                    } // container scheduler-policy

                    ///nokia-conf/configure/port/ethernet/access/egress/virtual-port/lag-per-link-hash
                    container lag-per-link-hash {
                        description "Enter the lag-per-link-hash context";

                        ///nokia-conf/configure/port/ethernet/access/egress/virtual-port/lag-per-link-hash/class
                        leaf class {
                            type types-services:sap-lag-per-link-hash-class;
                            default "1";
                            description "Class used on LAG egress using weighted per-link-hash";
                        }

                        ///nokia-conf/configure/port/ethernet/access/egress/virtual-port/lag-per-link-hash/weight
                        leaf weight {
                            type types-services:sap-lag-per-link-hash-weight;
                            default "1";
                            description "Weight used on LAG egress using weighted per-link-hash";
                        }

                    } // container lag-per-link-hash

                } // list virtual-port

            } // container egress

            ///nokia-conf/configure/port/ethernet/access/ingress
            container ingress {
                description "Enter the ingress context";

                ///nokia-conf/configure/port/ethernet/access/ingress/queue-group
                list queue-group {
                    key "queue-group-name";
                    description "Enter the queue-group list instance";

                    ///nokia-conf/configure/port/ethernet/access/ingress/queue-group/queue-group-name
                    leaf queue-group-name {
                        type leafref {
                            path "../../../../../../qos/queue-group-templates/ingress/queue-group/ingress-queue-group-name";
                        }
                        description "Queue group name";
                    }

                    ///nokia-conf/configure/port/ethernet/access/ingress/queue-group/accounting-policy
                    leaf accounting-policy {
                        type leafref {
                            path "../../../../../../log/accounting-policy/policy-id";
                        }
                        description "Accounting policy for the Ethernet port";
                    }

                    ///nokia-conf/configure/port/ethernet/access/ingress/queue-group/collect-stats
                    leaf collect-stats {
                        type boolean;
                        default "false";
                        description "Collect accounting and statistical data";
                    }

                    ///nokia-conf/configure/port/ethernet/access/ingress/queue-group/description
                    leaf description {
                        type types-sros:description;
                        description "Text description";
                    }

                    ///nokia-conf/configure/port/ethernet/access/ingress/queue-group/apply-groups
                    leaf-list apply-groups {
                        type leafref {
                            path "../../../../../../groups/group/name";
                        }
                        max-elements 8;
                        ordered-by user;
                        description "Apply a configuration group at this level";
                    }

                    ///nokia-conf/configure/port/ethernet/access/ingress/queue-group/apply-groups-exclude
                    leaf-list apply-groups-exclude {
                        type leafref {
                            path "../../../../../../groups/group/name";
                        }
                        max-elements 8;
                        ordered-by user;
                        description "Exclude a configuration group at this level";
                    }

                    ///nokia-conf/configure/port/ethernet/access/ingress/queue-group/queue-overrides
                    container queue-overrides {
                        description "Enter the queue-overrides context";

                        ///nokia-conf/configure/port/ethernet/access/ingress/queue-group/queue-overrides/queue
                        list queue {
                            key "queue-id";
                            description "Enter the queue list instance";

                            ///nokia-conf/configure/port/ethernet/access/ingress/queue-group/queue-overrides/queue/queue-id
                            leaf queue-id {
                                type leafref {
                                    path "../../../../../../../../qos/queue-group-templates/ingress/queue-group[ingress-queue-group-name=current()/../../../queue-group-name]/queue/queue-id";
                                }
                                description "Queue ID for the queue group template";
                            }

                            ///nokia-conf/configure/port/ethernet/access/ingress/queue-group/queue-overrides/queue/cbs
                            leaf cbs {
                                type types-qos:burst-size-override;
                                units "kilobytes";
                                description "CBS for the template queue";
                            }

                            ///nokia-conf/configure/port/ethernet/access/ingress/queue-group/queue-overrides/queue/mbs
                            leaf mbs {
                                type types-qos:queue-burst-size-override;
                                units "bytes";
                                description "MBS for the template queue";
                            }

                            ///nokia-conf/configure/port/ethernet/access/ingress/queue-group/queue-overrides/queue/monitor-depth
                            leaf monitor-depth {
                                status obsolete;
                                type boolean;
                                default "false";
                                description "Enable queue depth monitoring";
                            }

                            ///nokia-conf/configure/port/ethernet/access/ingress/queue-group/queue-overrides/queue/apply-groups
                            leaf-list apply-groups {
                                type leafref {
                                    path "../../../../../../../../groups/group/name";
                                }
                                max-elements 8;
                                ordered-by user;
                                description "Apply a configuration group at this level";
                            }

                            ///nokia-conf/configure/port/ethernet/access/ingress/queue-group/queue-overrides/queue/apply-groups-exclude
                            leaf-list apply-groups-exclude {
                                type leafref {
                                    path "../../../../../../../../groups/group/name";
                                }
                                max-elements 8;
                                ordered-by user;
                                description "Exclude a configuration group at this level";
                            }

                            ///nokia-conf/configure/port/ethernet/access/ingress/queue-group/queue-overrides/queue/adaptation-rule
                            container adaptation-rule {
                                description "Enter the adaptation-rule context";

                                ///nokia-conf/configure/port/ethernet/access/ingress/queue-group/queue-overrides/queue/adaptation-rule/cir
                                leaf cir {
                                    type types-qos:adaptation-rule-override;
                                    description "Constraint used when deriving the operational CIR value";
                                }

                                ///nokia-conf/configure/port/ethernet/access/ingress/queue-group/queue-overrides/queue/adaptation-rule/pir
                                leaf pir {
                                    type types-qos:adaptation-rule-override;
                                    description "Constraint used when deriving the operational PIR value";
                                }

                            } // container adaptation-rule

                            ///nokia-conf/configure/port/ethernet/access/ingress/queue-group/queue-overrides/queue/drop-tail
                            container drop-tail {
                                description "Enter the drop-tail context";

                                ///nokia-conf/configure/port/ethernet/access/ingress/queue-group/queue-overrides/queue/drop-tail/low
                                container low {
                                    description "Enter the low context";

                                    ///nokia-conf/configure/port/ethernet/access/ingress/queue-group/queue-overrides/queue/drop-tail/low/percent-reduction-from-mbs
                                    leaf percent-reduction-from-mbs {
                                        type types-qos:burst-percent-or-default-override;
                                        description "Percentage reduction from the MBS for a queue drop tail";
                                    }

                                } // container low

                            } // container drop-tail

                            ///nokia-conf/configure/port/ethernet/access/ingress/queue-group/queue-overrides/queue/rate
                            container rate {
                                description "Enter the rate context";

                                ///nokia-conf/configure/port/ethernet/access/ingress/queue-group/queue-overrides/queue/rate/cir
                                leaf cir {
                                    type types-qos:queue-cir-rate-override;
                                    units "kilobps";
                                    description "CIR for the queue";
                                }

                                ///nokia-conf/configure/port/ethernet/access/ingress/queue-group/queue-overrides/queue/rate/pir
                                leaf pir {
                                    type types-qos:queue-pir-rate-override;
                                    units "kilobps";
                                    description "PIR for the queue";
                                }

                            } // container rate

                            ///nokia-conf/configure/port/ethernet/access/ingress/queue-group/queue-overrides/queue/monitor-queue-depth
                            container monitor-queue-depth {
                                presence "Enable the monitor-queue-depth context";
                                description "Enable the monitor-queue-depth context";

                                ///nokia-conf/configure/port/ethernet/access/ingress/queue-group/queue-overrides/queue/monitor-queue-depth/fast-polling
                                leaf fast-polling {
                                    type boolean;
                                    default "false";
                                    description "Enable fast polling of the queue depth";
                                }

                            } // container monitor-queue-depth

                        } // list queue

                    } // container queue-overrides

                    ///nokia-conf/configure/port/ethernet/access/ingress/queue-group/scheduler-policy
                    container scheduler-policy {
                        description "Enter the scheduler-policy context";

                        ///nokia-conf/configure/port/ethernet/access/ingress/queue-group/scheduler-policy/policy-name
                        leaf policy-name {
                            type leafref {
                                path "../../../../../../../qos/scheduler-policy/scheduler-policy-name";
                            }
                            description "Scheduler policy name";
                        }

                        ///nokia-conf/configure/port/ethernet/access/ingress/queue-group/scheduler-policy/overrides
                        container overrides {
                            description "Enter the overrides context";

                            ///nokia-conf/configure/port/ethernet/access/ingress/queue-group/scheduler-policy/overrides/scheduler
                            list scheduler {
                                key "scheduler-name";
                                description "Enter the scheduler list instance";

                                ///nokia-conf/configure/port/ethernet/access/ingress/queue-group/scheduler-policy/overrides/scheduler/scheduler-name
                                leaf scheduler-name {
                                    type types-sros:named-item;
                                    description "Scheduler name";
                                }

                                ///nokia-conf/configure/port/ethernet/access/ingress/queue-group/scheduler-policy/overrides/scheduler/apply-groups
                                leaf-list apply-groups {
                                    type leafref {
                                        path "../../../../../../../../../groups/group/name";
                                    }
                                    max-elements 8;
                                    ordered-by user;
                                    description "Apply a configuration group at this level";
                                }

                                ///nokia-conf/configure/port/ethernet/access/ingress/queue-group/scheduler-policy/overrides/scheduler/apply-groups-exclude
                                leaf-list apply-groups-exclude {
                                    type leafref {
                                        path "../../../../../../../../../groups/group/name";
                                    }
                                    max-elements 8;
                                    ordered-by user;
                                    description "Exclude a configuration group at this level";
                                }

                                ///nokia-conf/configure/port/ethernet/access/ingress/queue-group/scheduler-policy/overrides/scheduler/parent
                                container parent {
                                    description "Enter the parent context";

                                    ///nokia-conf/configure/port/ethernet/access/ingress/queue-group/scheduler-policy/overrides/scheduler/parent/cir-weight
                                    leaf cir-weight {
                                        type types-qos:weight-override;
                                        description "CIR that overrides the parent";
                                    }

                                    ///nokia-conf/configure/port/ethernet/access/ingress/queue-group/scheduler-policy/overrides/scheduler/parent/weight
                                    leaf weight {
                                        type types-qos:weight-override;
                                        description "PIR that overrides the parent";
                                    }

                                } // container parent

                                ///nokia-conf/configure/port/ethernet/access/ingress/queue-group/scheduler-policy/overrides/scheduler/rate
                                container rate {
                                    description "Enter the rate context";

                                    ///nokia-conf/configure/port/ethernet/access/ingress/queue-group/scheduler-policy/overrides/scheduler/rate/cir
                                    leaf cir {
                                        type types-qos:sched-cir-rate-ovr;
                                        units "kilobps";
                                        description "CIR for the scheduler";
                                    }

                                    ///nokia-conf/configure/port/ethernet/access/ingress/queue-group/scheduler-policy/overrides/scheduler/rate/pir
                                    leaf pir {
                                        type types-qos:sched-pir-rate-ovr;
                                        units "kilobps";
                                        description "PIR for the scheduler";
                                    }

                                } // container rate

                            } // list scheduler

                        } // container overrides

                    } // container scheduler-policy

                } // list queue-group

            } // container ingress

        } // container access

    } // grouping conf-port-eth-access

}
