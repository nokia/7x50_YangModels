submodule nokia-state-router-wpp {

    yang-version "1.1";

    belongs-to nokia-state { prefix "state"; }

    import ietf-inet-types                { prefix "inet"; }
    import ietf-yang-types                { prefix "yang"; }
    import nokia-sros-yang-extensions     { prefix "sros-ext"; }
    import nokia-types-services           { prefix "types-services"; }
    import nokia-types-sros               { prefix "types-sros"; }

    sros-ext:sros-major-release "rel23";
    organization "Nokia";
    contact
        "Nokia SR OS Support
         Web: <http://www.nokia.com>";
    description
        "Nokia YANG Data model with operational state for wpp on SR OS based routers.

         Copyright 2016 Nokia. All rights reserved. Reproduction of this document
         is authorized on the condition that the foregoing copyright notice is included.

         This nokia-state-router-wpp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-10-04";

    grouping state-router-wpp {
        ///nokia-state/state/router/wpp
        container wpp {
            description "Enable the wpp context";

            ///nokia-state/state/router/wpp/portal
            list portal {
                key "name";
                description "Enter the portal list instance";

                ///nokia-state/state/router/wpp/portal/name
                leaf name {
                    type types-sros:named-item;
                    description "Web portal name";
                }

                ///nokia-state/state/router/wpp/portal/controlled-router
                leaf controlled-router {
                    type types-sros:router-instance;
                    description "The router controlled by this portal.";
                }

                ///nokia-state/state/router/wpp/portal/enabled-interfaces
                leaf enabled-interfaces {
                    type uint32;
                    description
                        "The number of interfaces that are associated with this portal
                         and adminstrative enabled.";
                }

                ///nokia-state/state/router/wpp/portal/triggered-hosts
                leaf triggered-hosts {
                    type boolean;
                    description "Indicates if triggered hosts are enabled or disabled on this portal.";
                }

                ///nokia-state/state/router/wpp/portal/statistics
                list statistics {
                    key "type id";
                    description "Enter the statistics list instance";

                    ///nokia-state/state/router/wpp/portal/statistics/type
                    leaf type {
                        type enumeration {
                            enum event                          { value 1; }
                            enum dropped                        { value 2; }
                            enum accepted                       { value 3; }
                            enum original-transmitted           { value 4; }
                            enum retransmitted                  { value 5; }
                            enum forwarded-to-peer              { value 6; }
                            enum received-from-peer             { value 7; }
                        }
                        description "Indicates the statistics type.";
                    }

                    ///nokia-state/state/router/wpp/portal/statistics/id
                    leaf id {
                        type uint32 {
                            range "0..40";
                        }
                        description "The counter id.";
                    }

                    ///nokia-state/state/router/wpp/portal/statistics/description
                    leaf description {
                        type types-sros:display-string {
                            length "1..64";
                        }
                        description "Describes the statistic.";
                    }

                    ///nokia-state/state/router/wpp/portal/statistics/value
                    leaf value {
                        type yang:counter32;
                        description "The value of the counter.";
                    }

                } // list statistics

                ///nokia-state/state/router/wpp/portal/host
                list host {
                    key "address";
                    description "Enter the host list instance";

                    ///nokia-state/state/router/wpp/portal/host/address
                    leaf address {
                        type types-sros:ipv4-unicast-address;
                        description "The address of the WPP host.";
                    }

                    ///nokia-state/state/router/wpp/portal/host/state
                    leaf state {
                        type enumeration {
                            enum idle                           { value 1; }
                            enum challenged                     { value 2; }
                            enum authenticating                 { value 3; }
                            enum authenticated                  { value 4; }
                            enum established                    { value 5; }
                            enum logging-out                    { value 6; }
                        }
                        description "The state of the WPP host.";
                    }

                    ///nokia-state/state/router/wpp/portal/host/serial-number
                    leaf serial-number {
                        type uint32 {
                            range "1..4294967295";
                        }
                        description "The serial number of the WPP host.";
                    }

                    ///nokia-state/state/router/wpp/portal/host/request-id
                    leaf request-id {
                        type uint32 {
                            range "1..4294967295";
                        }
                        description "The request-id of the WPP host.";
                    }

                    ///nokia-state/state/router/wpp/portal/host/remote-port
                    leaf remote-port {
                        type inet:port-number;
                        description "The UDP source port used by the portal while sending a message for this host.";
                    }

                    ///nokia-state/state/router/wpp/portal/host/local-address
                    leaf local-address {
                        type types-sros:ipv4-unicast-address;
                        description "The destination address used by the portal while sending a message for this host.";
                    }

                    ///nokia-state/state/router/wpp/portal/host/user-name
                    leaf user-name {
                        type types-sros:display-string;
                        description "The WPP user name of this WPP host.";
                    }

                    ///nokia-state/state/router/wpp/portal/host/service
                    leaf service {
                        type types-services:service-name;
                        description "The service to which the WPP host belongs.";
                    }

                    ///nokia-state/state/router/wpp/portal/host/mac-address
                    leaf mac-address {
                        type yang:mac-address;
                        description "The mac-address of the WPP host.";
                    }

                    ///nokia-state/state/router/wpp/portal/host/is-triggered
                    leaf is-triggered {
                        type boolean;
                        description "True if the creation of the host was triggered by the portal, false otherwise.";
                    }

                    ///nokia-state/state/router/wpp/portal/host/track-srrp-instance
                    leaf track-srrp-instance {
                        type uint32;
                        description
                            "The SRRP instance whose state is tracked by this WPP host to determine if
                             it is on the MCS master or backup node.";
                    }

                    ///nokia-state/state/router/wpp/portal/host/is-mcs-backup
                    leaf is-mcs-backup {
                        type boolean;
                        description "True if the WPP host is on the MCS backup node, false otherwise.";
                    }

                } // list host

                ///nokia-state/state/router/wpp/portal/session
                list session {
                    key "id";
                    description "Enter the session list instance";

                    ///nokia-state/state/router/wpp/portal/session/id
                    leaf id {
                        type uint32;
                        description "The unique identifier of this session.";
                    }

                    ///nokia-state/state/router/wpp/portal/session/state
                    leaf state {
                        type enumeration {
                            enum idle                           { value 1; }
                            enum challenged                     { value 2; }
                            enum authenticating                 { value 3; }
                            enum authenticated                  { value 4; }
                            enum established                    { value 5; }
                            enum logging-out                    { value 6; }
                        }
                        description "The state of the WPP session.";
                    }

                    ///nokia-state/state/router/wpp/portal/session/serial-number
                    leaf serial-number {
                        type uint32 {
                            range "1..4294967295";
                        }
                        description "The serial number of the WPP session.";
                    }

                    ///nokia-state/state/router/wpp/portal/session/request-id
                    leaf request-id {
                        type uint32 {
                            range "1..4294967295";
                        }
                        description "The request-id of the WPP session.";
                    }

                    ///nokia-state/state/router/wpp/portal/session/remote-port
                    leaf remote-port {
                        type inet:port-number;
                        description "The UDP source port used by the portal while sending a message for this session.";
                    }

                    ///nokia-state/state/router/wpp/portal/session/local-address
                    leaf local-address {
                        type types-sros:ipv4-unicast-address;
                        description "The destination address used by the portal while sending a message for this session.";
                    }

                    ///nokia-state/state/router/wpp/portal/session/user-name
                    leaf user-name {
                        type types-sros:display-string;
                        description "The WPP user name of this WPP session.";
                    }

                    ///nokia-state/state/router/wpp/portal/session/service
                    leaf service {
                        type types-services:service-name;
                        description "The service to which the WPP session belongs.";
                    }

                    ///nokia-state/state/router/wpp/portal/session/mac-address
                    leaf mac-address {
                        type yang:mac-address;
                        description "The mac-address of the WPP session.";
                    }

                    ///nokia-state/state/router/wpp/portal/session/is-triggered
                    leaf is-triggered {
                        type boolean;
                        description "True if the creation of the session was triggered by the portal, false otherwise.";
                    }

                    ///nokia-state/state/router/wpp/portal/session/track-srrp-instance
                    leaf track-srrp-instance {
                        type uint32;
                        description
                            "The SRRP instance whose state is tracked by this WPP session to determine if
                             it is on the MCS master or backup node.";
                    }

                    ///nokia-state/state/router/wpp/portal/session/is-mcs-backup
                    leaf is-mcs-backup {
                        type boolean;
                        description "True if the WPP session is on the MCS backup node, false otherwise.";
                    }

                    ///nokia-state/state/router/wpp/portal/session/client-address
                    leaf client-address {
                        type types-sros:ip-address;
                        description "The source address the client used to contact the WPP portal.";
                    }

                    ///nokia-state/state/router/wpp/portal/session/ipoe-session
                    container ipoe-session {
                        description "Enter the ipoe-session context";

                        ///nokia-state/state/router/wpp/portal/session/ipoe-session/sap-id
                        leaf sap-id {
                            type types-sros:sap;
                            description "Indicates the SAP used by this session.";
                        }

                        ///nokia-state/state/router/wpp/portal/session/ipoe-session/mac-address
                        leaf mac-address {
                            type yang:mac-address;
                            description "Indicates the MAC address of this session.";
                        }

                        ///nokia-state/state/router/wpp/portal/session/ipoe-session/remote-id
                        leaf remote-id {
                            type binary {
                                length "0..256";
                            }
                            description "Indicates the value of the remote-id sub-option.";
                        }

                        ///nokia-state/state/router/wpp/portal/session/ipoe-session/circuit-id
                        leaf circuit-id {
                            type binary {
                                length "0..256";
                            }
                            description "Indicates the value of the circuit-id sub-option.";
                        }

                    } // container ipoe-session

                } // list session

            } // list portal

            ///nokia-state/state/router/wpp/statistics
            list statistics {
                key "type id";
                description "Enter the statistics list instance";

                ///nokia-state/state/router/wpp/statistics/type
                leaf type {
                    type enumeration {
                        enum event                          { value 1; }
                        enum dropped                        { value 2; }
                        enum accepted                       { value 3; }
                        enum original-transmitted           { value 4; }
                        enum retransmitted                  { value 5; }
                        enum forwarded-to-peer              { value 6; }
                        enum received-from-peer             { value 7; }
                    }
                    description "Indicates the statistics type.";
                }

                ///nokia-state/state/router/wpp/statistics/id
                leaf id {
                    type uint32 {
                        range "0..40";
                    }
                    description "The counter id.";
                }

                ///nokia-state/state/router/wpp/statistics/description
                leaf description {
                    type types-sros:display-string {
                        length "1..64";
                    }
                    description "Describes the statistic.";
                }

                ///nokia-state/state/router/wpp/statistics/value
                leaf value {
                    type yang:counter32;
                    description "The value of the counter.";
                }

            } // list statistics

        } // container wpp

    } // grouping state-router-wpp

}
