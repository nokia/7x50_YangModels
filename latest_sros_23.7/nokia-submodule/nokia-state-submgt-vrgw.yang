submodule nokia-state-submgt-vrgw {

    yang-version "1.1";

    belongs-to nokia-state { prefix "state"; }

    import ietf-yang-types                { prefix "yang"; }
    import nokia-sros-yang-extensions     { prefix "sros-ext"; }
    import nokia-types-isa                { prefix "types-isa"; }
    import nokia-types-nat                { prefix "types-nat"; }
    import nokia-types-qos                { prefix "types-qos"; }
    import nokia-types-services           { prefix "types-services"; }
    import nokia-types-sros               { prefix "types-sros"; }
    import nokia-types-subscriber-mgmt    { prefix "types-submgt"; }

    sros-ext:sros-major-release "rel23";
    organization "Nokia";
    contact
        "Nokia SR OS Support
         Web: <http://www.nokia.com>";
    description
        "Nokia YANG Data model with operational state for subscriber management Virtual Residential Gateway on SR OS based routers.

         Copyright 2016 Nokia. All rights reserved. Reproduction of this document
         is authorized on the condition that the foregoing copyright notice is included.

         This nokia-state-submgt-vrgw YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-11-05";

    grouping state-submgt-vrgw {
        ///nokia-state/state/subscriber-mgmt/vrgw
        container vrgw {
            description "Enter the vrgw context";

            ///nokia-state/state/subscriber-mgmt/vrgw/brg
            list brg {
                key "id";
                description "Enter the brg list instance";

                ///nokia-state/state/subscriber-mgmt/vrgw/brg/id
                leaf id {
                    type types-sros:named-item-64;
                    description "The BRG identifier";
                }

                ///nokia-state/state/subscriber-mgmt/vrgw/brg/ip-address
                leaf ip-address {
                    type types-sros:ip-address;
                    description "The IP address of the BRG, as learned from radius-proxy or from the tunnel source";
                }

                ///nokia-state/state/subscriber-mgmt/vrgw/brg/state
                leaf state {
                    type enumeration {
                        enum initialized {
                            value 1;
                            description "The BRG is authenticated by the proxy but no devices have connected yet";
                        }
                        enum operational {
                            value 2;
                            description "The BRG is authenticated and devices are connected";
                        }
                        enum connectivity-verification {
                            value 3;
                            description "No dynamic devices are connected and the connectivity-verification is active to verify the BRG itself is still alive";
                        }
                        enum hold {
                            value 4;
                            description "No dynamic devices are connected and connectivity verification is either not active or failed. Upon expiry of the hold-timer the BRG will be removed.";
                        }
                    }
                    description "The BRG state";
                }

                ///nokia-state/state/subscriber-mgmt/vrgw/brg/connectivity-verification
                leaf connectivity-verification {
                    type boolean;
                    description "Indicates if periodic connectivity verification is done for this BRG while no dynamic sessions are active";
                }

                ///nokia-state/state/subscriber-mgmt/vrgw/brg/last-connectivity-verification
                leaf last-connectivity-verification {
                    type types-sros:date-time;
                    description "Indicates the time that the last connectivity verification test started";
                }

                ///nokia-state/state/subscriber-mgmt/vrgw/brg/proxy-authenticated
                leaf proxy-authenticated {
                    type boolean;
                    description "Whether the BRG was authenticated by a Radius proxy";
                }

                ///nokia-state/state/subscriber-mgmt/vrgw/brg/remaining-initial-hold-time
                leaf remaining-initial-hold-time {
                    type uint32;
                    description "The time interval until the initial hold timer expires";
                }

                ///nokia-state/state/subscriber-mgmt/vrgw/brg/remaining-hold-time
                leaf remaining-hold-time {
                    type uint32;
                    description "The time interval until the hold timer expires";
                }

                ///nokia-state/state/subscriber-mgmt/vrgw/brg/remaining-uplink-initial-hold-time
                leaf remaining-uplink-initial-hold-time {
                    type uint32;
                    description "The time interval until the uplink initial hold timer expires";
                }

                ///nokia-state/state/subscriber-mgmt/vrgw/brg/profile
                leaf profile {
                    type types-sros:named-item;
                    description "The BRG profile";
                }

                ///nokia-state/state/subscriber-mgmt/vrgw/brg/dmz-address
                leaf dmz-address {
                    type types-sros:ipv4-address;
                    description "The De-Militarized Zone (DMZ) address";
                }

                ///nokia-state/state/subscriber-mgmt/vrgw/brg/dmz-address-in-use
                leaf dmz-address-in-use {
                    type boolean;
                    description "Whether the DMZ address is currently in use";
                }

                ///nokia-state/state/subscriber-mgmt/vrgw/brg/home-pool
                container home-pool {
                    description "Enter the home-pool context";

                    ///nokia-state/state/subscriber-mgmt/vrgw/brg/home-pool/subnet
                    leaf subnet {
                        type types-sros:ipv4-unicast-prefix;
                        description "Subnet";
                    }

                    ///nokia-state/state/subscriber-mgmt/vrgw/brg/home-pool/gateway
                    leaf gateway {
                        type types-sros:ipv4-unicast-address;
                        description "Gateway";
                    }

                    ///nokia-state/state/subscriber-mgmt/vrgw/brg/home-pool/range
                    container range {
                        description "Enter the range context";

                        ///nokia-state/state/subscriber-mgmt/vrgw/brg/home-pool/range/start
                        leaf start {
                            type types-sros:ipv4-unicast-address;
                            description "Start address";
                        }

                        ///nokia-state/state/subscriber-mgmt/vrgw/brg/home-pool/range/end
                        leaf end {
                            type types-sros:ipv4-unicast-address;
                            description "End address";
                        }

                    } // container range

                    ///nokia-state/state/subscriber-mgmt/vrgw/brg/home-pool/standby
                    container standby {
                        description "Enter the standby context";

                        ///nokia-state/state/subscriber-mgmt/vrgw/brg/home-pool/standby/remaining-time
                        leaf remaining-time {
                            type uint32;
                            units "seconds";
                            description
                                "Remaining time after which the standby IPs expire and
                                 can be allocated to new connections";
                        }

                        ///nokia-state/state/subscriber-mgmt/vrgw/brg/home-pool/standby/ip
                        list ip {
                            key "ip-address";
                            description "Enter the ip list instance";

                            ///nokia-state/state/subscriber-mgmt/vrgw/brg/home-pool/standby/ip/ip-address
                            leaf ip-address {
                                type types-sros:ipv4-unicast-address;
                                description "IP address";
                            }

                        } // list ip

                    } // container standby

                    ///nokia-state/state/subscriber-mgmt/vrgw/brg/home-pool/binding
                    list binding {
                        key "mac-address";
                        description "Enter the binding list instance";

                        ///nokia-state/state/subscriber-mgmt/vrgw/brg/home-pool/binding/mac-address
                        leaf mac-address {
                            type types-sros:mac-unicast-address;
                            description "MAC address";
                        }

                        ///nokia-state/state/subscriber-mgmt/vrgw/brg/home-pool/binding/ip-address
                        leaf ip-address {
                            type types-sros:ipv4-unicast-address;
                            description "IP address";
                        }

                        ///nokia-state/state/subscriber-mgmt/vrgw/brg/home-pool/binding/allocation-type
                        leaf allocation-type {
                            type enumeration {
                                enum dynamic {
                                    value 1;
                                    description "A non-sticky device is using the binding";
                                }
                                enum static {
                                    value 2;
                                    description "Reserved static binding";
                                }
                                enum sticky {
                                    value 3;
                                    description "Reserved sticky binding";
                                }
                                enum offered {
                                    value 4;
                                    description "The binding has been sent in a DHCP OFFER";
                                }
                            }
                            description "Indicates what type of binding this is";
                        }

                        ///nokia-state/state/subscriber-mgmt/vrgw/brg/home-pool/binding/remaining-lease-time
                        leaf remaining-lease-time {
                            type uint32;
                            units "seconds";
                            description "Remaining lease time for a DHCP binding.";
                        }

                        ///nokia-state/state/subscriber-mgmt/vrgw/brg/home-pool/binding/session
                        container session {
                            description "Enter the session context";

                            ///nokia-state/state/subscriber-mgmt/vrgw/brg/home-pool/binding/session/sla-profile-instance
                            leaf sla-profile-instance {
                                type types-submgt:sla-profile-instance-id;
                                description "SLA profile instance identifier";
                            }

                            ///nokia-state/state/subscriber-mgmt/vrgw/brg/home-pool/binding/session/type
                            leaf type {
                                type types-submgt:session-type;
                                description "Session type";
                            }

                            ///nokia-state/state/subscriber-mgmt/vrgw/brg/home-pool/binding/session/id
                            leaf id {
                                type types-submgt:session-id;
                                description "Session identifier";
                            }

                        } // container session

                    } // list binding

                } // container home-pool

                ///nokia-state/state/subscriber-mgmt/vrgw/brg/public-static-device
                list public-static-device {
                    key "mac-address";
                    description "Enter the public-static-device list instance";

                    ///nokia-state/state/subscriber-mgmt/vrgw/brg/public-static-device/mac-address
                    leaf mac-address {
                        type types-sros:mac-unicast-address;
                        description "MAC address";
                    }

                    ///nokia-state/state/subscriber-mgmt/vrgw/brg/public-static-device/ip-address
                    leaf ip-address {
                        type types-sros:ipv4-unicast-address;
                        description "IP address";
                    }

                    ///nokia-state/state/subscriber-mgmt/vrgw/brg/public-static-device/session
                    container session {
                        description "Enter the session context";

                        ///nokia-state/state/subscriber-mgmt/vrgw/brg/public-static-device/session/sla-profile-instance
                        leaf sla-profile-instance {
                            type types-submgt:sla-profile-instance-id;
                            description "SLA profile instance identifier";
                        }

                        ///nokia-state/state/subscriber-mgmt/vrgw/brg/public-static-device/session/type
                        leaf type {
                            type types-submgt:session-type;
                            description "Session type";
                        }

                        ///nokia-state/state/subscriber-mgmt/vrgw/brg/public-static-device/session/id
                        leaf id {
                            type types-submgt:session-id;
                            description "Session identifier";
                        }

                    } // container session

                } // list public-static-device

                ///nokia-state/state/subscriber-mgmt/vrgw/brg/subscriber-parameters
                container subscriber-parameters {
                    description "Enter the subscriber-parameters context";

                    ///nokia-state/state/subscriber-mgmt/vrgw/brg/subscriber-parameters/router-advertisement-policy
                    leaf router-advertisement-policy {
                        type types-sros:named-item;
                        description "The router advertisement policy";
                    }

                    ///nokia-state/state/subscriber-mgmt/vrgw/brg/subscriber-parameters/sub-profile
                    leaf sub-profile {
                        type types-sros:named-item;
                        description "The subscriber profile string";
                    }

                    ///nokia-state/state/subscriber-mgmt/vrgw/brg/subscriber-parameters/sla-profile
                    leaf sla-profile {
                        type types-sros:named-item;
                        description "The SLA profile string";
                    }

                    ///nokia-state/state/subscriber-mgmt/vrgw/brg/subscriber-parameters/per-host-port-range-size
                    leaf per-host-port-range-size {
                        type uint32;
                        description "The outside port block size for each NAT host";
                    }

                    ///nokia-state/state/subscriber-mgmt/vrgw/brg/subscriber-parameters/upnp-policy
                    leaf upnp-policy {
                        type types-sros:named-item;
                        description "The UPnP policy";
                    }

                    ///nokia-state/state/subscriber-mgmt/vrgw/brg/subscriber-parameters/ipv4
                    container ipv4 {
                        description "Enter the ipv4 context";

                        ///nokia-state/state/subscriber-mgmt/vrgw/brg/subscriber-parameters/ipv4/dns
                        leaf-list dns {
                            type types-sros:ipv4-address;
                            description "The IPv4 Domain Name Servers";
                        }

                        ///nokia-state/state/subscriber-mgmt/vrgw/brg/subscriber-parameters/ipv4/nbns
                        leaf-list nbns {
                            type types-sros:ipv4-address;
                            description "The IPv4 NetBios Name Servers";
                        }

                        ///nokia-state/state/subscriber-mgmt/vrgw/brg/subscriber-parameters/ipv4/lease-time
                        leaf lease-time {
                            type uint32;
                            units "seconds";
                            description "The lease time of the hosts";
                        }

                    } // container ipv4

                    ///nokia-state/state/subscriber-mgmt/vrgw/brg/subscriber-parameters/ipv6
                    container ipv6 {
                        description "Enter the ipv6 context";

                        ///nokia-state/state/subscriber-mgmt/vrgw/brg/subscriber-parameters/ipv6/slaac-prefix
                        leaf slaac-prefix {
                            type types-sros:ipv6-prefix;
                            description "The SLAAC prefix";
                        }

                        ///nokia-state/state/subscriber-mgmt/vrgw/brg/subscriber-parameters/ipv6/slaac-prefix-valid
                        leaf slaac-prefix-valid {
                            type boolean;
                            description "In case SLAAC is learned from the uplink (e.g. PPPoE), indicates the slaac-prefix can be used to setup new hosts or renew existing hosts";
                        }

                        ///nokia-state/state/subscriber-mgmt/vrgw/brg/subscriber-parameters/ipv6/slaac-pool
                        leaf slaac-pool {
                            type types-sros:named-item;
                            description "The SLAAC pool used for local address assignment";
                        }

                        ///nokia-state/state/subscriber-mgmt/vrgw/brg/subscriber-parameters/ipv6/dns
                        leaf-list dns {
                            type types-sros:ipv6-address;
                            description "The IPv6 Domain Name Servers";
                        }

                    } // container ipv6

                    ///nokia-state/state/subscriber-mgmt/vrgw/brg/subscriber-parameters/value-added-service
                    container value-added-service {
                        description "Enter the value-added-service context";

                        ///nokia-state/state/subscriber-mgmt/vrgw/brg/subscriber-parameters/value-added-service/ipv4-filter
                        leaf ipv4-filter {
                            type types-sros:named-item;
                            description "The value added service IPv4 filter";
                        }

                    } // container value-added-service

                    ///nokia-state/state/subscriber-mgmt/vrgw/brg/subscriber-parameters/application-assurance
                    container application-assurance {
                        description "Enter the application-assurance context";

                        ///nokia-state/state/subscriber-mgmt/vrgw/brg/subscriber-parameters/application-assurance/profile
                        leaf profile {
                            type types-sros:named-item;
                            description "The Application Assurance profile";
                        }

                        ///nokia-state/state/subscriber-mgmt/vrgw/brg/subscriber-parameters/application-assurance/scope
                        leaf scope {
                            type enumeration {
                                enum subscriber {
                                    value 1;
                                    description "One Application Assurance subscriber per home";
                                }
                                enum device {
                                    value 2;
                                    description "One Application Assurance subscriber per device in the home";
                                }
                            }
                            description "The scope of the Application Assurance subscriber";
                        }

                    } // container application-assurance

                    ///nokia-state/state/subscriber-mgmt/vrgw/brg/subscriber-parameters/ingress
                    container ingress {
                        description "Enter the ingress context";

                        ///nokia-state/state/subscriber-mgmt/vrgw/brg/subscriber-parameters/ingress/filter
                        container filter {
                            description "Enter the filter context";

                            ///nokia-state/state/subscriber-mgmt/vrgw/brg/subscriber-parameters/ingress/filter/overrides
                            container overrides {
                                description "Enter the overrides context";

                                ///nokia-state/state/subscriber-mgmt/vrgw/brg/subscriber-parameters/ingress/filter/overrides/ipv4
                                container ipv4 {
                                    description "Enter the ipv4 context";

                                    ///nokia-state/state/subscriber-mgmt/vrgw/brg/subscriber-parameters/ingress/filter/overrides/ipv4/filter
                                    leaf filter {
                                        type types-submgt:overrule-filter-name;
                                        description "The ingress IPv4 filter";
                                    }

                                    ///nokia-state/state/subscriber-mgmt/vrgw/brg/subscriber-parameters/ingress/filter/overrides/ipv4/http-redirect-url
                                    leaf http-redirect-url {
                                        type types-sros:http-redirect-url;
                                        description "The URL of the IPv4 web portal";
                                    }

                                } // container ipv4

                                ///nokia-state/state/subscriber-mgmt/vrgw/brg/subscriber-parameters/ingress/filter/overrides/ipv6
                                container ipv6 {
                                    description "Enter the ipv6 context";

                                    ///nokia-state/state/subscriber-mgmt/vrgw/brg/subscriber-parameters/ingress/filter/overrides/ipv6/filter
                                    leaf filter {
                                        type types-submgt:overrule-filter-name;
                                        description "The ingress IPv6 filter";
                                    }

                                    ///nokia-state/state/subscriber-mgmt/vrgw/brg/subscriber-parameters/ingress/filter/overrides/ipv6/http-redirect-url
                                    leaf http-redirect-url {
                                        type types-sros:http-redirect-url;
                                        description "The URL of the IPv6 web portal";
                                    }

                                } // container ipv6

                            } // container overrides

                            ///nokia-state/state/subscriber-mgmt/vrgw/brg/subscriber-parameters/ingress/filter/shared-rule
                            list shared-rule {
                                key "index";
                                description "Enter the shared-rule list instance";

                                ///nokia-state/state/subscriber-mgmt/vrgw/brg/subscriber-parameters/ingress/filter/shared-rule/index
                                leaf index {
                                    type uint32;
                                    description "A BRG filter rule index.";
                                }

                                ///nokia-state/state/subscriber-mgmt/vrgw/brg/subscriber-parameters/ingress/filter/shared-rule/action
                                leaf action {
                                    type enumeration {
                                        enum forward                        { value 1; }
                                        enum drop                           { value 2; }
                                    }
                                    description "Action taken.";
                                }

                                ///nokia-state/state/subscriber-mgmt/vrgw/brg/subscriber-parameters/ingress/filter/shared-rule/match
                                container match {
                                    description "Enter the match context";

                                    ///nokia-state/state/subscriber-mgmt/vrgw/brg/subscriber-parameters/ingress/filter/shared-rule/match/protocol-next-header
                                    leaf protocol-next-header {
                                        type types-submgt:match-protocol-next-header;
                                        description "IPv4 protocol or IPv6 next-header";
                                    }

                                    ///nokia-state/state/subscriber-mgmt/vrgw/brg/subscriber-parameters/ingress/filter/shared-rule/match/fragment
                                    leaf fragment {
                                        type boolean;
                                        description "Indicates if this filter applies to fragmented or unfragmented packets only";
                                    }

                                    ///nokia-state/state/subscriber-mgmt/vrgw/brg/subscriber-parameters/ingress/filter/shared-rule/match/src-ip
                                    container src-ip {
                                        description "Enter the src-ip context";

                                        ///nokia-state/state/subscriber-mgmt/vrgw/brg/subscriber-parameters/ingress/filter/shared-rule/match/src-ip/address
                                        leaf address {
                                            type types-sros:ip-prefix-with-host-bits;
                                            description "Source IP address and mask";
                                        }

                                    } // container src-ip

                                    ///nokia-state/state/subscriber-mgmt/vrgw/brg/subscriber-parameters/ingress/filter/shared-rule/match/src-port
                                    container src-port {
                                        description "Enter the src-port context";

                                        ///nokia-state/state/subscriber-mgmt/vrgw/brg/subscriber-parameters/ingress/filter/shared-rule/match/src-port/range
                                        container range {
                                            description "Enter the range context";

                                            ///nokia-state/state/subscriber-mgmt/vrgw/brg/subscriber-parameters/ingress/filter/shared-rule/match/src-port/range/start
                                            leaf start {
                                                type types-sros:tcp-udp-port;
                                                description "Lower bound of source port range";
                                            }

                                            ///nokia-state/state/subscriber-mgmt/vrgw/brg/subscriber-parameters/ingress/filter/shared-rule/match/src-port/range/end
                                            leaf end {
                                                type types-sros:tcp-udp-port;
                                                description "Upper bound of source port range";
                                            }

                                        } // container range

                                    } // container src-port

                                    ///nokia-state/state/subscriber-mgmt/vrgw/brg/subscriber-parameters/ingress/filter/shared-rule/match/dst-ip
                                    container dst-ip {
                                        description "Enter the dst-ip context";

                                        ///nokia-state/state/subscriber-mgmt/vrgw/brg/subscriber-parameters/ingress/filter/shared-rule/match/dst-ip/address
                                        leaf address {
                                            type types-sros:ip-prefix-with-host-bits;
                                            description "Destination IP address and mask";
                                        }

                                    } // container dst-ip

                                    ///nokia-state/state/subscriber-mgmt/vrgw/brg/subscriber-parameters/ingress/filter/shared-rule/match/dst-port
                                    container dst-port {
                                        description "Enter the dst-port context";

                                        ///nokia-state/state/subscriber-mgmt/vrgw/brg/subscriber-parameters/ingress/filter/shared-rule/match/dst-port/range
                                        container range {
                                            description "Enter the range context";

                                            ///nokia-state/state/subscriber-mgmt/vrgw/brg/subscriber-parameters/ingress/filter/shared-rule/match/dst-port/range/start
                                            leaf start {
                                                type types-sros:tcp-udp-port;
                                                description "Lower bound of destination port range";
                                            }

                                            ///nokia-state/state/subscriber-mgmt/vrgw/brg/subscriber-parameters/ingress/filter/shared-rule/match/dst-port/range/end
                                            leaf end {
                                                type types-sros:tcp-udp-port;
                                                description "Upper bound of destination port range";
                                            }

                                        } // container range

                                    } // container dst-port

                                    ///nokia-state/state/subscriber-mgmt/vrgw/brg/subscriber-parameters/ingress/filter/shared-rule/match/ip-option
                                    container ip-option {
                                        description "Enter the ip-option context";

                                        ///nokia-state/state/subscriber-mgmt/vrgw/brg/subscriber-parameters/ingress/filter/shared-rule/match/ip-option/type
                                        leaf type {
                                            type types-sros:ip-option;
                                            description "Indicates ";
                                        }

                                    } // container ip-option

                                    ///nokia-state/state/subscriber-mgmt/vrgw/brg/subscriber-parameters/ingress/filter/shared-rule/match/tcp-flags
                                    container tcp-flags {
                                        description "Enter the tcp-flags context";

                                        ///nokia-state/state/subscriber-mgmt/vrgw/brg/subscriber-parameters/ingress/filter/shared-rule/match/tcp-flags/ack
                                        leaf ack {
                                            type boolean;
                                            description "Indicates if the control bits of the TCP header must contain the ACK bit";
                                        }

                                        ///nokia-state/state/subscriber-mgmt/vrgw/brg/subscriber-parameters/ingress/filter/shared-rule/match/tcp-flags/syn
                                        leaf syn {
                                            type boolean;
                                            description "Indicates ";
                                        }

                                    } // container tcp-flags

                                    ///nokia-state/state/subscriber-mgmt/vrgw/brg/subscriber-parameters/ingress/filter/shared-rule/match/icmp
                                    container icmp {
                                        description "Enter the icmp context";

                                        ///nokia-state/state/subscriber-mgmt/vrgw/brg/subscriber-parameters/ingress/filter/shared-rule/match/icmp/type
                                        leaf type {
                                            type types-submgt:match-icmp-type;
                                            description "Indicates the ICMP type to be matched";
                                        }

                                    } // container icmp

                                } // container match

                            } // list shared-rule

                            ///nokia-state/state/subscriber-mgmt/vrgw/brg/subscriber-parameters/ingress/filter/host-specific-rule
                            list host-specific-rule {
                                key "index";
                                description "Enter the host-specific-rule list instance";

                                ///nokia-state/state/subscriber-mgmt/vrgw/brg/subscriber-parameters/ingress/filter/host-specific-rule/index
                                leaf index {
                                    type uint32;
                                    description "A BRG filter rule index.";
                                }

                                ///nokia-state/state/subscriber-mgmt/vrgw/brg/subscriber-parameters/ingress/filter/host-specific-rule/action
                                leaf action {
                                    type enumeration {
                                        enum forward                        { value 1; }
                                        enum drop                           { value 2; }
                                    }
                                    description "Action taken.";
                                }

                                ///nokia-state/state/subscriber-mgmt/vrgw/brg/subscriber-parameters/ingress/filter/host-specific-rule/match
                                container match {
                                    description "Enter the match context";

                                    ///nokia-state/state/subscriber-mgmt/vrgw/brg/subscriber-parameters/ingress/filter/host-specific-rule/match/protocol-next-header
                                    leaf protocol-next-header {
                                        type types-submgt:match-protocol-next-header;
                                        description "IPv4 protocol or IPv6 next-header";
                                    }

                                    ///nokia-state/state/subscriber-mgmt/vrgw/brg/subscriber-parameters/ingress/filter/host-specific-rule/match/fragment
                                    leaf fragment {
                                        type boolean;
                                        description "Indicates if this filter applies to fragmented or unfragmented packets only";
                                    }

                                    ///nokia-state/state/subscriber-mgmt/vrgw/brg/subscriber-parameters/ingress/filter/host-specific-rule/match/src-port
                                    container src-port {
                                        description "Enter the src-port context";

                                        ///nokia-state/state/subscriber-mgmt/vrgw/brg/subscriber-parameters/ingress/filter/host-specific-rule/match/src-port/range
                                        container range {
                                            description "Enter the range context";

                                            ///nokia-state/state/subscriber-mgmt/vrgw/brg/subscriber-parameters/ingress/filter/host-specific-rule/match/src-port/range/start
                                            leaf start {
                                                type types-sros:tcp-udp-port;
                                                description "Lower bound of source port range";
                                            }

                                            ///nokia-state/state/subscriber-mgmt/vrgw/brg/subscriber-parameters/ingress/filter/host-specific-rule/match/src-port/range/end
                                            leaf end {
                                                type types-sros:tcp-udp-port;
                                                description "Upper bound of source port range";
                                            }

                                        } // container range

                                    } // container src-port

                                    ///nokia-state/state/subscriber-mgmt/vrgw/brg/subscriber-parameters/ingress/filter/host-specific-rule/match/dst-ip
                                    container dst-ip {
                                        description "Enter the dst-ip context";

                                        ///nokia-state/state/subscriber-mgmt/vrgw/brg/subscriber-parameters/ingress/filter/host-specific-rule/match/dst-ip/address
                                        leaf address {
                                            type types-sros:ip-prefix-with-host-bits;
                                            description "Destination IP address and mask";
                                        }

                                    } // container dst-ip

                                    ///nokia-state/state/subscriber-mgmt/vrgw/brg/subscriber-parameters/ingress/filter/host-specific-rule/match/dst-port
                                    container dst-port {
                                        description "Enter the dst-port context";

                                        ///nokia-state/state/subscriber-mgmt/vrgw/brg/subscriber-parameters/ingress/filter/host-specific-rule/match/dst-port/range
                                        container range {
                                            description "Enter the range context";

                                            ///nokia-state/state/subscriber-mgmt/vrgw/brg/subscriber-parameters/ingress/filter/host-specific-rule/match/dst-port/range/start
                                            leaf start {
                                                type types-sros:tcp-udp-port;
                                                description "Lower bound of destination port range";
                                            }

                                            ///nokia-state/state/subscriber-mgmt/vrgw/brg/subscriber-parameters/ingress/filter/host-specific-rule/match/dst-port/range/end
                                            leaf end {
                                                type types-sros:tcp-udp-port;
                                                description "Upper bound of destination port range";
                                            }

                                        } // container range

                                    } // container dst-port

                                    ///nokia-state/state/subscriber-mgmt/vrgw/brg/subscriber-parameters/ingress/filter/host-specific-rule/match/ip-option
                                    container ip-option {
                                        description "Enter the ip-option context";

                                        ///nokia-state/state/subscriber-mgmt/vrgw/brg/subscriber-parameters/ingress/filter/host-specific-rule/match/ip-option/type
                                        leaf type {
                                            type types-sros:ip-option;
                                            description "Indicates ";
                                        }

                                    } // container ip-option

                                    ///nokia-state/state/subscriber-mgmt/vrgw/brg/subscriber-parameters/ingress/filter/host-specific-rule/match/tcp-flags
                                    container tcp-flags {
                                        description "Enter the tcp-flags context";

                                        ///nokia-state/state/subscriber-mgmt/vrgw/brg/subscriber-parameters/ingress/filter/host-specific-rule/match/tcp-flags/ack
                                        leaf ack {
                                            type boolean;
                                            description "Indicates if the control bits of the TCP header must contain the ACK bit";
                                        }

                                        ///nokia-state/state/subscriber-mgmt/vrgw/brg/subscriber-parameters/ingress/filter/host-specific-rule/match/tcp-flags/syn
                                        leaf syn {
                                            type boolean;
                                            description "Indicates ";
                                        }

                                    } // container tcp-flags

                                    ///nokia-state/state/subscriber-mgmt/vrgw/brg/subscriber-parameters/ingress/filter/host-specific-rule/match/icmp
                                    container icmp {
                                        description "Enter the icmp context";

                                        ///nokia-state/state/subscriber-mgmt/vrgw/brg/subscriber-parameters/ingress/filter/host-specific-rule/match/icmp/type
                                        leaf type {
                                            type types-submgt:match-icmp-type;
                                            description "Indicates the ICMP type to be matched";
                                        }

                                    } // container icmp

                                } // container match

                            } // list host-specific-rule

                        } // container filter

                        ///nokia-state/state/subscriber-mgmt/vrgw/brg/subscriber-parameters/ingress/qos
                        container qos {
                            description "Enter the qos context";

                            ///nokia-state/state/subscriber-mgmt/vrgw/brg/subscriber-parameters/ingress/qos/overrides
                            container overrides {
                                description "Enter the overrides context";

                                ///nokia-state/state/subscriber-mgmt/vrgw/brg/subscriber-parameters/ingress/qos/overrides/arbiter
                                list arbiter {
                                    key "arbiter-name";
                                    description "Enter the arbiter list instance";

                                    ///nokia-state/state/subscriber-mgmt/vrgw/brg/subscriber-parameters/ingress/qos/overrides/arbiter/arbiter-name
                                    leaf arbiter-name {
                                        type types-sros:named-item;
                                        description "Name of overridden arbiter";
                                    }

                                    ///nokia-state/state/subscriber-mgmt/vrgw/brg/subscriber-parameters/ingress/qos/overrides/arbiter/pir
                                    leaf pir {
                                        type types-qos:policer-pir-rate-override;
                                        units "kilobps";
                                        description "PIR rate";
                                    }

                                } // list arbiter

                                ///nokia-state/state/subscriber-mgmt/vrgw/brg/subscriber-parameters/ingress/qos/overrides/policer
                                list policer {
                                    key "policer-id";
                                    description "Enter the policer list instance";

                                    ///nokia-state/state/subscriber-mgmt/vrgw/brg/subscriber-parameters/ingress/qos/overrides/policer/policer-id
                                    leaf policer-id {
                                        type types-qos:ingress-policer-id;
                                        description "The unique identifier for the policer.";
                                    }

                                    ///nokia-state/state/subscriber-mgmt/vrgw/brg/subscriber-parameters/ingress/qos/overrides/policer/pir
                                    leaf pir {
                                        type types-qos:policer-pir-rate-override;
                                        units "kilobps";
                                        description "PIR rate";
                                    }

                                    ///nokia-state/state/subscriber-mgmt/vrgw/brg/subscriber-parameters/ingress/qos/overrides/policer/cir
                                    leaf cir {
                                        type types-qos:policer-cir-rate-override;
                                        units "kilobps";
                                        description "CIR rate";
                                    }

                                    ///nokia-state/state/subscriber-mgmt/vrgw/brg/subscriber-parameters/ingress/qos/overrides/policer/mbs
                                    leaf mbs {
                                        type types-qos:policer-burst-size-override-max;
                                        units "bytes";
                                        description "The maximum reserved buffer space";
                                    }

                                    ///nokia-state/state/subscriber-mgmt/vrgw/brg/subscriber-parameters/ingress/qos/overrides/policer/cbs
                                    leaf cbs {
                                        type types-qos:policer-burst-size-override-max;
                                        units "bytes";
                                        description "The committed buffer size";
                                    }

                                } // list policer

                                ///nokia-state/state/subscriber-mgmt/vrgw/brg/subscriber-parameters/ingress/qos/overrides/queue
                                list queue {
                                    key "queue-id";
                                    description "Enter the queue list instance";

                                    ///nokia-state/state/subscriber-mgmt/vrgw/brg/subscriber-parameters/ingress/qos/overrides/queue/queue-id
                                    leaf queue-id {
                                        type types-qos:ingress-queue-id;
                                        description "The unique identifier for the queue.";
                                    }

                                    ///nokia-state/state/subscriber-mgmt/vrgw/brg/subscriber-parameters/ingress/qos/overrides/queue/pir
                                    leaf pir {
                                        type types-qos:queue-pir-rate-override;
                                        units "kilobps";
                                        description "PIR rate";
                                    }

                                    ///nokia-state/state/subscriber-mgmt/vrgw/brg/subscriber-parameters/ingress/qos/overrides/queue/cir
                                    leaf cir {
                                        type types-qos:queue-cir-rate-override;
                                        units "kilobps";
                                        description "CIR rate";
                                    }

                                    ///nokia-state/state/subscriber-mgmt/vrgw/brg/subscriber-parameters/ingress/qos/overrides/queue/mbs
                                    leaf mbs {
                                        type types-qos:queue-burst-size-override;
                                        units "bytes";
                                        description "The maximum reserved buffer space";
                                    }

                                    ///nokia-state/state/subscriber-mgmt/vrgw/brg/subscriber-parameters/ingress/qos/overrides/queue/cbs
                                    leaf cbs {
                                        type types-qos:queue-burst-size-override;
                                        units "bytes";
                                        description "The committed buffer size";
                                    }

                                } // list queue

                                ///nokia-state/state/subscriber-mgmt/vrgw/brg/subscriber-parameters/ingress/qos/overrides/scheduler
                                list scheduler {
                                    key "scheduler-name";
                                    description "Enter the scheduler list instance";

                                    ///nokia-state/state/subscriber-mgmt/vrgw/brg/subscriber-parameters/ingress/qos/overrides/scheduler/scheduler-name
                                    leaf scheduler-name {
                                        type types-sros:named-item;
                                        description "Name of overridden scheduler";
                                    }

                                    ///nokia-state/state/subscriber-mgmt/vrgw/brg/subscriber-parameters/ingress/qos/overrides/scheduler/pir
                                    leaf pir {
                                        type types-qos:scheduler-cir-rate;
                                        units "kilobps";
                                        description "PIR rate";
                                    }

                                    ///nokia-state/state/subscriber-mgmt/vrgw/brg/subscriber-parameters/ingress/qos/overrides/scheduler/cir
                                    leaf cir {
                                        type types-qos:scheduler-cir-rate-override;
                                        units "kilobps";
                                        description "CIR rate";
                                    }

                                } // list scheduler

                            } // container overrides

                        } // container qos

                    } // container ingress

                    ///nokia-state/state/subscriber-mgmt/vrgw/brg/subscriber-parameters/egress
                    container egress {
                        description "Enter the egress context";

                        ///nokia-state/state/subscriber-mgmt/vrgw/brg/subscriber-parameters/egress/filter
                        container filter {
                            description "Enter the filter context";

                            ///nokia-state/state/subscriber-mgmt/vrgw/brg/subscriber-parameters/egress/filter/overrides
                            container overrides {
                                description "Enter the overrides context";

                                ///nokia-state/state/subscriber-mgmt/vrgw/brg/subscriber-parameters/egress/filter/overrides/ipv4
                                container ipv4 {
                                    description "Enter the ipv4 context";

                                    ///nokia-state/state/subscriber-mgmt/vrgw/brg/subscriber-parameters/egress/filter/overrides/ipv4/filter
                                    leaf filter {
                                        type types-submgt:overrule-filter-name;
                                        description "The egress IPv4 filter";
                                    }

                                } // container ipv4

                                ///nokia-state/state/subscriber-mgmt/vrgw/brg/subscriber-parameters/egress/filter/overrides/ipv6
                                container ipv6 {
                                    description "Enter the ipv6 context";

                                    ///nokia-state/state/subscriber-mgmt/vrgw/brg/subscriber-parameters/egress/filter/overrides/ipv6/filter
                                    leaf filter {
                                        type types-submgt:overrule-filter-name;
                                        description "The egress IPv6 filter";
                                    }

                                } // container ipv6

                            } // container overrides

                            ///nokia-state/state/subscriber-mgmt/vrgw/brg/subscriber-parameters/egress/filter/shared-rule
                            list shared-rule {
                                key "index";
                                description "Enter the shared-rule list instance";

                                ///nokia-state/state/subscriber-mgmt/vrgw/brg/subscriber-parameters/egress/filter/shared-rule/index
                                leaf index {
                                    type uint32;
                                    description "A BRG filter rule index.";
                                }

                                ///nokia-state/state/subscriber-mgmt/vrgw/brg/subscriber-parameters/egress/filter/shared-rule/action
                                leaf action {
                                    type enumeration {
                                        enum forward                        { value 1; }
                                        enum drop                           { value 2; }
                                    }
                                    description "Action taken.";
                                }

                                ///nokia-state/state/subscriber-mgmt/vrgw/brg/subscriber-parameters/egress/filter/shared-rule/match
                                container match {
                                    description "Enter the match context";

                                    ///nokia-state/state/subscriber-mgmt/vrgw/brg/subscriber-parameters/egress/filter/shared-rule/match/protocol-next-header
                                    leaf protocol-next-header {
                                        type types-submgt:match-protocol-next-header;
                                        description "IPv4 protocol or IPv6 next-header";
                                    }

                                    ///nokia-state/state/subscriber-mgmt/vrgw/brg/subscriber-parameters/egress/filter/shared-rule/match/fragment
                                    leaf fragment {
                                        type boolean;
                                        description "Indicates if this filter applies to fragmented or unfragmented packets only";
                                    }

                                    ///nokia-state/state/subscriber-mgmt/vrgw/brg/subscriber-parameters/egress/filter/shared-rule/match/src-ip
                                    container src-ip {
                                        description "Enter the src-ip context";

                                        ///nokia-state/state/subscriber-mgmt/vrgw/brg/subscriber-parameters/egress/filter/shared-rule/match/src-ip/address
                                        leaf address {
                                            type types-sros:ip-prefix-with-host-bits;
                                            description "Source IP address and mask";
                                        }

                                    } // container src-ip

                                    ///nokia-state/state/subscriber-mgmt/vrgw/brg/subscriber-parameters/egress/filter/shared-rule/match/src-port
                                    container src-port {
                                        description "Enter the src-port context";

                                        ///nokia-state/state/subscriber-mgmt/vrgw/brg/subscriber-parameters/egress/filter/shared-rule/match/src-port/range
                                        container range {
                                            description "Enter the range context";

                                            ///nokia-state/state/subscriber-mgmt/vrgw/brg/subscriber-parameters/egress/filter/shared-rule/match/src-port/range/start
                                            leaf start {
                                                type types-sros:tcp-udp-port;
                                                description "Lower bound of source port range";
                                            }

                                            ///nokia-state/state/subscriber-mgmt/vrgw/brg/subscriber-parameters/egress/filter/shared-rule/match/src-port/range/end
                                            leaf end {
                                                type types-sros:tcp-udp-port;
                                                description "Upper bound of source port range";
                                            }

                                        } // container range

                                    } // container src-port

                                    ///nokia-state/state/subscriber-mgmt/vrgw/brg/subscriber-parameters/egress/filter/shared-rule/match/dst-ip
                                    container dst-ip {
                                        description "Enter the dst-ip context";

                                        ///nokia-state/state/subscriber-mgmt/vrgw/brg/subscriber-parameters/egress/filter/shared-rule/match/dst-ip/address
                                        leaf address {
                                            type types-sros:ip-prefix-with-host-bits;
                                            description "Destination IP address and mask";
                                        }

                                    } // container dst-ip

                                    ///nokia-state/state/subscriber-mgmt/vrgw/brg/subscriber-parameters/egress/filter/shared-rule/match/dst-port
                                    container dst-port {
                                        description "Enter the dst-port context";

                                        ///nokia-state/state/subscriber-mgmt/vrgw/brg/subscriber-parameters/egress/filter/shared-rule/match/dst-port/range
                                        container range {
                                            description "Enter the range context";

                                            ///nokia-state/state/subscriber-mgmt/vrgw/brg/subscriber-parameters/egress/filter/shared-rule/match/dst-port/range/start
                                            leaf start {
                                                type types-sros:tcp-udp-port;
                                                description "Lower bound of destination port range";
                                            }

                                            ///nokia-state/state/subscriber-mgmt/vrgw/brg/subscriber-parameters/egress/filter/shared-rule/match/dst-port/range/end
                                            leaf end {
                                                type types-sros:tcp-udp-port;
                                                description "Upper bound of destination port range";
                                            }

                                        } // container range

                                    } // container dst-port

                                    ///nokia-state/state/subscriber-mgmt/vrgw/brg/subscriber-parameters/egress/filter/shared-rule/match/ip-option
                                    container ip-option {
                                        description "Enter the ip-option context";

                                        ///nokia-state/state/subscriber-mgmt/vrgw/brg/subscriber-parameters/egress/filter/shared-rule/match/ip-option/type
                                        leaf type {
                                            type types-sros:ip-option;
                                            description "Indicates ";
                                        }

                                    } // container ip-option

                                    ///nokia-state/state/subscriber-mgmt/vrgw/brg/subscriber-parameters/egress/filter/shared-rule/match/tcp-flags
                                    container tcp-flags {
                                        description "Enter the tcp-flags context";

                                        ///nokia-state/state/subscriber-mgmt/vrgw/brg/subscriber-parameters/egress/filter/shared-rule/match/tcp-flags/ack
                                        leaf ack {
                                            type boolean;
                                            description "Indicates if the control bits of the TCP header must contain the ACK bit";
                                        }

                                        ///nokia-state/state/subscriber-mgmt/vrgw/brg/subscriber-parameters/egress/filter/shared-rule/match/tcp-flags/syn
                                        leaf syn {
                                            type boolean;
                                            description "Indicates ";
                                        }

                                    } // container tcp-flags

                                    ///nokia-state/state/subscriber-mgmt/vrgw/brg/subscriber-parameters/egress/filter/shared-rule/match/icmp
                                    container icmp {
                                        description "Enter the icmp context";

                                        ///nokia-state/state/subscriber-mgmt/vrgw/brg/subscriber-parameters/egress/filter/shared-rule/match/icmp/type
                                        leaf type {
                                            type types-submgt:match-icmp-type;
                                            description "Indicates the ICMP type to be matched";
                                        }

                                    } // container icmp

                                } // container match

                            } // list shared-rule

                            ///nokia-state/state/subscriber-mgmt/vrgw/brg/subscriber-parameters/egress/filter/host-specific-rule
                            list host-specific-rule {
                                key "index";
                                description "Enter the host-specific-rule list instance";

                                ///nokia-state/state/subscriber-mgmt/vrgw/brg/subscriber-parameters/egress/filter/host-specific-rule/index
                                leaf index {
                                    type uint32;
                                    description "A BRG filter rule index.";
                                }

                                ///nokia-state/state/subscriber-mgmt/vrgw/brg/subscriber-parameters/egress/filter/host-specific-rule/action
                                leaf action {
                                    type enumeration {
                                        enum forward                        { value 1; }
                                        enum drop                           { value 2; }
                                    }
                                    description "Action taken.";
                                }

                                ///nokia-state/state/subscriber-mgmt/vrgw/brg/subscriber-parameters/egress/filter/host-specific-rule/match
                                container match {
                                    description "Enter the match context";

                                    ///nokia-state/state/subscriber-mgmt/vrgw/brg/subscriber-parameters/egress/filter/host-specific-rule/match/protocol-next-header
                                    leaf protocol-next-header {
                                        type types-submgt:match-protocol-next-header;
                                        description "IPv4 protocol or IPv6 next-header";
                                    }

                                    ///nokia-state/state/subscriber-mgmt/vrgw/brg/subscriber-parameters/egress/filter/host-specific-rule/match/fragment
                                    leaf fragment {
                                        type boolean;
                                        description "Indicates if this filter applies to fragmented or unfragmented packets only";
                                    }

                                    ///nokia-state/state/subscriber-mgmt/vrgw/brg/subscriber-parameters/egress/filter/host-specific-rule/match/src-ip
                                    container src-ip {
                                        description "Enter the src-ip context";

                                        ///nokia-state/state/subscriber-mgmt/vrgw/brg/subscriber-parameters/egress/filter/host-specific-rule/match/src-ip/address
                                        leaf address {
                                            type types-sros:ip-prefix-with-host-bits;
                                            description "Source IP address and mask";
                                        }

                                    } // container src-ip

                                    ///nokia-state/state/subscriber-mgmt/vrgw/brg/subscriber-parameters/egress/filter/host-specific-rule/match/src-port
                                    container src-port {
                                        description "Enter the src-port context";

                                        ///nokia-state/state/subscriber-mgmt/vrgw/brg/subscriber-parameters/egress/filter/host-specific-rule/match/src-port/range
                                        container range {
                                            description "Enter the range context";

                                            ///nokia-state/state/subscriber-mgmt/vrgw/brg/subscriber-parameters/egress/filter/host-specific-rule/match/src-port/range/start
                                            leaf start {
                                                type types-sros:tcp-udp-port;
                                                description "Lower bound of source port range";
                                            }

                                            ///nokia-state/state/subscriber-mgmt/vrgw/brg/subscriber-parameters/egress/filter/host-specific-rule/match/src-port/range/end
                                            leaf end {
                                                type types-sros:tcp-udp-port;
                                                description "Upper bound of source port range";
                                            }

                                        } // container range

                                    } // container src-port

                                    ///nokia-state/state/subscriber-mgmt/vrgw/brg/subscriber-parameters/egress/filter/host-specific-rule/match/dst-port
                                    container dst-port {
                                        description "Enter the dst-port context";

                                        ///nokia-state/state/subscriber-mgmt/vrgw/brg/subscriber-parameters/egress/filter/host-specific-rule/match/dst-port/range
                                        container range {
                                            description "Enter the range context";

                                            ///nokia-state/state/subscriber-mgmt/vrgw/brg/subscriber-parameters/egress/filter/host-specific-rule/match/dst-port/range/start
                                            leaf start {
                                                type types-sros:tcp-udp-port;
                                                description "Lower bound of destination port range";
                                            }

                                            ///nokia-state/state/subscriber-mgmt/vrgw/brg/subscriber-parameters/egress/filter/host-specific-rule/match/dst-port/range/end
                                            leaf end {
                                                type types-sros:tcp-udp-port;
                                                description "Upper bound of destination port range";
                                            }

                                        } // container range

                                    } // container dst-port

                                    ///nokia-state/state/subscriber-mgmt/vrgw/brg/subscriber-parameters/egress/filter/host-specific-rule/match/ip-option
                                    container ip-option {
                                        description "Enter the ip-option context";

                                        ///nokia-state/state/subscriber-mgmt/vrgw/brg/subscriber-parameters/egress/filter/host-specific-rule/match/ip-option/type
                                        leaf type {
                                            type types-sros:ip-option;
                                            description "Indicates ";
                                        }

                                    } // container ip-option

                                    ///nokia-state/state/subscriber-mgmt/vrgw/brg/subscriber-parameters/egress/filter/host-specific-rule/match/tcp-flags
                                    container tcp-flags {
                                        description "Enter the tcp-flags context";

                                        ///nokia-state/state/subscriber-mgmt/vrgw/brg/subscriber-parameters/egress/filter/host-specific-rule/match/tcp-flags/ack
                                        leaf ack {
                                            type boolean;
                                            description "Indicates if the control bits of the TCP header must contain the ACK bit";
                                        }

                                        ///nokia-state/state/subscriber-mgmt/vrgw/brg/subscriber-parameters/egress/filter/host-specific-rule/match/tcp-flags/syn
                                        leaf syn {
                                            type boolean;
                                            description "Indicates ";
                                        }

                                    } // container tcp-flags

                                    ///nokia-state/state/subscriber-mgmt/vrgw/brg/subscriber-parameters/egress/filter/host-specific-rule/match/icmp
                                    container icmp {
                                        description "Enter the icmp context";

                                        ///nokia-state/state/subscriber-mgmt/vrgw/brg/subscriber-parameters/egress/filter/host-specific-rule/match/icmp/type
                                        leaf type {
                                            type types-submgt:match-icmp-type;
                                            description "Indicates the ICMP type to be matched";
                                        }

                                    } // container icmp

                                } // container match

                            } // list host-specific-rule

                        } // container filter

                        ///nokia-state/state/subscriber-mgmt/vrgw/brg/subscriber-parameters/egress/qos
                        container qos {
                            description "Enter the qos context";

                            ///nokia-state/state/subscriber-mgmt/vrgw/brg/subscriber-parameters/egress/qos/overrides
                            container overrides {
                                description "Enter the overrides context";

                                ///nokia-state/state/subscriber-mgmt/vrgw/brg/subscriber-parameters/egress/qos/overrides/sub-aggregate-rate
                                leaf sub-aggregate-rate {
                                    type types-qos:rate-limit;
                                    units "kilobps";
                                    description "The maximum total rate of all egress queues of the subscriber.";
                                }

                                ///nokia-state/state/subscriber-mgmt/vrgw/brg/subscriber-parameters/egress/qos/overrides/sla-aggregate-rate
                                leaf sla-aggregate-rate {
                                    type types-qos:rate-limit;
                                    units "kilobps";
                                    description "The maximum rate of all egress queues of the SLA profile instance.";
                                }

                                ///nokia-state/state/subscriber-mgmt/vrgw/brg/subscriber-parameters/egress/qos/overrides/arbiter
                                list arbiter {
                                    key "arbiter-name";
                                    description "Enter the arbiter list instance";

                                    ///nokia-state/state/subscriber-mgmt/vrgw/brg/subscriber-parameters/egress/qos/overrides/arbiter/arbiter-name
                                    leaf arbiter-name {
                                        type types-sros:named-item;
                                        description "Name of overridden arbiter";
                                    }

                                    ///nokia-state/state/subscriber-mgmt/vrgw/brg/subscriber-parameters/egress/qos/overrides/arbiter/pir
                                    leaf pir {
                                        type types-qos:policer-pir-rate-override;
                                        units "kilobps";
                                        description "PIR rate";
                                    }

                                } // list arbiter

                                ///nokia-state/state/subscriber-mgmt/vrgw/brg/subscriber-parameters/egress/qos/overrides/policer
                                list policer {
                                    key "policer-id";
                                    description "Enter the policer list instance";

                                    ///nokia-state/state/subscriber-mgmt/vrgw/brg/subscriber-parameters/egress/qos/overrides/policer/policer-id
                                    leaf policer-id {
                                        type types-qos:sap-egress-policer-id;
                                        description "The unique identifier for the policer.";
                                    }

                                    ///nokia-state/state/subscriber-mgmt/vrgw/brg/subscriber-parameters/egress/qos/overrides/policer/pir
                                    leaf pir {
                                        type types-qos:policer-pir-rate-override;
                                        units "kilobps";
                                        description "PIR rate";
                                    }

                                    ///nokia-state/state/subscriber-mgmt/vrgw/brg/subscriber-parameters/egress/qos/overrides/policer/cir
                                    leaf cir {
                                        type types-qos:policer-cir-rate-override;
                                        units "kilobps";
                                        description "CIR rate";
                                    }

                                    ///nokia-state/state/subscriber-mgmt/vrgw/brg/subscriber-parameters/egress/qos/overrides/policer/mbs
                                    leaf mbs {
                                        type types-qos:policer-burst-size-override-max;
                                        units "bytes";
                                        description "The maximum reserved buffer space";
                                    }

                                    ///nokia-state/state/subscriber-mgmt/vrgw/brg/subscriber-parameters/egress/qos/overrides/policer/cbs
                                    leaf cbs {
                                        type types-qos:policer-burst-size-override-max;
                                        units "bytes";
                                        description "The committed buffer size";
                                    }

                                } // list policer

                                ///nokia-state/state/subscriber-mgmt/vrgw/brg/subscriber-parameters/egress/qos/overrides/queue
                                list queue {
                                    key "queue-id";
                                    description "Enter the queue list instance";

                                    ///nokia-state/state/subscriber-mgmt/vrgw/brg/subscriber-parameters/egress/qos/overrides/queue/queue-id
                                    leaf queue-id {
                                        type types-qos:egress-queue-id;
                                        description "The unique identifier for the queue.";
                                    }

                                    ///nokia-state/state/subscriber-mgmt/vrgw/brg/subscriber-parameters/egress/qos/overrides/queue/pir
                                    leaf pir {
                                        type types-qos:queue-pir-rate-override;
                                        units "kilobps";
                                        description "PIR rate";
                                    }

                                    ///nokia-state/state/subscriber-mgmt/vrgw/brg/subscriber-parameters/egress/qos/overrides/queue/cir
                                    leaf cir {
                                        type types-qos:queue-cir-rate-override;
                                        units "kilobps";
                                        description "CIR rate";
                                    }

                                    ///nokia-state/state/subscriber-mgmt/vrgw/brg/subscriber-parameters/egress/qos/overrides/queue/mbs
                                    leaf mbs {
                                        type types-qos:queue-burst-size-override;
                                        units "bytes";
                                        description "The maximum reserved buffer space";
                                    }

                                    ///nokia-state/state/subscriber-mgmt/vrgw/brg/subscriber-parameters/egress/qos/overrides/queue/cbs
                                    leaf cbs {
                                        type types-qos:queue-burst-size-override;
                                        units "bytes";
                                        description "The committed buffer size";
                                    }

                                    ///nokia-state/state/subscriber-mgmt/vrgw/brg/subscriber-parameters/egress/qos/overrides/queue/wrr-weight
                                    leaf wrr-weight {
                                        type types-qos:hs-wrr-weight-override;
                                        description
                                            "The Weighted Round Robin (WRR) weight with which
                                             this queue should parent into the scheduler.";
                                    }

                                    ///nokia-state/state/subscriber-mgmt/vrgw/brg/subscriber-parameters/egress/qos/overrides/queue/class-weight
                                    leaf class-weight {
                                        type types-qos:hs-class-weight-override;
                                        description "The scheduling class weight.";
                                    }

                                } // list queue

                                ///nokia-state/state/subscriber-mgmt/vrgw/brg/subscriber-parameters/egress/qos/overrides/scheduler
                                list scheduler {
                                    key "scheduler-name";
                                    description "Enter the scheduler list instance";

                                    ///nokia-state/state/subscriber-mgmt/vrgw/brg/subscriber-parameters/egress/qos/overrides/scheduler/scheduler-name
                                    leaf scheduler-name {
                                        type types-sros:named-item;
                                        description "Name of overridden scheduler";
                                    }

                                    ///nokia-state/state/subscriber-mgmt/vrgw/brg/subscriber-parameters/egress/qos/overrides/scheduler/pir
                                    leaf pir {
                                        type types-qos:scheduler-cir-rate;
                                        units "kilobps";
                                        description "PIR rate";
                                    }

                                    ///nokia-state/state/subscriber-mgmt/vrgw/brg/subscriber-parameters/egress/qos/overrides/scheduler/cir
                                    leaf cir {
                                        type types-qos:scheduler-cir-rate-override;
                                        units "kilobps";
                                        description "CIR rate";
                                    }

                                } // list scheduler

                                ///nokia-state/state/subscriber-mgmt/vrgw/brg/subscriber-parameters/egress/qos/overrides/wrr-group
                                list wrr-group {
                                    key "group-id";
                                    description "Enter the wrr-group list instance";

                                    ///nokia-state/state/subscriber-mgmt/vrgw/brg/subscriber-parameters/egress/qos/overrides/wrr-group/group-id
                                    leaf group-id {
                                        type types-qos:hs-wrr-group-id;
                                        description "HS WRR group identifier";
                                    }

                                    ///nokia-state/state/subscriber-mgmt/vrgw/brg/subscriber-parameters/egress/qos/overrides/wrr-group/pir
                                    leaf pir {
                                        type types-qos:hs-wrr-rate-override;
                                        units "kilobps";
                                        description "The rate (PIR) override for WRR group.";
                                    }

                                    ///nokia-state/state/subscriber-mgmt/vrgw/brg/subscriber-parameters/egress/qos/overrides/wrr-group/class-weight
                                    leaf class-weight {
                                        type types-qos:hs-class-weight-override;
                                        description "The class weight override for WRR group.";
                                    }

                                } // list wrr-group

                            } // container overrides

                        } // container qos

                    } // container egress


                } // container subscriber-parameters

                ///nokia-state/state/subscriber-mgmt/vrgw/brg/pppoe-client
                container pppoe-client {
                    description "Enter the pppoe-client context";

                    ///nokia-state/state/subscriber-mgmt/vrgw/brg/pppoe-client/service
                    leaf service {
                        type types-services:service-name;
                        description "The L2 service where the PPPoE client is initiated";
                    }

                    ///nokia-state/state/subscriber-mgmt/vrgw/brg/pppoe-client/mac
                    leaf mac {
                        type types-sros:mac-unicast-address;
                        description "The source MAC address used for the client";
                    }

                    ///nokia-state/state/subscriber-mgmt/vrgw/brg/pppoe-client/up-time
                    leaf up-time {
                        type uint32;
                        description "How long the PPPoE session has been active";
                    }

                    ///nokia-state/state/subscriber-mgmt/vrgw/brg/pppoe-client/policy
                    leaf policy {
                        type types-sros:named-item;
                        description "The PPPoE client policy";
                    }

                    ///nokia-state/state/subscriber-mgmt/vrgw/brg/pppoe-client/service-name
                    leaf service-name {
                        type string;
                        description "The service-name";
                    }

                    ///nokia-state/state/subscriber-mgmt/vrgw/brg/pppoe-client/session-id
                    leaf session-id {
                        type uint16;
                        description "The PPPoE session ID";
                    }

                    ///nokia-state/state/subscriber-mgmt/vrgw/brg/pppoe-client/access-concentrator-mac
                    leaf access-concentrator-mac {
                        type types-sros:mac-unicast-address;
                        description "The access concentrator MAC address";
                    }

                    ///nokia-state/state/subscriber-mgmt/vrgw/brg/pppoe-client/access-concentrator-name
                    leaf access-concentrator-name {
                        type string {
                            length "0..64";
                        }
                        description "The access concentrator name";
                    }

                    ///nokia-state/state/subscriber-mgmt/vrgw/brg/pppoe-client/lcp
                    container lcp {
                        description "Enter the lcp context";

                        ///nokia-state/state/subscriber-mgmt/vrgw/brg/pppoe-client/lcp/state
                        leaf state {
                            type enumeration {
                                enum initial                        { value 1; }
                                enum starting                       { value 2; }
                                enum closed                         { value 3; }
                                enum stopped                        { value 4; }
                                enum closing                        { value 5; }
                                enum stopping                       { value 6; }
                                enum request-sent                   { value 7; }
                                enum ack-received                   { value 8; }
                                enum ack-sent                       { value 9; }
                                enum opened                         { value 10; }
                            }
                            description "The LCP state, as defined in RFC 1661";
                        }

                        ///nokia-state/state/subscriber-mgmt/vrgw/brg/pppoe-client/lcp/local-magic-number
                        leaf local-magic-number {
                            type uint32;
                            description "The magic number of the client";
                        }

                        ///nokia-state/state/subscriber-mgmt/vrgw/brg/pppoe-client/lcp/remote-magic-number
                        leaf remote-magic-number {
                            type uint32;
                            description "The magic number sent by the access concentrator";
                        }

                        ///nokia-state/state/subscriber-mgmt/vrgw/brg/pppoe-client/lcp/remote-mru
                        leaf remote-mru {
                            type uint32;
                            description "The MRU sent by the Access Concentrator";
                        }

                    } // container lcp

                    ///nokia-state/state/subscriber-mgmt/vrgw/brg/pppoe-client/authentication
                    container authentication {
                        description "Enter the authentication context";

                        ///nokia-state/state/subscriber-mgmt/vrgw/brg/pppoe-client/authentication/user-name
                        leaf user-name {
                            type string;
                            description "The PPP user name";
                        }

                        ///nokia-state/state/subscriber-mgmt/vrgw/brg/pppoe-client/authentication/protocol
                        leaf protocol {
                            type enumeration {
                                enum none {
                                    value 0;
                                    description "No authentication is performed, NCP is started immediately after LCP is finished";
                                }
                                enum pap {
                                    value 1;
                                    description "The PPPoE client authenticates itself using PAP";
                                }
                                enum chap {
                                    value 2;
                                    description "The PPPoE client authenticates itself using CHAP";
                                }
                            }
                            description "The PPP authentication protocol";
                        }

                    } // container authentication

                    ///nokia-state/state/subscriber-mgmt/vrgw/brg/pppoe-client/ipcp
                    container ipcp {
                        description "Enter the ipcp context";

                        ///nokia-state/state/subscriber-mgmt/vrgw/brg/pppoe-client/ipcp/state
                        leaf state {
                            type enumeration {
                                enum initial                        { value 1; }
                                enum starting                       { value 2; }
                                enum closed                         { value 3; }
                                enum stopped                        { value 4; }
                                enum closing                        { value 5; }
                                enum stopping                       { value 6; }
                                enum request-sent                   { value 7; }
                                enum ack-received                   { value 8; }
                                enum ack-sent                       { value 9; }
                                enum opened                         { value 10; }
                            }
                            description "The IPCP state, as defined in RFC 1661";
                        }

                        ///nokia-state/state/subscriber-mgmt/vrgw/brg/pppoe-client/ipcp/address
                        leaf address {
                            type types-sros:ipv4-address;
                            description "The IPv4 address";
                        }

                        ///nokia-state/state/subscriber-mgmt/vrgw/brg/pppoe-client/ipcp/dns
                        leaf-list dns {
                            type types-sros:ipv4-address;
                            description "The IPv4 Domain Name Servers";
                        }

                        ///nokia-state/state/subscriber-mgmt/vrgw/brg/pppoe-client/ipcp/nbns
                        leaf-list nbns {
                            type types-sros:ipv4-address;
                            description "The IPv4 NetBios Name Servers";
                        }

                    } // container ipcp

                    ///nokia-state/state/subscriber-mgmt/vrgw/brg/pppoe-client/ipv6cp
                    container ipv6cp {
                        description "Enter the ipv6cp context";

                        ///nokia-state/state/subscriber-mgmt/vrgw/brg/pppoe-client/ipv6cp/state
                        leaf state {
                            type enumeration {
                                enum initial                        { value 1; }
                                enum starting                       { value 2; }
                                enum closed                         { value 3; }
                                enum stopped                        { value 4; }
                                enum closing                        { value 5; }
                                enum stopping                       { value 6; }
                                enum request-sent                   { value 7; }
                                enum ack-received                   { value 8; }
                                enum ack-sent                       { value 9; }
                                enum opened                         { value 10; }
                            }
                            description "The IPv6CP state, as defined in RFC 1661";
                        }

                        ///nokia-state/state/subscriber-mgmt/vrgw/brg/pppoe-client/ipv6cp/interface-id
                        leaf interface-id {
                            type string;
                            description "The client IPv6 Interface Identifier used for link-local addressing";
                        }

                        ///nokia-state/state/subscriber-mgmt/vrgw/brg/pppoe-client/ipv6cp/dns
                        leaf-list dns {
                            type types-sros:ipv6-address;
                            description "The IPv6 Domain Name Servers";
                        }

                        ///nokia-state/state/subscriber-mgmt/vrgw/brg/pppoe-client/ipv6cp/slaac
                        container slaac {
                            description "Enter the slaac context";

                            ///nokia-state/state/subscriber-mgmt/vrgw/brg/pppoe-client/ipv6cp/slaac/prefix
                            leaf prefix {
                                type types-sros:ipv6-prefix;
                                description "The SLAAC prefix";
                            }

                            ///nokia-state/state/subscriber-mgmt/vrgw/brg/pppoe-client/ipv6cp/slaac/prefix-timeout
                            leaf prefix-timeout {
                                type uint32;
                                description "Timeout after which the SLAAC prefix is no longer considered valid. Will be updated when an RA is received.";
                            }

                        } // container slaac

                    } // container ipv6cp

                    ///nokia-state/state/subscriber-mgmt/vrgw/brg/pppoe-client/statistics
                    container statistics {
                        description "Enter the statistics context";

                        ///nokia-state/state/subscriber-mgmt/vrgw/brg/pppoe-client/statistics/tx-padi
                        leaf tx-padi {
                            type yang:counter32;
                            description "PADI packets transmitted by this PPPoE client";
                        }

                        ///nokia-state/state/subscriber-mgmt/vrgw/brg/pppoe-client/statistics/tx-padr
                        leaf tx-padr {
                            type yang:counter32;
                            description "PADR (PPPoE Active Discovery Request) packets transmitted by this PPPoE client";
                        }

                        ///nokia-state/state/subscriber-mgmt/vrgw/brg/pppoe-client/statistics/tx-padt
                        leaf tx-padt {
                            type yang:counter32;
                            description "PADT (PPPoE Active Discovery Terminate) packets transmitted by this PPPoE client";
                        }

                        ///nokia-state/state/subscriber-mgmt/vrgw/brg/pppoe-client/statistics/tx-session
                        leaf tx-session {
                            type yang:counter32;
                            description "PPP session stage packets transmitted by this PPPoE client";
                        }

                        ///nokia-state/state/subscriber-mgmt/vrgw/brg/pppoe-client/statistics/tx-lcp-echo-request
                        leaf tx-lcp-echo-request {
                            type yang:counter32;
                            description "LCP echo request packets transmitted by this PPPoE client";
                        }

                        ///nokia-state/state/subscriber-mgmt/vrgw/brg/pppoe-client/statistics/tx-lcp-echo-reply
                        leaf tx-lcp-echo-reply {
                            type yang:counter32;
                            description "LCP echo reply packets transmitted by this PPPoE client";
                        }

                        ///nokia-state/state/subscriber-mgmt/vrgw/brg/pppoe-client/statistics/tx-icmpv6-router-solicit
                        leaf tx-icmpv6-router-solicit {
                            type yang:counter32;
                            description "ICMPv6 Router-Solicit packets transmitted by this PPPoE client";
                        }

                        ///nokia-state/state/subscriber-mgmt/vrgw/brg/pppoe-client/statistics/tx-dhcpv6-info
                        leaf tx-dhcpv6-info {
                            type yang:counter32;
                            description "DHCPv6 Info-Request packets transmitted by this PPPoE client";
                        }

                        ///nokia-state/state/subscriber-mgmt/vrgw/brg/pppoe-client/statistics/rx-pado
                        leaf rx-pado {
                            type yang:counter32;
                            description "PADO packets received by this PPPoE client";
                        }

                        ///nokia-state/state/subscriber-mgmt/vrgw/brg/pppoe-client/statistics/rx-pads
                        leaf rx-pads {
                            type yang:counter32;
                            description "PADS packets received by this PPPoE client";
                        }

                        ///nokia-state/state/subscriber-mgmt/vrgw/brg/pppoe-client/statistics/rx-padt
                        leaf rx-padt {
                            type yang:counter32;
                            description "PADT packets received by this PPPoE client";
                        }

                        ///nokia-state/state/subscriber-mgmt/vrgw/brg/pppoe-client/statistics/rx-session
                        leaf rx-session {
                            type yang:counter32;
                            description "PPP session stage packets received by this PPPoE client";
                        }

                        ///nokia-state/state/subscriber-mgmt/vrgw/brg/pppoe-client/statistics/rx-lcp-echo-request
                        leaf rx-lcp-echo-request {
                            type yang:counter32;
                            description "LCP echo request packets received by this PPPoE client";
                        }

                        ///nokia-state/state/subscriber-mgmt/vrgw/brg/pppoe-client/statistics/rx-lcp-echo-reply
                        leaf rx-lcp-echo-reply {
                            type yang:counter32;
                            description "LCP echo reply packets received by this PPPoE client";
                        }

                        ///nokia-state/state/subscriber-mgmt/vrgw/brg/pppoe-client/statistics/rx-icmpv6-router-advertisement
                        leaf rx-icmpv6-router-advertisement {
                            type yang:counter32;
                            description "ICMPv6 Router-Advertisement packets received by this PPPoE client";
                        }

                        ///nokia-state/state/subscriber-mgmt/vrgw/brg/pppoe-client/statistics/rx-dhcpv6-reply
                        leaf rx-dhcpv6-reply {
                            type yang:counter32;
                            description "DHCPv6 Reply packets received by this PPPoE client";
                        }

                        ///nokia-state/state/subscriber-mgmt/vrgw/brg/pppoe-client/statistics/rx-dropped
                        leaf rx-dropped {
                            type yang:counter32;
                            description "packets dropped by this PPPoE client";
                        }

                    } // container statistics

                } // container pppoe-client

                ///nokia-state/state/subscriber-mgmt/vrgw/brg/bridge-domain
                container bridge-domain {
                    description "Enter the bridge-domain context";

                    ///nokia-state/state/subscriber-mgmt/vrgw/brg/bridge-domain/id
                    leaf id {
                        type uint32;
                        description "Bridge domain identifier";
                    }

                    ///nokia-state/state/subscriber-mgmt/vrgw/brg/bridge-domain/vni
                    leaf vni {
                        type uint32;
                        description "VXLAN Network Identifier (VNI) of this bridge domain";
                    }

                    ///nokia-state/state/subscriber-mgmt/vrgw/brg/bridge-domain/route-target
                    leaf route-target {
                        type types-services:route-target;
                        description "EVPN route-target of this bridge domain";
                    }

                    ///nokia-state/state/subscriber-mgmt/vrgw/brg/bridge-domain/route-distinguisher
                    leaf route-distinguisher {
                        type types-services:vpn-route-distinguisher;
                        description "EVPN route-distinguisher of this bridge domain";
                    }

                    ///nokia-state/state/subscriber-mgmt/vrgw/brg/bridge-domain/wlan-gw-group
                    leaf wlan-gw-group {
                        type types-isa:wlan-gw-group-id;
                        description "WLAN Gateway ISA group associated with this bridge domain";
                    }

                    ///nokia-state/state/subscriber-mgmt/vrgw/brg/bridge-domain/wlan-gw-group-member
                    leaf wlan-gw-group-member {
                        type types-nat:bb-group-member;
                        description "WLAN Gateway ISA Group member associated with this bridge domain";
                    }

                    ///nokia-state/state/subscriber-mgmt/vrgw/brg/bridge-domain/mdu-vlan-tag
                    leaf mdu-vlan-tag {
                        type types-sros:qtag-full-range;
                        description "VLAN tag associated with this bridge domain";
                    }

                    ///nokia-state/state/subscriber-mgmt/vrgw/brg/bridge-domain/service
                    leaf service {
                        type types-services:service-name;
                        description "Service of the ESM SAP associated with this bridge domain";
                    }

                    ///nokia-state/state/subscriber-mgmt/vrgw/brg/bridge-domain/group-interface
                    leaf group-interface {
                        type types-sros:interface-name;
                        description "Group interface associated with this bridge domain";
                    }

                    ///nokia-state/state/subscriber-mgmt/vrgw/brg/bridge-domain/assistive-address-resolution
                    leaf assistive-address-resolution {
                        type boolean;
                        description "Use ARP/ND assist for this bridge domain";
                    }

                    ///nokia-state/state/subscriber-mgmt/vrgw/brg/bridge-domain/network
                    leaf network {
                        type boolean;
                        description "Allow network side connections";
                    }

                    ///nokia-state/state/subscriber-mgmt/vrgw/brg/bridge-domain/mac-translation
                    container mac-translation {
                        description "Enter the mac-translation context";

                        ///nokia-state/state/subscriber-mgmt/vrgw/brg/bridge-domain/mac-translation/oper-state
                        leaf oper-state {
                            type types-sros:oper-state;
                            description "Operational state of MAC translation for this bridge domain";
                        }

                        ///nokia-state/state/subscriber-mgmt/vrgw/brg/bridge-domain/mac-translation/mac
                        leaf mac {
                            type types-sros:mac-unicast-address;
                            description "Translated MAC address of home users towards datacenter";
                        }

                    } // container mac-translation

                    ///nokia-state/state/subscriber-mgmt/vrgw/brg/bridge-domain/max-macs
                    container max-macs {
                        description "Enter the max-macs context";

                        ///nokia-state/state/subscriber-mgmt/vrgw/brg/bridge-domain/max-macs/access
                        leaf access {
                            type int32;
                            description "Maximum number of MAC entries over access connection";
                        }

                        ///nokia-state/state/subscriber-mgmt/vrgw/brg/bridge-domain/max-macs/network
                        leaf network {
                            type int32;
                            description "Maximum number of MAC entries over network side connection";
                        }

                    } // container max-macs

                    ///nokia-state/state/subscriber-mgmt/vrgw/brg/bridge-domain/ingress
                    container ingress {
                        description "Enter the ingress context";

                        ///nokia-state/state/subscriber-mgmt/vrgw/brg/bridge-domain/ingress/access-policer
                        leaf access-policer {
                            type types-sros:named-item;
                            description "Bridge domain policer for ingress access traffic";
                        }

                        ///nokia-state/state/subscriber-mgmt/vrgw/brg/bridge-domain/ingress/network-policer
                        leaf network-policer {
                            type types-sros:named-item;
                            description "Bridge domain policer for ingress network traffic";
                        }

                    } // container ingress

                } // container bridge-domain


            } // list brg

            ///nokia-state/state/subscriber-mgmt/vrgw/statistics
            container statistics {
                description "Enter the statistics context";

                ///nokia-state/state/subscriber-mgmt/vrgw/statistics/brg
                container brg {
                    description "Enter the brg context";

                    ///nokia-state/state/subscriber-mgmt/vrgw/statistics/brg/initialized
                    leaf initialized {
                        type yang:counter32;
                        description "Number of initialized BRGs";
                    }

                    ///nokia-state/state/subscriber-mgmt/vrgw/statistics/brg/operational
                    leaf operational {
                        type yang:counter32;
                        description "Number of operational BRGs";
                    }

                    ///nokia-state/state/subscriber-mgmt/vrgw/statistics/brg/connectivity-verification
                    leaf connectivity-verification {
                        type yang:counter32;
                        description "Number of BRGs running connectivity verification";
                    }

                    ///nokia-state/state/subscriber-mgmt/vrgw/statistics/brg/hold
                    leaf hold {
                        type yang:counter32;
                        description "Number of held BRGs";
                    }

                    ///nokia-state/state/subscriber-mgmt/vrgw/statistics/brg/proxy-authenticated
                    leaf proxy-authenticated {
                        type yang:counter32;
                        description "Number of proxy-authenticated BRGs";
                    }

                } // container brg

            } // container statistics

        } // container vrgw

    } // grouping state-submgt-vrgw

}
