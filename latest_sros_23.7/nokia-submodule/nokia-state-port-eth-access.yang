submodule nokia-state-port-eth-access {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }

    include nokia-state-qos;

    sros-ext:sros-major-release "rel23";
    organization "Nokia";
    contact
        "Nokia SR OS Support
         Web: <http://www.nokia.com>";
    description
        "Nokia YANG Data model with operational state for access capabilities for ethernet ports on SR OS based routers.

         Copyright 2016 Nokia. All rights reserved. Reproduction of this document
         is authorized on the condition that the foregoing copyright notice is included.

         This nokia-state-port-eth-access YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-15";

    grouping state-port-eth-access {
        container access {
            description "Enter the access context";

            leaf available-bandwidth {
                type yang:counter64;
                units "kilobps";
                description "Indicates the bandwidth that is still free for booking on the Ethernet port.";
            }

            leaf booked-bandwidth {
                type yang:counter64;
                units "kilobps";
                description "Indicates the bandwidth that has been booked on the Ethernet port.";
            }

            container egress {
                description "Enter the egress context";

                list queue-group {
                    key "queue-group-name instance-id";
                    description "Enter the queue-group list instance";

                    leaf queue-group-name {
                        type leafref {
                            path "../../../../../../qos/queue-group-templates/egress/queue-group/egress-queue-group-name";
                        }
                        description "Queue group name";
                    }

                    leaf instance-id {
                        type uint16 {
                            range "1..65535";
                        }
                        description "Instance ID for the egress queue group";
                    }

                    container aggregate-rate {
                        description "Enter the aggregate-rate context";


                    } // container aggregate-rate

                    container scheduler-policy {
                        description "Enter the scheduler-policy context";

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type leafref {
                                path "../../../../../../../qos/queue-group-templates/egress/queue-group[egress-queue-group-name=current()/../../queue-group-name]/queue/queue-id";
                            }
                            description "Specifies the queue overrides queue identifier.";
                        }

                        container statistics {
                            description "Enter the statistics context";

                            choice stat-mode {
                                case profile {

                                    container profile {
                                        description "Enter the profile context";

                                        leaf in-inplus-profile-forwarded-packets {
                                            type yang:counter64;
                                            description
                                                "The number of in-profile/in-plus-profile packets
                                                 (rate below CIR) forwarded.";
                                        }

                                        leaf in-inplus-profile-forwarded-octets {
                                            type yang:counter64;
                                            description
                                                "The number of in-profile/in-plus-profile octets
                                                 (rate below CIR) forwarded.";
                                        }

                                        leaf in-inplus-profile-dropped-packets {
                                            type yang:counter64;
                                            description
                                                "The number of in-profile/in-plus-profile packets
                                                 discarded.";
                                        }

                                        leaf in-inplus-profile-dropped-octets {
                                            type yang:counter64;
                                            description
                                                "The number of in-profile/in-plus-profile octets
                                                 discarded.";
                                        }

                                        leaf out-exceed-profile-forwarded-packets {
                                            type yang:counter64;
                                            description
                                                "The number of out-profile/exceed-profile packets
                                                 (rate above CIR) forwarded.";
                                        }

                                        leaf out-exceed-profile-forwarded-octets {
                                            type yang:counter64;
                                            description
                                                "The number of out-profile/exceed-profile octets
                                                 (rate above CIR) forwarded.";
                                        }

                                        leaf out-exceed-profile-dropped-packets {
                                            type yang:counter64;
                                            description
                                                "The number of out-profile/exceed-profile packets
                                                 discarded.";
                                        }

                                        leaf out-exceed-profile-dropped-octets {
                                            type yang:counter64;
                                            description
                                                "The number of out-profile/exceed-profile octets
                                                 discarded.";
                                        }

                                    } // container profile

                                }
                            }
                        } // container statistics

                        container hardware-queue {
                            description "Enter the hardware-queue context";

                            leaf adapted-admin-mbs {
                                type types-qos:bytes;
                                units "bytes";
                                description "Admin MBS.";
                            }

                            leaf exceed-droptail {
                                type types-qos:queue-burst-size-64-override-max;
                                description "Exceed droptail.";
                            }

                            leaf high-droptail {
                                type types-qos:queue-burst-size-64-override-max;
                                description "High droptail.";
                            }

                            leaf high-plus-droptail {
                                type union {
                                    type int64 {
                                        range "0..max";
                                    }
                                    type enumeration {
                                        enum auto                           { value -1; }
                                    }
                                }
                                description "Highplus droptail.";
                            }

                            leaf low-droptail {
                                type types-qos:queue-burst-size-64-override-max;
                                description "Low droptail.";
                            }

                            leaf operational-cbs {
                                type types-qos:bytes;
                                units "bytes";
                                description "Oper CBS.";
                            }

                            leaf operational-cir {
                                type types-qos:int-max;
                                description "Oper CIR.";
                            }

                            leaf operational-mbs {
                                type types-qos:bytes;
                                units "bytes";
                                description "Oper MBS.";
                            }

                            leaf operational-pir {
                                type types-qos:int-max;
                                description "Oper PIR.";
                            }

                            leaf burst-limit {
                                type union {
                                    type int32;
                                    type enumeration {
                                        enum auto                           { value -1; }
                                    }
                                }
                                description "Oper burst limit.";
                            }

                            leaf operational-exceed-burst {
                                type types-qos:int64-max;
                                description "Oper burst exceed.";
                            }

                            leaf operational-max-transmit-data-size {
                                type types-qos:int64-max;
                                description "Oper max transmit data size.";
                            }

                            container exceed-slope {
                                description "Enter the exceed-slope context";

                                leaf current-probability {
                                    type types-sros:percent;
                                    description "Specifies the current probability in percentage";
                                }

                            } // container exceed-slope

                            container high-slope {
                                description "Enter the high-slope context";

                                leaf current-probability {
                                    type types-sros:percent;
                                    description "Specifies the current probability in percentage";
                                }

                            } // container high-slope

                            container high-plus-slope {
                                description "Enter the high-plus-slope context";

                                leaf current-probability {
                                    type types-sros:percent;
                                    description "Specifies the current probability in percentage";
                                }

                            } // container high-plus-slope

                            container low-slope {
                                description "Enter the low-slope context";

                                leaf current-probability {
                                    type types-sros:percent;
                                    description "Specifies the current probability in percentage";
                                }

                            } // container low-slope

                        } // container hardware-queue

                        container queue-depth {
                            description "Enter the queue-depth context";

                            leaf elapsed-time {
                                type types-sros:time-interval;
                                description "Indicated the elapsed time.";
                            }

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                            leaf queue-polling-interval {
                                type types-sros:time-interval;
                                description "Indicates the queue polling interval.";
                            }

                            leaf last-violation {
                                type yang:date-and-time;
                                description "Indicates the last violation time.";
                            }

                            leaf total-threshold-violations {
                                type yang:counter32;
                                description "Indicates the total threshold violations.";
                            }

                            leaf high-water-mark-polling-interval {
                                type types-sros:time-duration;
                                units "microseconds";
                                description "Indicates the high water mark polling interval.";
                            }

                        } // container queue-depth

                    } // list queue

                } // list queue-group

                list virtual-port {
                    key "vport-name";
                    description "Enter the virtual-port list instance";

                    leaf vport-name {
                        type types-sros:named-item;
                        description "Vport scheduling node name";
                    }

                    leaf multicast-hqos-adjustment-delta {
                        type uint32;
                        units "kilobps";
                        description "Indicates the actual bandwidth correction.";
                    }

                    container scheduler-policy {
                        description "Enter the scheduler-policy context";

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    container hw-agg-shaper-scheduler {
                        description "Enter the hw-agg-shaper-scheduler context";

                        leaf policy-name {
                            type types-sros:named-item-or-empty;
                            description "Specifies an hardware aggregate shaper scheduler policy.";
                        }

                        leaf oper-color {
                            type types-qos:color-oper;
                            description "Specify what is state of hw-agg-shaper scheduler algorithm";
                        }

                        leaf num-child-agg-shapers {
                            type int64 {
                                range "0..6400000000";
                            }
                            description "Specify number of agg-shapers parented to this vport scheduler.";
                        }

                        leaf num-orphan-agg-shapers {
                            type int64 {
                                range "0..6400000000";
                            }
                            description "Specify number of agg-shapers not parented to this vport scheduler.";
                        }

                        container statistics {
                            description "Enter the statistics context";

                            leaf total-forwarded-octets {
                                type yang:counter64;
                                description "Indicates the total number of octets forwarded.";
                            }

                            leaf total-forwarded-packets {
                                type yang:counter64;
                                description "Indicates the total number of packets forwarded.";
                            }

                            leaf total-dropped-octets {
                                type yang:counter64;
                                description "Indicates the total number of octets dropped.";
                            }

                            leaf total-dropped-packets {
                                type yang:counter64;
                                description "Indicates the total number of packets dropped.";
                            }

                            leaf last-cleared-time {
                                type yang:date-and-time;
                                description
                                    "Indicates the time, since system startup, when the counters in
                                     IF-MIB::ifTable were last cleared.";
                            }

                            list class {
                                key "sched-class";
                                description "Enter the class list instance";

                                leaf sched-class {
                                    type uint32 {
                                        range "1..6";
                                    }
                                    description "Specifies the scheduler class of the hardware aggregate shaper scheduler policy.";
                                }

                                leaf forwarded-octets {
                                    type yang:counter64;
                                    description "Indicates the total number of octets forwarded.";
                                }

                                leaf forwarded-packets {
                                    type yang:counter64;
                                    description "Indicates the total number of packets forwarded.";
                                }

                                leaf dropped-octets {
                                    type yang:counter64;
                                    description "Indicates the total number of octets dropped.";
                                }

                                leaf dropped-packets {
                                    type yang:counter64;
                                    description "Indicates the total number of packets dropped.";
                                }

                                leaf last-cleared-time {
                                    type yang:date-and-time;
                                    description
                                        "Indicates the time, since system startup, when the counters in
                                         IF-MIB::ifTable were last cleared.";
                                }

                            } // list class

                        } // container statistics

                        container monitor-threshold {
                            description "Enter the monitor-threshold context";

                            leaf exceed-count {
                                type yang:counter32;
                                description "Indicates the exceed count for egress hardware aggregate shaper scheduler.";
                            }

                            leaf start-time {
                                type yang:date-and-time;
                                description "Indicates the start time for threshold monitoring.";
                            }

                            leaf end-time {
                                type yang:date-and-time;
                                description "Indicates the end time for threshold monitoring.";
                            }

                            leaf total-samples {
                                type yang:date-and-time;
                                description "Indicates the total samples collected during the threshold monitoring interval.";
                            }

                        } // container monitor-threshold

                    } // container hw-agg-shaper-scheduler

                } // list virtual-port

            } // container egress

            container ingress {
                description "Enter the ingress context";

                list queue-group {
                    key "queue-group-name";
                    description "Enter the queue-group list instance";

                    leaf queue-group-name {
                        type leafref {
                            path "../../../../../../qos/queue-group-templates/ingress/queue-group/ingress-queue-group-name";
                        }
                        description "Queue group name";
                    }

                    container scheduler-policy {
                        description "Enter the scheduler-policy context";

                        list scheduler {
                            key "scheduler-name";
                            description "Enter the scheduler list instance";

                            leaf scheduler-name {
                                type types-sros:named-item;
                                description "Scheduler name";
                            }

                            container statistics {
                                description "Enter the statistics context";

                                leaf forwarded-packets {
                                    type yang:counter64;
                                    description "The number of forwarded packets.";
                                }

                                leaf forwarded-octets {
                                    type yang:counter64;
                                    description "The number of forwarded octets.";
                                }

                            } // container statistics

                        } // list scheduler

                    } // container scheduler-policy

                    list queue {
                        key "queue-id";
                        description "Enter the queue list instance";

                        leaf queue-id {
                            type types-qos:ingress-queue-id;
                            description "Specifies the queue group queue identifier.";
                        }

                        container statistics {
                            description "Enter the statistics context";

                            choice stat-mode {
                                case unicast-priority {

                                    container unicast-priority {
                                        description "Enter the unicast-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-priority

                                }
                                case unicast-profile {

                                    container unicast-profile {
                                        description "Enter the unicast-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf color-offered-packets {
                                            type yang:counter64;
                                            description "The number of color packets offered to traffic manager.";
                                        }

                                        leaf color-offered-octets {
                                            type yang:counter64;
                                            description "The number of color octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container unicast-profile

                                }
                                case multipoint-priority {

                                    container multipoint-priority {
                                        description "Enter the multipoint-priority context";

                                        leaf high-priority-offered-packets {
                                            type yang:counter64;
                                            description "The number of high-priority packets offered by packet processor to traffic manager.";
                                        }

                                        leaf high-priority-offered-octets {
                                            type yang:counter64;
                                            description "The number of high-priority octets offered by packet processor to traffic manager.";
                                        }

                                        leaf low-priority-offered-packets {
                                            type yang:counter64;
                                            description "The number of low-priority packets offered by packet processor to traffic manager.";
                                        }

                                        leaf low-priority-offered-octets {
                                            type yang:counter64;
                                            description "The number of low-priority octets offered by packet processor to traffic manager.";
                                        }

                                        leaf combined-offered-packets {
                                            type yang:counter64;
                                            description "The number of combined high and low priority packets offered by packet processor to traffic manager.";
                                        }

                                        leaf combined-offered-octets {
                                            type yang:counter64;
                                            description "The number of combined high and low priority octets offered by packet processor to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf high-priority-dropped-packets {
                                            type yang:counter64;
                                            description "The number of high-priority packets dropped by packet processor to traffic manager.";
                                        }

                                        leaf high-priority-dropped-octets {
                                            type yang:counter64;
                                            description "The number of high-priority octets dropped by packet processor to traffic manager.";
                                        }

                                        leaf low-priority-dropped-packets {
                                            type yang:counter64;
                                            description "The number of low-priority packets dropped by packet processor to traffic manager.";
                                        }

                                        leaf low-priority-dropped-octets {
                                            type yang:counter64;
                                            description "The number of low-priority octets dropped by packet processor to traffic manager.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-priority

                                }
                                case multipoint-profile {

                                    container multipoint-profile {
                                        description "Enter the multipoint-profile context";

                                        leaf color-in-offered-packets {
                                            type yang:counter64;
                                            description "The number of color-in packets offered to traffic manager.";
                                        }

                                        leaf color-in-offered-octets {
                                            type yang:counter64;
                                            description "The number of color-in octets offered to traffic manager.";
                                        }

                                        leaf color-out-offered-packets {
                                            type yang:counter64;
                                            description "The number of color-out packets offered to traffic manager.";
                                        }

                                        leaf color-out-offered-octets {
                                            type yang:counter64;
                                            description "The number of color-out octets offered to traffic manager.";
                                        }

                                        leaf uncolor-offered-packets {
                                            type yang:counter64;
                                            description "The number of uncolor packets offered to traffic manager.";
                                        }

                                        leaf uncolor-offered-octets {
                                            type yang:counter64;
                                            description "The number of uncolor octets offered to traffic manager.";
                                        }

                                        leaf combined-offered-packets {
                                            type yang:counter64;
                                            description "The number of combined colored in, out and uncolored packets offered to traffic manager.";
                                        }

                                        leaf combined-offered-octets {
                                            type yang:counter64;
                                            description "The number of combined colored in, out and uncolored octets offered to traffic manager.";
                                        }

                                        leaf managed-offered-packets {
                                            type yang:counter64;
                                            description "The number of managed packets offered by packet processor to traffic manager.";
                                        }

                                        leaf managed-offered-octets {
                                            type yang:counter64;
                                            description "The number of managed octets offered by packet processor to traffic manager.";
                                        }

                                        leaf color-out-dropped-packets {
                                            type yang:counter64;
                                            description "The number of color-out packets dropped.";
                                        }

                                        leaf color-out-dropped-octets {
                                            type yang:counter64;
                                            description "The number of color-out octets dropped.";
                                        }

                                        leaf color-in-uncolor-dropped-packets {
                                            type yang:counter64;
                                            description "The number of color-in/uncolor packets dropped.";
                                        }

                                        leaf color-in-uncolor-dropped-octets {
                                            type yang:counter64;
                                            description "The number of color-in/uncolor octets dropped.";
                                        }

                                        leaf in-profile-forwarded-packets {
                                            type yang:counter64;
                                            description "The number of in-profile packets (rate below CIR) forwarded.";
                                        }

                                        leaf in-profile-forwarded-octets {
                                            type yang:counter64;
                                            description "The number of in-profile octets (rate below CIR) forwarded.";
                                        }

                                        leaf out-profile-forwarded-packets {
                                            type yang:counter64;
                                            description "The number of out-of-profile packets (rate below CIR) forwarded.";
                                        }

                                        leaf out-profile-forwarded-octets {
                                            type yang:counter64;
                                            description "The number of out-of-profile octets (rate below CIR) forwarded.";
                                        }

                                    } // container multipoint-profile

                                }
                            }
                        } // container statistics

                        container queue-depth {
                            description "Enter the queue-depth context";

                            leaf elapsed-time {
                                type types-sros:time-interval;
                                description "Indicated the elapsed time.";
                            }

                            leaf depth-0-to-10-percent {
                                type decimal64 {
                                    fraction-digits 2;
                                }
                                description "Indicated the depth 0 to 10 percent.";
                            }

                            leaf depth-11-to-20-percent {
                                type decimal64 {
                                    fraction-digits 2;
                                }
                                description "Indicated the depth 0 to 20 percent.";
                            }

                            leaf depth-21-to-30-percent {
                                type decimal64 {
                                    fraction-digits 2;
                                }
                                description "Indicated the depth 0 to 30 percent.";
                            }

                            leaf depth-31-to-40-percent {
                                type decimal64 {
                                    fraction-digits 2;
                                }
                                description "Indicated the depth 0 to 40 percent.";
                            }

                            leaf depth-41-to-50-percent {
                                type decimal64 {
                                    fraction-digits 2;
                                }
                                description "Indicated the depth 0 to 50 percent.";
                            }

                            leaf depth-51-to-60-percent {
                                type decimal64 {
                                    fraction-digits 2;
                                }
                                description "Indicated the depth 0 to 60 percent.";
                            }

                            leaf depth-61-to-70-percent {
                                type decimal64 {
                                    fraction-digits 2;
                                }
                                description "Indicated the depth 0 to 70 percent.";
                            }

                            leaf depth-71-to-80-percent {
                                type decimal64 {
                                    fraction-digits 2;
                                }
                                description "Indicated the depth 0 to 80 percent.";
                            }

                            leaf depth-81-to-90-percent {
                                type decimal64 {
                                    fraction-digits 2;
                                }
                                description "Indicated the depth 0 to 90 percent.";
                            }

                            leaf depth-91-to-100-percent {
                                type decimal64 {
                                    fraction-digits 2;
                                }
                                description "Indicated the depth 0 to 100 percent.";
                            }

                            leaf queue-polling-interval {
                                type types-sros:time-interval;
                                description "Indicates the queue polling interval.";
                            }

                        } // container queue-depth

                        list hardware-queue {
                            key "source-tap-offset dest-card dest-fp dest-tap-offset";
                            description "Enter the hardware-queue list instance";

                            leaf source-tap-offset {
                                type int32;
                                description "Source TAP.";
                            }

                            leaf dest-card {
                                type int32;
                                description "Card number";
                            }

                            leaf dest-fp {
                                type int32;
                                description "FP number";
                            }

                            leaf dest-tap-offset {
                                type int32;
                                description "Destination TAP.";
                            }

                            leaf adapted-admin-mbs {
                                type int64;
                                units "bytes";
                                description "Admin MBS.";
                            }

                            leaf adapted-admin-cbs {
                                type types-qos:bytes;
                                units "bytes";
                                description "Admin CBS.";
                            }

                            leaf operational-mbs {
                                type int64;
                                units "bytes";
                                description "Oper MBS.";
                            }

                            leaf depth {
                                type union {
                                    type enumeration {
                                        enum max                            { value -1; }
                                    }
                                    type int64;
                                }
                                description "Depth CIR.";
                            }

                            leaf operational-cir {
                                type union {
                                    type enumeration {
                                        enum max                            { value -1; }
                                    }
                                    type int64;
                                }
                                description "Oper CIR.";
                            }

                            leaf operational-fir {
                                type union {
                                    type enumeration {
                                        enum max                            { value -1; }
                                    }
                                    type int64;
                                }
                                description "Oper FIR.";
                            }

                            leaf operational-pir {
                                type union {
                                    type enumeration {
                                        enum max                            { value -1; }
                                    }
                                    type int64;
                                }
                                description "Oper PIR.";
                            }

                            leaf exceed-droptail {
                                type union {
                                    type int64 {
                                        range "0..max";
                                    }
                                    type enumeration {
                                        enum auto                           { value -1; }
                                    }
                                }
                                description "Exceed droptail.";
                            }

                            leaf high-droptail {
                                type union {
                                    type int64 {
                                        range "0..max";
                                    }
                                    type enumeration {
                                        enum auto                           { value -1; }
                                    }
                                }
                                description "High droptail.";
                            }

                            leaf high-plus-droptail {
                                type union {
                                    type int64 {
                                        range "0..max";
                                    }
                                    type enumeration {
                                        enum auto                           { value -1; }
                                    }
                                }
                                description "Highplus droptail.";
                            }

                            leaf low-droptail {
                                type union {
                                    type int64 {
                                        range "0..max";
                                    }
                                    type enumeration {
                                        enum auto                           { value -1; }
                                    }
                                }
                                description "Low droptail.";
                            }

                            leaf operational-exceed-burst {
                                type types-qos:int64-max;
                                description "Oper burst exceed.";
                            }

                            leaf operational-max-transmit-data-size {
                                type types-qos:int64-max;
                                description "Oper max transmit data size.";
                            }

                        } // list hardware-queue

                    } // list queue

                } // list queue-group

            } // container ingress

        } // container access

    } // grouping state-port-eth-access

}
