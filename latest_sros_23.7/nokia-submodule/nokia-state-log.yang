submodule nokia-state-log {

    yang-version "1.1";

    belongs-to nokia-state { prefix "state"; }

    import ietf-yang-types                { prefix "yang"; }
    import nokia-sros-yang-extensions     { prefix "sros-ext"; }
    import nokia-types-application-assurance { prefix "types-aa"; }
    import nokia-types-card               { prefix "types-card"; }
    import nokia-types-log                { prefix "types-log"; }
    import nokia-types-services           { prefix "types-services"; }
    import nokia-types-sros               { prefix "types-sros"; }

    include nokia-state-test-oam;
    include nokia-state-testoam-service-activation-testhead;

    sros-ext:sros-major-release "rel23";
    organization "Nokia";
    contact
        "Nokia SR OS Support
         Web: <http://www.nokia.com>";
    description
        "Nokia YANG Data model with operational state for event stream logging on SR OS based routers.

         Copyright 2016 Nokia. All rights reserved. Reproduction of this document
         is authorized on the condition that the foregoing copyright notice is included.

         This nokia-state-log YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-06-19";

    grouping state-log {
        ///nokia-state/state/log
        container log {
            description "Enable the log context";

            ///nokia-state/state/log/accounting-policy
            list accounting-policy {
                key "policy-id";
                description "Enter the accounting-policy list instance";

                ///nokia-state/state/log/accounting-policy/policy-id
                leaf policy-id {
                    type types-log:log-policy-id;
                    description "Accounting policy unique ID";
                }

                ///nokia-state/state/log/accounting-policy/oper-state
                leaf oper-state {
                    type types-sros:oper-state;
                    description
                        "The value of the this object indicates the operational
                         state of the accounting policy.";
                }

                ///nokia-state/state/log/accounting-policy/port-type
                leaf port-type {
                    type types-log:accounting-port-type;
                    description
                        "Indicates the type of facility associated with the specified
                         accounting policy's record type.";
                }

                ///nokia-state/state/log/accounting-policy/data-loss-count
                leaf data-loss-count {
                    type yang:counter32;
                    description
                        "Indicates the number of times a log accounting data loss trap was
                         raised against this application policy.";
                }

                ///nokia-state/state/log/accounting-policy/last-data-loss-time
                leaf last-data-loss-time {
                    type yang:date-and-time;
                    description
                        "Indicates the last time, since system startup that log accounting
                         data loss trap was raised against this application policy.";
                }

                ///nokia-state/state/log/accounting-policy/associations
                container associations {
                    description "Enter the associations context";

                    ///nokia-state/state/log/accounting-policy/associations/access
                    list access {
                        key "service-name sap-id";
                        description "Enter the access list instance";

                        ///nokia-state/state/log/accounting-policy/associations/access/service-name
                        leaf service-name {
                            type types-sros:named-item-64;
                            description "Acc-policy is associated with service-name";
                        }

                        ///nokia-state/state/log/accounting-policy/associations/access/sap-id
                        leaf sap-id {
                            type types-sros:sap;
                            description "Acc-policy is associated with the SAP ID.";
                        }

                    } // list access

                    ///nokia-state/state/log/accounting-policy/associations/network
                    list network {
                        key "port-id";
                        description "Enter the network list instance";

                        ///nokia-state/state/log/accounting-policy/associations/network/port-id
                        leaf port-id {
                            type types-sros:port;
                            description "The host port of the PXC.";
                        }

                    } // list network

                    ///nokia-state/state/log/accounting-policy/associations/sdp
                    list sdp {
                        key "sdp-id";
                        description "Enter the sdp list instance";

                        ///nokia-state/state/log/accounting-policy/associations/sdp/sdp-id
                        leaf sdp-id {
                            type types-services:sdp-id;
                            description "Service Distribution Point (SDP) identifier.";
                        }

                    } // list sdp

                    ///nokia-state/state/log/accounting-policy/associations/sdp-bind
                    list sdp-bind {
                        key "service-name sdp-bind-id";
                        description "Enter the sdp-bind list instance";

                        ///nokia-state/state/log/accounting-policy/associations/sdp-bind/service-name
                        leaf service-name {
                            type types-sros:named-item-64;
                            description "Acc-policy is associated with service-name";
                        }

                        ///nokia-state/state/log/accounting-policy/associations/sdp-bind/sdp-bind-id
                        leaf sdp-bind-id {
                            type types-services:sdp-bind-id;
                            description "Acc-policy is associated with the SDP ID.";
                        }

                    } // list sdp-bind

                    ///nokia-state/state/log/accounting-policy/associations/subscriber
                    list subscriber {
                        key "profile-name";
                        description "Enter the subscriber list instance";

                        ///nokia-state/state/log/accounting-policy/associations/subscriber/profile-name
                        leaf profile-name {
                            type types-sros:named-item;
                            description "Acc-policy is associated with profile";
                        }

                    } // list subscriber

                    ///nokia-state/state/log/accounting-policy/associations/aa-performance
                    list aa-performance {
                        key "aa-assur-isa-group-id";
                        description "Enter the aa-performance list instance";

                        ///nokia-state/state/log/accounting-policy/associations/aa-performance/aa-assur-isa-group-id
                        leaf aa-assur-isa-group-id {
                            type uint32;
                            description "Acc-policy is associated with the isa.";
                        }

                    } // list aa-performance

                    ///nokia-state/state/log/accounting-policy/associations/application-assurance
                    list application-assurance {
                        key "aa-group-id aa-partition-id category-name";
                        description "Enter the application-assurance list instance";

                        ///nokia-state/state/log/accounting-policy/associations/application-assurance/aa-group-id
                        leaf aa-group-id {
                            type types-aa:isa-aa-grp-id;
                            description "Specifies an identfifer that uniquely identifies an AA group within the system.";
                        }

                        ///nokia-state/state/log/accounting-policy/associations/application-assurance/aa-partition-id
                        leaf aa-partition-id {
                            type types-aa:aa-grp-part-id;
                            description "The identifier which uniquely identifies the partition within the parent AA group.";
                        }

                        ///nokia-state/state/log/accounting-policy/associations/application-assurance/category-name
                        leaf category-name {
                            type types-aa:partition-stats-category;
                            description
                                "Specifies an identifier which uniquely identifies a statistics category
                                 within a AA partition";
                        }

                    } // list application-assurance

                    ///nokia-state/state/log/accounting-policy/associations/qgrp-ingress
                    list qgrp-ingress {
                        key "port-id group-name";
                        description "Enter the qgrp-ingress list instance";

                        ///nokia-state/state/log/accounting-policy/associations/qgrp-ingress/port-id
                        leaf port-id {
                            type types-sros:port;
                            description "Acc-policy is associated with qgrp with port";
                        }

                        ///nokia-state/state/log/accounting-policy/associations/qgrp-ingress/group-name
                        leaf group-name {
                            type types-sros:named-item;
                            description "Acc-policy is associated with qgrp with group name";
                        }

                        ///nokia-state/state/log/accounting-policy/associations/qgrp-ingress/mode
                        leaf mode {
                            type types-log:access-network;
                            description "Acc-policy is associated with qgrp with mode";
                        }

                    } // list qgrp-ingress

                    ///nokia-state/state/log/accounting-policy/associations/qgrp-egress
                    list qgrp-egress {
                        key "port-id group-name instance-id";
                        description "Enter the qgrp-egress list instance";

                        ///nokia-state/state/log/accounting-policy/associations/qgrp-egress/port-id
                        leaf port-id {
                            type types-sros:port;
                            description "Acc-policy is associated with qgrp with port";
                        }

                        ///nokia-state/state/log/accounting-policy/associations/qgrp-egress/group-name
                        leaf group-name {
                            type types-sros:named-item;
                            description "Acc-policy is associated with qgrp with group name";
                        }

                        ///nokia-state/state/log/accounting-policy/associations/qgrp-egress/instance-id
                        leaf instance-id {
                            type uint16 {
                                range "1..65535";
                            }
                            description "Specifies the instance identifier.";
                        }

                        ///nokia-state/state/log/accounting-policy/associations/qgrp-egress/mode
                        leaf mode {
                            type types-log:access-network;
                            description "Acc-policy is associated with qgrp with mode";
                        }

                    } // list qgrp-egress

                    ///nokia-state/state/log/accounting-policy/associations/qgrp-net-egress
                    list qgrp-net-egress {
                        key "port-id group-name instance-id";
                        description "Enter the qgrp-net-egress list instance";

                        ///nokia-state/state/log/accounting-policy/associations/qgrp-net-egress/port-id
                        leaf port-id {
                            type types-sros:port;
                            description "Acc-policy is associated with qgrp with port";
                        }

                        ///nokia-state/state/log/accounting-policy/associations/qgrp-net-egress/group-name
                        leaf group-name {
                            type types-sros:named-item;
                            description "Acc-policy is associated with qgrp with group name";
                        }

                        ///nokia-state/state/log/accounting-policy/associations/qgrp-net-egress/instance-id
                        leaf instance-id {
                            type uint16 {
                                range "1..65535";
                            }
                            description "Specifies the instance identifier.";
                        }

                        ///nokia-state/state/log/accounting-policy/associations/qgrp-net-egress/mode
                        leaf mode {
                            type types-log:access-network;
                            description "Acc-policy is associated with qgrp with mode";
                        }

                    } // list qgrp-net-egress

                    ///nokia-state/state/log/accounting-policy/associations/qgrp-card-acc
                    list qgrp-card-acc {
                        key "slot-number fp-number group-name instance-id";
                        description "Enter the qgrp-card-acc list instance";

                        ///nokia-state/state/log/accounting-policy/associations/qgrp-card-acc/slot-number
                        leaf slot-number {
                            type types-card:iom-card-slot;
                            description "Acc-policy is associated with qgrp with cardId";
                        }

                        ///nokia-state/state/log/accounting-policy/associations/qgrp-card-acc/fp-number
                        leaf fp-number {
                            type uint32;
                            description "Acc-policy is associated with qgrp with fp number.";
                        }

                        ///nokia-state/state/log/accounting-policy/associations/qgrp-card-acc/group-name
                        leaf group-name {
                            type types-sros:named-item;
                            description "Acc-policy is associated with qgrp with group name";
                        }

                        ///nokia-state/state/log/accounting-policy/associations/qgrp-card-acc/instance-id
                        leaf instance-id {
                            type uint32;
                            description "Acc-policy is associated with qgrp with instance Id.";
                        }

                        ///nokia-state/state/log/accounting-policy/associations/qgrp-card-acc/mode
                        leaf mode {
                            type types-log:access-network;
                            description "Acc-policy is associated with qgrp with mode";
                        }

                    } // list qgrp-card-acc

                    ///nokia-state/state/log/accounting-policy/associations/qgrp-card-net
                    list qgrp-card-net {
                        key "slot-number fp-number group-name instance-id";
                        description "Enter the qgrp-card-net list instance";

                        ///nokia-state/state/log/accounting-policy/associations/qgrp-card-net/slot-number
                        leaf slot-number {
                            type types-card:iom-card-slot;
                            description "Acc-policy is associated with qgrp with cardId";
                        }

                        ///nokia-state/state/log/accounting-policy/associations/qgrp-card-net/fp-number
                        leaf fp-number {
                            type uint32;
                            description "Acc-policy is associated with qgrp with fp number.";
                        }

                        ///nokia-state/state/log/accounting-policy/associations/qgrp-card-net/group-name
                        leaf group-name {
                            type types-sros:named-item;
                            description "Acc-policy is associated with qgrp with group name";
                        }

                        ///nokia-state/state/log/accounting-policy/associations/qgrp-card-net/instance-id
                        leaf instance-id {
                            type uint32;
                            description "Acc-policy is associated with qgrp with instance Id.";
                        }

                        ///nokia-state/state/log/accounting-policy/associations/qgrp-card-net/mode
                        leaf mode {
                            type types-log:access-network;
                            description "Acc-policy is associated with qgrp with mode";
                        }

                    } // list qgrp-card-net

                    ///nokia-state/state/log/accounting-policy/associations/saa
                    list saa {
                        key "owner test";
                        description "Enter the saa list instance";

                        ///nokia-state/state/log/accounting-policy/associations/saa/owner
                        leaf owner {
                            type types-sros:named-item;
                            description "Acc-policy is associated with saa with owner name";
                        }

                        ///nokia-state/state/log/accounting-policy/associations/saa/test
                        leaf test {
                            type types-sros:named-item;
                            description "Acc-policy is associated with saa with test name";
                        }

                    } // list saa

                    ///nokia-state/state/log/accounting-policy/associations/ldp-lsp-egress
                    list ldp-lsp-egress {
                        key "router-instance fec-prefix";
                        description "Enter the ldp-lsp-egress list instance";

                        ///nokia-state/state/log/accounting-policy/associations/ldp-lsp-egress/router-instance
                        leaf router-instance {
                            type types-sros:named-item-64;
                            description
                                "The administrative name for this virtual router.

                                 The router name must be unique among all virtual routers in the system.";
                        }

                        ///nokia-state/state/log/accounting-policy/associations/ldp-lsp-egress/fec-prefix
                        leaf fec-prefix {
                            type types-sros:ip-prefix;
                            description "Configure ip-prefix.";
                        }

                    } // list ldp-lsp-egress

                    ///nokia-state/state/log/accounting-policy/associations/mpls-lsp-ingress
                    list mpls-lsp-ingress {
                        key "router-instance sender lsp-name";
                        description "Enter the mpls-lsp-ingress list instance";

                        ///nokia-state/state/log/accounting-policy/associations/mpls-lsp-ingress/router-instance
                        leaf router-instance {
                            type types-sros:named-item-64;
                            description
                                "The administrative name for this virtual router.

                                 The router name must be unique among all virtual routers in the system.";
                        }

                        ///nokia-state/state/log/accounting-policy/associations/mpls-lsp-ingress/sender
                        leaf sender {
                            type types-sros:ip-address;
                            description "Sender-address of mpls-lsp-ingress";
                        }

                        ///nokia-state/state/log/accounting-policy/associations/mpls-lsp-ingress/lsp-name
                        leaf lsp-name {
                            type types-sros:named-item-64;
                            description "Lsp-name for mpls";
                        }

                    } // list mpls-lsp-ingress

                    ///nokia-state/state/log/accounting-policy/associations/mpls-lsp-egress
                    list mpls-lsp-egress {
                        key "router-instance lsp-name";
                        description "Enter the mpls-lsp-egress list instance";

                        ///nokia-state/state/log/accounting-policy/associations/mpls-lsp-egress/router-instance
                        leaf router-instance {
                            type types-sros:named-item-64;
                            description
                                "The administrative name for this virtual router.

                                 The router name must be unique among all virtual routers in the system.";
                        }

                        ///nokia-state/state/log/accounting-policy/associations/mpls-lsp-egress/lsp-name
                        leaf lsp-name {
                            type types-sros:named-item-64;
                            description "Lsp-name for mpls";
                        }

                    } // list mpls-lsp-egress

                    ///nokia-state/state/log/accounting-policy/associations/mpls-srte-egress
                    list mpls-srte-egress {
                        key "router-instance lsp-name";
                        description "Enter the mpls-srte-egress list instance";

                        ///nokia-state/state/log/accounting-policy/associations/mpls-srte-egress/router-instance
                        leaf router-instance {
                            type types-sros:named-item-64;
                            description
                                "The administrative name for this virtual router.

                                 The router name must be unique among all virtual routers in the system.";
                        }

                        ///nokia-state/state/log/accounting-policy/associations/mpls-srte-egress/lsp-name
                        leaf lsp-name {
                            type types-sros:named-item-64;
                            description "Lsp-name for mpls";
                        }

                    } // list mpls-srte-egress

                    ///nokia-state/state/log/accounting-policy/associations/sr-policy-egress
                    list sr-policy-egress {
                        key "color endpoint segment-index";
                        description "Enter the sr-policy-egress list instance";

                        ///nokia-state/state/log/accounting-policy/associations/sr-policy-egress/color
                        leaf color {
                            type uint32;
                            description "Acc-policy is associated with sr-policy with color.";
                        }

                        ///nokia-state/state/log/accounting-policy/associations/sr-policy-egress/endpoint
                        leaf endpoint {
                            type types-sros:ip-address;
                            description "Acc-policy is associated with sr-policy with end point address";
                        }

                        ///nokia-state/state/log/accounting-policy/associations/sr-policy-egress/segment-index
                        leaf segment-index {
                            type uint32;
                            description "Acc-policy is associated with sr-policy with segment list index.";
                        }

                    } // list sr-policy-egress

                    ///nokia-state/state/log/accounting-policy/associations/video
                    list video {
                        key "service-name interface-name";
                        description "Enter the video list instance";

                        ///nokia-state/state/log/accounting-policy/associations/video/service-name
                        leaf service-name {
                            type types-sros:named-item-64;
                            description "Acc-policy is associated with service-name";
                        }

                        ///nokia-state/state/log/accounting-policy/associations/video/interface-name
                        leaf interface-name {
                            type types-sros:interface-name {
                                length "1..29";
                            }
                            description "[29 chars max] (must start with a letter).";
                        }

                    } // list video

                    ///nokia-state/state/log/accounting-policy/associations/ethernet
                    list ethernet {
                        key "port-id";
                        description "Enter the ethernet list instance";

                        ///nokia-state/state/log/accounting-policy/associations/ethernet/port-id
                        leaf port-id {
                            type types-sros:port;
                            description "The host port of the PXC.";
                        }

                    } // list ethernet

                    ///nokia-state/state/log/accounting-policy/associations/oam-pm
                    list oam-pm {
                        key "session-name measurment-interval-duration";
                        description "Enter the oam-pm list instance";

                        ///nokia-state/state/log/accounting-policy/associations/oam-pm/session-name
                        leaf session-name {
                            type types-sros:named-item;
                            description "Acc-policy is associated with oam pm with sesion name";
                        }

                        ///nokia-state/state/log/accounting-policy/associations/oam-pm/measurment-interval-duration
                        leaf measurment-interval-duration {
                            type types-log:measurment-interval-duration;
                            description "Acc-policy is associated with oam pm with measurment interval duration";
                        }

                    } // list oam-pm

                    ///nokia-state/state/log/accounting-policy/associations/oam-service-activation-testhead
                    list oam-service-activation-testhead {
                        key "service-test-name";
                        description "Enter the oam-service-activation-testhead list instance";

                        ///nokia-state/state/log/accounting-policy/associations/oam-service-activation-testhead/service-test-name
                        leaf service-test-name {
                            type leafref {
                                path "../../../../../test-oam/service-activation-testhead/service-test/test-name";
                            }
                            description
                                "Accounting policy that is associated with a Service
                                 Activation TestHead Service Test";
                        }

                    } // list oam-service-activation-testhead

                } // container associations

            } // list accounting-policy

            ///nokia-state/state/log/log-events
            container log-events {
                description "Enter the log-events context";

                ///nokia-state/state/log/log-events/adp
                list adp {
                    key "event";
                    description "Enter the adp list instance";

                    ///nokia-state/state/log/log-events/adp/event
                    leaf event {
                        type types-log:adp-events;
                        description "Log event as a trigger for one or more EHS handlers";
                    }

                    ///nokia-state/state/log/log-events/adp/event-id
                    leaf event-id {
                        type types-log:log-event-id;
                        description
                            "Unique arbitrary identifier for indexing event type entries within
                             an event generator application.";
                    }

                    ///nokia-state/state/log/log-events/adp/parameters
                    leaf-list parameters {
                        type types-sros:named-item;
                        description
                            "Indicates an event's specific parameters. These parameters can
                             be passed from a triggering event to its triggered EHS script.";
                    }

                    ///nokia-state/state/log/log-events/adp/statistics
                    container statistics {
                        description "Enter the statistics context";

                        ///nokia-state/state/log/log-events/adp/statistics/count
                        leaf count {
                            type yang:counter32;
                            description "Number of times an event of this type has been generated.";
                        }

                        ///nokia-state/state/log/log-events/adp/statistics/drop
                        leaf drop {
                            type yang:counter32;
                            description "Indicates the number of times an event of this type has been dropped.";
                        }

                    } // container statistics

                } // list adp

                ///nokia-state/state/log/log-events/anysec
                list anysec {
                    key "event";
                    description "Enter the anysec list instance";

                    ///nokia-state/state/log/log-events/anysec/event
                    leaf event {
                        type types-log:anysec-events;
                        description "ANYSec module event";
                    }

                    ///nokia-state/state/log/log-events/anysec/event-id
                    leaf event-id {
                        type types-log:log-event-id;
                        description
                            "Unique arbitrary identifier for indexing event type entries within
                             an event generator application.";
                    }

                    ///nokia-state/state/log/log-events/anysec/parameters
                    leaf-list parameters {
                        type types-sros:named-item;
                        description
                            "Indicates an event's specific parameters. These parameters can
                             be passed from a triggering event to its triggered EHS script.";
                    }

                    ///nokia-state/state/log/log-events/anysec/statistics
                    container statistics {
                        description "Enter the statistics context";

                        ///nokia-state/state/log/log-events/anysec/statistics/count
                        leaf count {
                            type yang:counter32;
                            description "Number of times an event of this type has been generated.";
                        }

                        ///nokia-state/state/log/log-events/anysec/statistics/drop
                        leaf drop {
                            type yang:counter32;
                            description "Indicates the number of times an event of this type has been dropped.";
                        }

                    } // container statistics

                } // list anysec

                ///nokia-state/state/log/log-events/application-assurance
                list application-assurance {
                    key "event";
                    description "Enter the application-assurance list instance";

                    ///nokia-state/state/log/log-events/application-assurance/event
                    leaf event {
                        type types-log:application-assurance-events;
                        description "Log event as a trigger for one or more EHS handlers";
                    }

                    ///nokia-state/state/log/log-events/application-assurance/event-id
                    leaf event-id {
                        type types-log:log-event-id;
                        description
                            "Unique arbitrary identifier for indexing event type entries within
                             an event generator application.";
                    }

                    ///nokia-state/state/log/log-events/application-assurance/parameters
                    leaf-list parameters {
                        type types-sros:named-item;
                        description
                            "Indicates an event's specific parameters. These parameters can
                             be passed from a triggering event to its triggered EHS script.";
                    }

                    ///nokia-state/state/log/log-events/application-assurance/statistics
                    container statistics {
                        description "Enter the statistics context";

                        ///nokia-state/state/log/log-events/application-assurance/statistics/count
                        leaf count {
                            type yang:counter32;
                            description "Number of times an event of this type has been generated.";
                        }

                        ///nokia-state/state/log/log-events/application-assurance/statistics/drop
                        leaf drop {
                            type yang:counter32;
                            description "Indicates the number of times an event of this type has been dropped.";
                        }

                    } // container statistics

                } // list application-assurance

                ///nokia-state/state/log/log-events/aps
                list aps {
                    key "event";
                    description "Enter the aps list instance";

                    ///nokia-state/state/log/log-events/aps/event
                    leaf event {
                        type types-log:aps-events;
                        description "Log event as a trigger for one or more EHS handlers";
                    }

                    ///nokia-state/state/log/log-events/aps/event-id
                    leaf event-id {
                        type types-log:log-event-id;
                        description
                            "Unique arbitrary identifier for indexing event type entries within
                             an event generator application.";
                    }

                    ///nokia-state/state/log/log-events/aps/parameters
                    leaf-list parameters {
                        type types-sros:named-item;
                        description
                            "Indicates an event's specific parameters. These parameters can
                             be passed from a triggering event to its triggered EHS script.";
                    }

                    ///nokia-state/state/log/log-events/aps/statistics
                    container statistics {
                        description "Enter the statistics context";

                        ///nokia-state/state/log/log-events/aps/statistics/count
                        leaf count {
                            type yang:counter32;
                            description "Number of times an event of this type has been generated.";
                        }

                        ///nokia-state/state/log/log-events/aps/statistics/drop
                        leaf drop {
                            type yang:counter32;
                            description "Indicates the number of times an event of this type has been dropped.";
                        }

                    } // container statistics

                } // list aps

                ///nokia-state/state/log/log-events/auto-prov
                list auto-prov {
                    key "event";
                    description "Enter the auto-prov list instance";

                    ///nokia-state/state/log/log-events/auto-prov/event
                    leaf event {
                        type types-log:auto-prov-events;
                        description "Log event as a trigger for one or more EHS handlers";
                    }

                    ///nokia-state/state/log/log-events/auto-prov/event-id
                    leaf event-id {
                        type types-log:log-event-id;
                        description
                            "Unique arbitrary identifier for indexing event type entries within
                             an event generator application.";
                    }

                    ///nokia-state/state/log/log-events/auto-prov/parameters
                    leaf-list parameters {
                        type types-sros:named-item;
                        description
                            "Indicates an event's specific parameters. These parameters can
                             be passed from a triggering event to its triggered EHS script.";
                    }

                    ///nokia-state/state/log/log-events/auto-prov/statistics
                    container statistics {
                        description "Enter the statistics context";

                        ///nokia-state/state/log/log-events/auto-prov/statistics/count
                        leaf count {
                            type yang:counter32;
                            description "Number of times an event of this type has been generated.";
                        }

                        ///nokia-state/state/log/log-events/auto-prov/statistics/drop
                        leaf drop {
                            type yang:counter32;
                            description "Indicates the number of times an event of this type has been dropped.";
                        }

                    } // container statistics

                } // list auto-prov

                ///nokia-state/state/log/log-events/bfd
                list bfd {
                    key "event";
                    description "Enter the bfd list instance";

                    ///nokia-state/state/log/log-events/bfd/event
                    leaf event {
                        type types-log:bfd-events;
                        description "Log event as a trigger for one or more EHS handlers";
                    }

                    ///nokia-state/state/log/log-events/bfd/event-id
                    leaf event-id {
                        type types-log:log-event-id;
                        description
                            "Unique arbitrary identifier for indexing event type entries within
                             an event generator application.";
                    }

                    ///nokia-state/state/log/log-events/bfd/parameters
                    leaf-list parameters {
                        type types-sros:named-item;
                        description
                            "Indicates an event's specific parameters. These parameters can
                             be passed from a triggering event to its triggered EHS script.";
                    }

                    ///nokia-state/state/log/log-events/bfd/statistics
                    container statistics {
                        description "Enter the statistics context";

                        ///nokia-state/state/log/log-events/bfd/statistics/count
                        leaf count {
                            type yang:counter32;
                            description "Number of times an event of this type has been generated.";
                        }

                        ///nokia-state/state/log/log-events/bfd/statistics/drop
                        leaf drop {
                            type yang:counter32;
                            description "Indicates the number of times an event of this type has been dropped.";
                        }

                    } // container statistics

                } // list bfd

                ///nokia-state/state/log/log-events/bgp
                list bgp {
                    key "event";
                    description "Enter the bgp list instance";

                    ///nokia-state/state/log/log-events/bgp/event
                    leaf event {
                        type types-log:bgp-events;
                        description "Log event as a trigger for one or more EHS handlers";
                    }

                    ///nokia-state/state/log/log-events/bgp/event-id
                    leaf event-id {
                        type types-log:log-event-id;
                        description
                            "Unique arbitrary identifier for indexing event type entries within
                             an event generator application.";
                    }

                    ///nokia-state/state/log/log-events/bgp/parameters
                    leaf-list parameters {
                        type types-sros:named-item;
                        description
                            "Indicates an event's specific parameters. These parameters can
                             be passed from a triggering event to its triggered EHS script.";
                    }

                    ///nokia-state/state/log/log-events/bgp/statistics
                    container statistics {
                        description "Enter the statistics context";

                        ///nokia-state/state/log/log-events/bgp/statistics/count
                        leaf count {
                            type yang:counter32;
                            description "Number of times an event of this type has been generated.";
                        }

                        ///nokia-state/state/log/log-events/bgp/statistics/drop
                        leaf drop {
                            type yang:counter32;
                            description "Indicates the number of times an event of this type has been dropped.";
                        }

                    } // container statistics

                } // list bgp

                ///nokia-state/state/log/log-events/bier
                list bier {
                    key "event";
                    description "Enter the bier list instance";

                    ///nokia-state/state/log/log-events/bier/event
                    leaf event {
                        type types-log:bier-events;
                        description "Log event as a trigger for one or more EHS handlers";
                    }

                    ///nokia-state/state/log/log-events/bier/event-id
                    leaf event-id {
                        type types-log:log-event-id;
                        description
                            "Unique arbitrary identifier for indexing event type entries within
                             an event generator application.";
                    }

                    ///nokia-state/state/log/log-events/bier/parameters
                    leaf-list parameters {
                        type types-sros:named-item;
                        description
                            "Indicates an event's specific parameters. These parameters can
                             be passed from a triggering event to its triggered EHS script.";
                    }

                    ///nokia-state/state/log/log-events/bier/statistics
                    container statistics {
                        description "Enter the statistics context";

                        ///nokia-state/state/log/log-events/bier/statistics/count
                        leaf count {
                            type yang:counter32;
                            description "Number of times an event of this type has been generated.";
                        }

                        ///nokia-state/state/log/log-events/bier/statistics/drop
                        leaf drop {
                            type yang:counter32;
                            description "Indicates the number of times an event of this type has been dropped.";
                        }

                    } // container statistics

                } // list bier

                ///nokia-state/state/log/log-events/calltrace
                list calltrace {
                    key "event";
                    description "Enter the calltrace list instance";

                    ///nokia-state/state/log/log-events/calltrace/event
                    leaf event {
                        type types-log:calltrace-events;
                        description "Log event as a trigger for one or more EHS handlers";
                    }

                    ///nokia-state/state/log/log-events/calltrace/event-id
                    leaf event-id {
                        type types-log:log-event-id;
                        description
                            "Unique arbitrary identifier for indexing event type entries within
                             an event generator application.";
                    }

                    ///nokia-state/state/log/log-events/calltrace/parameters
                    leaf-list parameters {
                        type types-sros:named-item;
                        description
                            "Indicates an event's specific parameters. These parameters can
                             be passed from a triggering event to its triggered EHS script.";
                    }

                    ///nokia-state/state/log/log-events/calltrace/statistics
                    container statistics {
                        description "Enter the statistics context";

                        ///nokia-state/state/log/log-events/calltrace/statistics/count
                        leaf count {
                            type yang:counter32;
                            description "Number of times an event of this type has been generated.";
                        }

                        ///nokia-state/state/log/log-events/calltrace/statistics/drop
                        leaf drop {
                            type yang:counter32;
                            description "Indicates the number of times an event of this type has been dropped.";
                        }

                    } // container statistics

                } // list calltrace

                ///nokia-state/state/log/log-events/cflowd
                list cflowd {
                    key "event";
                    description "Enter the cflowd list instance";

                    ///nokia-state/state/log/log-events/cflowd/event
                    leaf event {
                        type types-log:cflowd-events;
                        description "Log event as a trigger for one or more EHS handlers";
                    }

                    ///nokia-state/state/log/log-events/cflowd/event-id
                    leaf event-id {
                        type types-log:log-event-id;
                        description
                            "Unique arbitrary identifier for indexing event type entries within
                             an event generator application.";
                    }

                    ///nokia-state/state/log/log-events/cflowd/parameters
                    leaf-list parameters {
                        type types-sros:named-item;
                        description
                            "Indicates an event's specific parameters. These parameters can
                             be passed from a triggering event to its triggered EHS script.";
                    }

                    ///nokia-state/state/log/log-events/cflowd/statistics
                    container statistics {
                        description "Enter the statistics context";

                        ///nokia-state/state/log/log-events/cflowd/statistics/count
                        leaf count {
                            type yang:counter32;
                            description "Number of times an event of this type has been generated.";
                        }

                        ///nokia-state/state/log/log-events/cflowd/statistics/drop
                        leaf drop {
                            type yang:counter32;
                            description "Indicates the number of times an event of this type has been dropped.";
                        }

                    } // container statistics

                } // list cflowd

                ///nokia-state/state/log/log-events/chassis
                list chassis {
                    key "event";
                    description "Enter the chassis list instance";

                    ///nokia-state/state/log/log-events/chassis/event
                    leaf event {
                        type types-log:chassis-events;
                        description "Log event as a trigger for one or more EHS handlers";
                    }

                    ///nokia-state/state/log/log-events/chassis/event-id
                    leaf event-id {
                        type types-log:log-event-id;
                        description
                            "Unique arbitrary identifier for indexing event type entries within
                             an event generator application.";
                    }

                    ///nokia-state/state/log/log-events/chassis/parameters
                    leaf-list parameters {
                        type types-sros:named-item;
                        description
                            "Indicates an event's specific parameters. These parameters can
                             be passed from a triggering event to its triggered EHS script.";
                    }

                    ///nokia-state/state/log/log-events/chassis/statistics
                    container statistics {
                        description "Enter the statistics context";

                        ///nokia-state/state/log/log-events/chassis/statistics/count
                        leaf count {
                            type yang:counter32;
                            description "Number of times an event of this type has been generated.";
                        }

                        ///nokia-state/state/log/log-events/chassis/statistics/drop
                        leaf drop {
                            type yang:counter32;
                            description "Indicates the number of times an event of this type has been dropped.";
                        }

                    } // container statistics

                } // list chassis

                ///nokia-state/state/log/log-events/debug
                list debug {
                    key "event";
                    description "Enter the debug list instance";

                    ///nokia-state/state/log/log-events/debug/event
                    leaf event {
                        type types-log:debug-events;
                        description "Log event as a trigger for one or more EHS handlers";
                    }

                    ///nokia-state/state/log/log-events/debug/event-id
                    leaf event-id {
                        type types-log:log-event-id;
                        description
                            "Unique arbitrary identifier for indexing event type entries within
                             an event generator application.";
                    }

                    ///nokia-state/state/log/log-events/debug/parameters
                    leaf-list parameters {
                        type types-sros:named-item;
                        description
                            "Indicates an event's specific parameters. These parameters can
                             be passed from a triggering event to its triggered EHS script.";
                    }

                    ///nokia-state/state/log/log-events/debug/statistics
                    container statistics {
                        description "Enter the statistics context";

                        ///nokia-state/state/log/log-events/debug/statistics/count
                        leaf count {
                            type yang:counter32;
                            description "Number of times an event of this type has been generated.";
                        }

                        ///nokia-state/state/log/log-events/debug/statistics/drop
                        leaf drop {
                            type yang:counter32;
                            description "Indicates the number of times an event of this type has been dropped.";
                        }

                    } // container statistics

                } // list debug

                ///nokia-state/state/log/log-events/dhcp
                list dhcp {
                    key "event";
                    description "Enter the dhcp list instance";

                    ///nokia-state/state/log/log-events/dhcp/event
                    leaf event {
                        type types-log:dhcp-events;
                        description "Log event as a trigger for one or more EHS handlers";
                    }

                    ///nokia-state/state/log/log-events/dhcp/event-id
                    leaf event-id {
                        type types-log:log-event-id;
                        description
                            "Unique arbitrary identifier for indexing event type entries within
                             an event generator application.";
                    }

                    ///nokia-state/state/log/log-events/dhcp/parameters
                    leaf-list parameters {
                        type types-sros:named-item;
                        description
                            "Indicates an event's specific parameters. These parameters can
                             be passed from a triggering event to its triggered EHS script.";
                    }

                    ///nokia-state/state/log/log-events/dhcp/statistics
                    container statistics {
                        description "Enter the statistics context";

                        ///nokia-state/state/log/log-events/dhcp/statistics/count
                        leaf count {
                            type yang:counter32;
                            description "Number of times an event of this type has been generated.";
                        }

                        ///nokia-state/state/log/log-events/dhcp/statistics/drop
                        leaf drop {
                            type yang:counter32;
                            description "Indicates the number of times an event of this type has been dropped.";
                        }

                    } // container statistics

                } // list dhcp

                ///nokia-state/state/log/log-events/dhcps
                list dhcps {
                    key "event";
                    description "Enter the dhcps list instance";

                    ///nokia-state/state/log/log-events/dhcps/event
                    leaf event {
                        type types-log:dhcps-events;
                        description "Log event as a trigger for one or more EHS handlers";
                    }

                    ///nokia-state/state/log/log-events/dhcps/event-id
                    leaf event-id {
                        type types-log:log-event-id;
                        description
                            "Unique arbitrary identifier for indexing event type entries within
                             an event generator application.";
                    }

                    ///nokia-state/state/log/log-events/dhcps/parameters
                    leaf-list parameters {
                        type types-sros:named-item;
                        description
                            "Indicates an event's specific parameters. These parameters can
                             be passed from a triggering event to its triggered EHS script.";
                    }

                    ///nokia-state/state/log/log-events/dhcps/statistics
                    container statistics {
                        description "Enter the statistics context";

                        ///nokia-state/state/log/log-events/dhcps/statistics/count
                        leaf count {
                            type yang:counter32;
                            description "Number of times an event of this type has been generated.";
                        }

                        ///nokia-state/state/log/log-events/dhcps/statistics/drop
                        leaf drop {
                            type yang:counter32;
                            description "Indicates the number of times an event of this type has been dropped.";
                        }

                    } // container statistics

                } // list dhcps

                ///nokia-state/state/log/log-events/diameter
                list diameter {
                    key "event";
                    description "Enter the diameter list instance";

                    ///nokia-state/state/log/log-events/diameter/event
                    leaf event {
                        type types-log:diameter-events;
                        description "Log event as a trigger for one or more EHS handlers";
                    }

                    ///nokia-state/state/log/log-events/diameter/event-id
                    leaf event-id {
                        type types-log:log-event-id;
                        description
                            "Unique arbitrary identifier for indexing event type entries within
                             an event generator application.";
                    }

                    ///nokia-state/state/log/log-events/diameter/parameters
                    leaf-list parameters {
                        type types-sros:named-item;
                        description
                            "Indicates an event's specific parameters. These parameters can
                             be passed from a triggering event to its triggered EHS script.";
                    }

                    ///nokia-state/state/log/log-events/diameter/statistics
                    container statistics {
                        description "Enter the statistics context";

                        ///nokia-state/state/log/log-events/diameter/statistics/count
                        leaf count {
                            type yang:counter32;
                            description "Number of times an event of this type has been generated.";
                        }

                        ///nokia-state/state/log/log-events/diameter/statistics/drop
                        leaf drop {
                            type yang:counter32;
                            description "Indicates the number of times an event of this type has been dropped.";
                        }

                    } // container statistics

                } // list diameter

                ///nokia-state/state/log/log-events/dot1x
                list dot1x {
                    key "event";
                    description "Enter the dot1x list instance";

                    ///nokia-state/state/log/log-events/dot1x/event
                    leaf event {
                        type types-log:dot1x-events;
                        description "Events for dynsvc module.";
                    }

                    ///nokia-state/state/log/log-events/dot1x/event-id
                    leaf event-id {
                        type types-log:log-event-id;
                        description
                            "Unique arbitrary identifier for indexing event type entries within
                             an event generator application.";
                    }

                    ///nokia-state/state/log/log-events/dot1x/parameters
                    leaf-list parameters {
                        type types-sros:named-item;
                        description
                            "Indicates an event's specific parameters. These parameters can
                             be passed from a triggering event to its triggered EHS script.";
                    }

                    ///nokia-state/state/log/log-events/dot1x/statistics
                    container statistics {
                        description "Enter the statistics context";

                        ///nokia-state/state/log/log-events/dot1x/statistics/count
                        leaf count {
                            type yang:counter32;
                            description "Number of times an event of this type has been generated.";
                        }

                        ///nokia-state/state/log/log-events/dot1x/statistics/drop
                        leaf drop {
                            type yang:counter32;
                            description "Indicates the number of times an event of this type has been dropped.";
                        }

                    } // container statistics

                } // list dot1x

                ///nokia-state/state/log/log-events/dynsvc
                list dynsvc {
                    key "event";
                    description "Enter the dynsvc list instance";

                    ///nokia-state/state/log/log-events/dynsvc/event
                    leaf event {
                        type types-log:dynsvc-events;
                        description "Log event as a trigger for one or more EHS handlers";
                    }

                    ///nokia-state/state/log/log-events/dynsvc/event-id
                    leaf event-id {
                        type types-log:log-event-id;
                        description
                            "Unique arbitrary identifier for indexing event type entries within
                             an event generator application.";
                    }

                    ///nokia-state/state/log/log-events/dynsvc/parameters
                    leaf-list parameters {
                        type types-sros:named-item;
                        description
                            "Indicates an event's specific parameters. These parameters can
                             be passed from a triggering event to its triggered EHS script.";
                    }

                    ///nokia-state/state/log/log-events/dynsvc/statistics
                    container statistics {
                        description "Enter the statistics context";

                        ///nokia-state/state/log/log-events/dynsvc/statistics/count
                        leaf count {
                            type yang:counter32;
                            description "Number of times an event of this type has been generated.";
                        }

                        ///nokia-state/state/log/log-events/dynsvc/statistics/drop
                        leaf drop {
                            type yang:counter32;
                            description "Indicates the number of times an event of this type has been dropped.";
                        }

                    } // container statistics

                } // list dynsvc

                ///nokia-state/state/log/log-events/efm-oam
                list efm-oam {
                    key "event";
                    description "Enter the efm-oam list instance";

                    ///nokia-state/state/log/log-events/efm-oam/event
                    leaf event {
                        type types-log:efm-oam-events;
                        description "Log event as a trigger for one or more EHS handlers";
                    }

                    ///nokia-state/state/log/log-events/efm-oam/event-id
                    leaf event-id {
                        type types-log:log-event-id;
                        description
                            "Unique arbitrary identifier for indexing event type entries within
                             an event generator application.";
                    }

                    ///nokia-state/state/log/log-events/efm-oam/parameters
                    leaf-list parameters {
                        type types-sros:named-item;
                        description
                            "Indicates an event's specific parameters. These parameters can
                             be passed from a triggering event to its triggered EHS script.";
                    }

                    ///nokia-state/state/log/log-events/efm-oam/statistics
                    container statistics {
                        description "Enter the statistics context";

                        ///nokia-state/state/log/log-events/efm-oam/statistics/count
                        leaf count {
                            type yang:counter32;
                            description "Number of times an event of this type has been generated.";
                        }

                        ///nokia-state/state/log/log-events/efm-oam/statistics/drop
                        leaf drop {
                            type yang:counter32;
                            description "Indicates the number of times an event of this type has been dropped.";
                        }

                    } // container statistics

                } // list efm-oam

                ///nokia-state/state/log/log-events/elmi
                list elmi {
                    key "event";
                    description "Enter the elmi list instance";

                    ///nokia-state/state/log/log-events/elmi/event
                    leaf event {
                        type types-log:elmi-events;
                        description "Log event as a trigger for one or more EHS handlers";
                    }

                    ///nokia-state/state/log/log-events/elmi/event-id
                    leaf event-id {
                        type types-log:log-event-id;
                        description
                            "Unique arbitrary identifier for indexing event type entries within
                             an event generator application.";
                    }

                    ///nokia-state/state/log/log-events/elmi/parameters
                    leaf-list parameters {
                        type types-sros:named-item;
                        description
                            "Indicates an event's specific parameters. These parameters can
                             be passed from a triggering event to its triggered EHS script.";
                    }

                    ///nokia-state/state/log/log-events/elmi/statistics
                    container statistics {
                        description "Enter the statistics context";

                        ///nokia-state/state/log/log-events/elmi/statistics/count
                        leaf count {
                            type yang:counter32;
                            description "Number of times an event of this type has been generated.";
                        }

                        ///nokia-state/state/log/log-events/elmi/statistics/drop
                        leaf drop {
                            type yang:counter32;
                            description "Indicates the number of times an event of this type has been dropped.";
                        }

                    } // container statistics

                } // list elmi

                ///nokia-state/state/log/log-events/ering
                list ering {
                    key "event";
                    description "Enter the ering list instance";

                    ///nokia-state/state/log/log-events/ering/event
                    leaf event {
                        type types-log:ethring-events;
                        description "Log event as a trigger for one or more EHS handlers";
                    }

                    ///nokia-state/state/log/log-events/ering/event-id
                    leaf event-id {
                        type types-log:log-event-id;
                        description
                            "Unique arbitrary identifier for indexing event type entries within
                             an event generator application.";
                    }

                    ///nokia-state/state/log/log-events/ering/parameters
                    leaf-list parameters {
                        type types-sros:named-item;
                        description
                            "Indicates an event's specific parameters. These parameters can
                             be passed from a triggering event to its triggered EHS script.";
                    }

                    ///nokia-state/state/log/log-events/ering/statistics
                    container statistics {
                        description "Enter the statistics context";

                        ///nokia-state/state/log/log-events/ering/statistics/count
                        leaf count {
                            type yang:counter32;
                            description "Number of times an event of this type has been generated.";
                        }

                        ///nokia-state/state/log/log-events/ering/statistics/drop
                        leaf drop {
                            type yang:counter32;
                            description "Indicates the number of times an event of this type has been dropped.";
                        }

                    } // container statistics

                } // list ering

                ///nokia-state/state/log/log-events/eth-cfm
                list eth-cfm {
                    key "event";
                    description "Enter the eth-cfm list instance";

                    ///nokia-state/state/log/log-events/eth-cfm/event
                    leaf event {
                        type types-log:ethcfm-events;
                        description "Log event as a trigger for one or more EHS handlers";
                    }

                    ///nokia-state/state/log/log-events/eth-cfm/event-id
                    leaf event-id {
                        type types-log:log-event-id;
                        description
                            "Unique arbitrary identifier for indexing event type entries within
                             an event generator application.";
                    }

                    ///nokia-state/state/log/log-events/eth-cfm/parameters
                    leaf-list parameters {
                        type types-sros:named-item;
                        description
                            "Indicates an event's specific parameters. These parameters can
                             be passed from a triggering event to its triggered EHS script.";
                    }

                    ///nokia-state/state/log/log-events/eth-cfm/statistics
                    container statistics {
                        description "Enter the statistics context";

                        ///nokia-state/state/log/log-events/eth-cfm/statistics/count
                        leaf count {
                            type yang:counter32;
                            description "Number of times an event of this type has been generated.";
                        }

                        ///nokia-state/state/log/log-events/eth-cfm/statistics/drop
                        leaf drop {
                            type yang:counter32;
                            description "Indicates the number of times an event of this type has been dropped.";
                        }

                    } // container statistics

                } // list eth-cfm

                ///nokia-state/state/log/log-events/etun
                list etun {
                    key "event";
                    description "Enter the etun list instance";

                    ///nokia-state/state/log/log-events/etun/event
                    leaf event {
                        type types-log:etun-events;
                        description "Log event as a trigger for one or more EHS handlers";
                    }

                    ///nokia-state/state/log/log-events/etun/event-id
                    leaf event-id {
                        type types-log:log-event-id;
                        description
                            "Unique arbitrary identifier for indexing event type entries within
                             an event generator application.";
                    }

                    ///nokia-state/state/log/log-events/etun/parameters
                    leaf-list parameters {
                        type types-sros:named-item;
                        description
                            "Indicates an event's specific parameters. These parameters can
                             be passed from a triggering event to its triggered EHS script.";
                    }

                    ///nokia-state/state/log/log-events/etun/statistics
                    container statistics {
                        description "Enter the statistics context";

                        ///nokia-state/state/log/log-events/etun/statistics/count
                        leaf count {
                            type yang:counter32;
                            description "Number of times an event of this type has been generated.";
                        }

                        ///nokia-state/state/log/log-events/etun/statistics/drop
                        leaf drop {
                            type yang:counter32;
                            description "Indicates the number of times an event of this type has been dropped.";
                        }

                    } // container statistics

                } // list etun

                ///nokia-state/state/log/log-events/filter
                list filter {
                    key "event";
                    description "Enter the filter list instance";

                    ///nokia-state/state/log/log-events/filter/event
                    leaf event {
                        type types-log:filter-events;
                        description "Log event as a trigger for one or more EHS handlers";
                    }

                    ///nokia-state/state/log/log-events/filter/event-id
                    leaf event-id {
                        type types-log:log-event-id;
                        description
                            "Unique arbitrary identifier for indexing event type entries within
                             an event generator application.";
                    }

                    ///nokia-state/state/log/log-events/filter/parameters
                    leaf-list parameters {
                        type types-sros:named-item;
                        description
                            "Indicates an event's specific parameters. These parameters can
                             be passed from a triggering event to its triggered EHS script.";
                    }

                    ///nokia-state/state/log/log-events/filter/statistics
                    container statistics {
                        description "Enter the statistics context";

                        ///nokia-state/state/log/log-events/filter/statistics/count
                        leaf count {
                            type yang:counter32;
                            description "Number of times an event of this type has been generated.";
                        }

                        ///nokia-state/state/log/log-events/filter/statistics/drop
                        leaf drop {
                            type yang:counter32;
                            description "Indicates the number of times an event of this type has been dropped.";
                        }

                    } // container statistics

                } // list filter

                ///nokia-state/state/log/log-events/gsmp
                list gsmp {
                    key "event";
                    description "Enter the gsmp list instance";

                    ///nokia-state/state/log/log-events/gsmp/event
                    leaf event {
                        type types-log:gsmp-events;
                        description "Log event as a trigger for one or more EHS handlers";
                    }

                    ///nokia-state/state/log/log-events/gsmp/event-id
                    leaf event-id {
                        type types-log:log-event-id;
                        description
                            "Unique arbitrary identifier for indexing event type entries within
                             an event generator application.";
                    }

                    ///nokia-state/state/log/log-events/gsmp/parameters
                    leaf-list parameters {
                        type types-sros:named-item;
                        description
                            "Indicates an event's specific parameters. These parameters can
                             be passed from a triggering event to its triggered EHS script.";
                    }

                    ///nokia-state/state/log/log-events/gsmp/statistics
                    container statistics {
                        description "Enter the statistics context";

                        ///nokia-state/state/log/log-events/gsmp/statistics/count
                        leaf count {
                            type yang:counter32;
                            description "Number of times an event of this type has been generated.";
                        }

                        ///nokia-state/state/log/log-events/gsmp/statistics/drop
                        leaf drop {
                            type yang:counter32;
                            description "Indicates the number of times an event of this type has been dropped.";
                        }

                    } // container statistics

                } // list gsmp

                ///nokia-state/state/log/log-events/igmp
                list igmp {
                    key "event";
                    description "Enter the igmp list instance";

                    ///nokia-state/state/log/log-events/igmp/event
                    leaf event {
                        type types-log:igmp-events;
                        description "Log event as a trigger for one or more EHS handlers";
                    }

                    ///nokia-state/state/log/log-events/igmp/event-id
                    leaf event-id {
                        type types-log:log-event-id;
                        description
                            "Unique arbitrary identifier for indexing event type entries within
                             an event generator application.";
                    }

                    ///nokia-state/state/log/log-events/igmp/parameters
                    leaf-list parameters {
                        type types-sros:named-item;
                        description
                            "Indicates an event's specific parameters. These parameters can
                             be passed from a triggering event to its triggered EHS script.";
                    }

                    ///nokia-state/state/log/log-events/igmp/statistics
                    container statistics {
                        description "Enter the statistics context";

                        ///nokia-state/state/log/log-events/igmp/statistics/count
                        leaf count {
                            type yang:counter32;
                            description "Number of times an event of this type has been generated.";
                        }

                        ///nokia-state/state/log/log-events/igmp/statistics/drop
                        leaf drop {
                            type yang:counter32;
                            description "Indicates the number of times an event of this type has been dropped.";
                        }

                    } // container statistics

                } // list igmp

                ///nokia-state/state/log/log-events/igmp-snooping
                list igmp-snooping {
                    key "event";
                    description "Enter the igmp-snooping list instance";

                    ///nokia-state/state/log/log-events/igmp-snooping/event
                    leaf event {
                        type types-log:igmp-snooping-events;
                        description "Log event as a trigger for one or more EHS handlers";
                    }

                    ///nokia-state/state/log/log-events/igmp-snooping/event-id
                    leaf event-id {
                        type types-log:log-event-id;
                        description
                            "Unique arbitrary identifier for indexing event type entries within
                             an event generator application.";
                    }

                    ///nokia-state/state/log/log-events/igmp-snooping/parameters
                    leaf-list parameters {
                        type types-sros:named-item;
                        description
                            "Indicates an event's specific parameters. These parameters can
                             be passed from a triggering event to its triggered EHS script.";
                    }

                    ///nokia-state/state/log/log-events/igmp-snooping/statistics
                    container statistics {
                        description "Enter the statistics context";

                        ///nokia-state/state/log/log-events/igmp-snooping/statistics/count
                        leaf count {
                            type yang:counter32;
                            description "Number of times an event of this type has been generated.";
                        }

                        ///nokia-state/state/log/log-events/igmp-snooping/statistics/drop
                        leaf drop {
                            type yang:counter32;
                            description "Indicates the number of times an event of this type has been dropped.";
                        }

                    } // container statistics

                } // list igmp-snooping

                ///nokia-state/state/log/log-events/ip
                list ip {
                    key "event";
                    description "Enter the ip list instance";

                    ///nokia-state/state/log/log-events/ip/event
                    leaf event {
                        type types-log:ip-events;
                        description "Log event as a trigger for one or more EHS handlers";
                    }

                    ///nokia-state/state/log/log-events/ip/event-id
                    leaf event-id {
                        type types-log:log-event-id;
                        description
                            "Unique arbitrary identifier for indexing event type entries within
                             an event generator application.";
                    }

                    ///nokia-state/state/log/log-events/ip/parameters
                    leaf-list parameters {
                        type types-sros:named-item;
                        description
                            "Indicates an event's specific parameters. These parameters can
                             be passed from a triggering event to its triggered EHS script.";
                    }

                    ///nokia-state/state/log/log-events/ip/statistics
                    container statistics {
                        description "Enter the statistics context";

                        ///nokia-state/state/log/log-events/ip/statistics/count
                        leaf count {
                            type yang:counter32;
                            description "Number of times an event of this type has been generated.";
                        }

                        ///nokia-state/state/log/log-events/ip/statistics/drop
                        leaf drop {
                            type yang:counter32;
                            description "Indicates the number of times an event of this type has been dropped.";
                        }

                    } // container statistics

                } // list ip

                ///nokia-state/state/log/log-events/ipsec
                list ipsec {
                    key "event";
                    description "Enter the ipsec list instance";

                    ///nokia-state/state/log/log-events/ipsec/event
                    leaf event {
                        type types-log:ipsec-events;
                        description "Log event as a trigger for one or more EHS handlers";
                    }

                    ///nokia-state/state/log/log-events/ipsec/event-id
                    leaf event-id {
                        type types-log:log-event-id;
                        description
                            "Unique arbitrary identifier for indexing event type entries within
                             an event generator application.";
                    }

                    ///nokia-state/state/log/log-events/ipsec/parameters
                    leaf-list parameters {
                        type types-sros:named-item;
                        description
                            "Indicates an event's specific parameters. These parameters can
                             be passed from a triggering event to its triggered EHS script.";
                    }

                    ///nokia-state/state/log/log-events/ipsec/statistics
                    container statistics {
                        description "Enter the statistics context";

                        ///nokia-state/state/log/log-events/ipsec/statistics/count
                        leaf count {
                            type yang:counter32;
                            description "Number of times an event of this type has been generated.";
                        }

                        ///nokia-state/state/log/log-events/ipsec/statistics/drop
                        leaf drop {
                            type yang:counter32;
                            description "Indicates the number of times an event of this type has been dropped.";
                        }

                    } // container statistics

                } // list ipsec

                ///nokia-state/state/log/log-events/isis
                list isis {
                    key "event";
                    description "Enter the isis list instance";

                    ///nokia-state/state/log/log-events/isis/event
                    leaf event {
                        type types-log:isis-events;
                        description "Log event as a trigger for one or more EHS handlers";
                    }

                    ///nokia-state/state/log/log-events/isis/event-id
                    leaf event-id {
                        type types-log:log-event-id;
                        description
                            "Unique arbitrary identifier for indexing event type entries within
                             an event generator application.";
                    }

                    ///nokia-state/state/log/log-events/isis/parameters
                    leaf-list parameters {
                        type types-sros:named-item;
                        description
                            "Indicates an event's specific parameters. These parameters can
                             be passed from a triggering event to its triggered EHS script.";
                    }

                    ///nokia-state/state/log/log-events/isis/statistics
                    container statistics {
                        description "Enter the statistics context";

                        ///nokia-state/state/log/log-events/isis/statistics/count
                        leaf count {
                            type yang:counter32;
                            description "Number of times an event of this type has been generated.";
                        }

                        ///nokia-state/state/log/log-events/isis/statistics/drop
                        leaf drop {
                            type yang:counter32;
                            description "Indicates the number of times an event of this type has been dropped.";
                        }

                    } // container statistics

                } // list isis

                ///nokia-state/state/log/log-events/l2tp
                list l2tp {
                    key "event";
                    description "Enter the l2tp list instance";

                    ///nokia-state/state/log/log-events/l2tp/event
                    leaf event {
                        type types-log:l2tp-events;
                        description "Log event as a trigger for one or more EHS handlers";
                    }

                    ///nokia-state/state/log/log-events/l2tp/event-id
                    leaf event-id {
                        type types-log:log-event-id;
                        description
                            "Unique arbitrary identifier for indexing event type entries within
                             an event generator application.";
                    }

                    ///nokia-state/state/log/log-events/l2tp/parameters
                    leaf-list parameters {
                        type types-sros:named-item;
                        description
                            "Indicates an event's specific parameters. These parameters can
                             be passed from a triggering event to its triggered EHS script.";
                    }

                    ///nokia-state/state/log/log-events/l2tp/statistics
                    container statistics {
                        description "Enter the statistics context";

                        ///nokia-state/state/log/log-events/l2tp/statistics/count
                        leaf count {
                            type yang:counter32;
                            description "Number of times an event of this type has been generated.";
                        }

                        ///nokia-state/state/log/log-events/l2tp/statistics/drop
                        leaf drop {
                            type yang:counter32;
                            description "Indicates the number of times an event of this type has been dropped.";
                        }

                    } // container statistics

                } // list l2tp

                ///nokia-state/state/log/log-events/lag
                list lag {
                    key "event";
                    description "Enter the lag list instance";

                    ///nokia-state/state/log/log-events/lag/event
                    leaf event {
                        type types-log:lag-events;
                        description "Log event as a trigger for one or more EHS handlers";
                    }

                    ///nokia-state/state/log/log-events/lag/event-id
                    leaf event-id {
                        type types-log:log-event-id;
                        description
                            "Unique arbitrary identifier for indexing event type entries within
                             an event generator application.";
                    }

                    ///nokia-state/state/log/log-events/lag/parameters
                    leaf-list parameters {
                        type types-sros:named-item;
                        description
                            "Indicates an event's specific parameters. These parameters can
                             be passed from a triggering event to its triggered EHS script.";
                    }

                    ///nokia-state/state/log/log-events/lag/statistics
                    container statistics {
                        description "Enter the statistics context";

                        ///nokia-state/state/log/log-events/lag/statistics/count
                        leaf count {
                            type yang:counter32;
                            description "Number of times an event of this type has been generated.";
                        }

                        ///nokia-state/state/log/log-events/lag/statistics/drop
                        leaf drop {
                            type yang:counter32;
                            description "Indicates the number of times an event of this type has been dropped.";
                        }

                    } // container statistics

                } // list lag

                ///nokia-state/state/log/log-events/ldap
                list ldap {
                    key "event";
                    description "Enter the ldap list instance";

                    ///nokia-state/state/log/log-events/ldap/event
                    leaf event {
                        type types-log:ldap-events;
                        description "Log event as a trigger for one or more EHS handlers";
                    }

                    ///nokia-state/state/log/log-events/ldap/event-id
                    leaf event-id {
                        type types-log:log-event-id;
                        description
                            "Unique arbitrary identifier for indexing event type entries within
                             an event generator application.";
                    }

                    ///nokia-state/state/log/log-events/ldap/parameters
                    leaf-list parameters {
                        type types-sros:named-item;
                        description
                            "Indicates an event's specific parameters. These parameters can
                             be passed from a triggering event to its triggered EHS script.";
                    }

                    ///nokia-state/state/log/log-events/ldap/statistics
                    container statistics {
                        description "Enter the statistics context";

                        ///nokia-state/state/log/log-events/ldap/statistics/count
                        leaf count {
                            type yang:counter32;
                            description "Number of times an event of this type has been generated.";
                        }

                        ///nokia-state/state/log/log-events/ldap/statistics/drop
                        leaf drop {
                            type yang:counter32;
                            description "Indicates the number of times an event of this type has been dropped.";
                        }

                    } // container statistics

                } // list ldap

                ///nokia-state/state/log/log-events/ldp
                list ldp {
                    key "event";
                    description "Enter the ldp list instance";

                    ///nokia-state/state/log/log-events/ldp/event
                    leaf event {
                        type types-log:ldp-events;
                        description "Log event as a trigger for one or more EHS handlers";
                    }

                    ///nokia-state/state/log/log-events/ldp/event-id
                    leaf event-id {
                        type types-log:log-event-id;
                        description
                            "Unique arbitrary identifier for indexing event type entries within
                             an event generator application.";
                    }

                    ///nokia-state/state/log/log-events/ldp/parameters
                    leaf-list parameters {
                        type types-sros:named-item;
                        description
                            "Indicates an event's specific parameters. These parameters can
                             be passed from a triggering event to its triggered EHS script.";
                    }

                    ///nokia-state/state/log/log-events/ldp/statistics
                    container statistics {
                        description "Enter the statistics context";

                        ///nokia-state/state/log/log-events/ldp/statistics/count
                        leaf count {
                            type yang:counter32;
                            description "Number of times an event of this type has been generated.";
                        }

                        ///nokia-state/state/log/log-events/ldp/statistics/drop
                        leaf drop {
                            type yang:counter32;
                            description "Indicates the number of times an event of this type has been dropped.";
                        }

                    } // container statistics

                } // list ldp

                ///nokia-state/state/log/log-events/li
                list li {
                    key "event";
                    description "Enter the li list instance";

                    ///nokia-state/state/log/log-events/li/event
                    leaf event {
                        type types-log:li-events;
                        description "Log event as a trigger for one or more EHS handlers";
                    }

                    ///nokia-state/state/log/log-events/li/event-id
                    leaf event-id {
                        type types-log:log-event-id;
                        description
                            "Unique arbitrary identifier for indexing event type entries within
                             an event generator application.";
                    }

                    ///nokia-state/state/log/log-events/li/parameters
                    leaf-list parameters {
                        type types-sros:named-item;
                        description
                            "Indicates an event's specific parameters. These parameters can
                             be passed from a triggering event to its triggered EHS script.";
                    }

                    ///nokia-state/state/log/log-events/li/statistics
                    container statistics {
                        description "Enter the statistics context";

                        ///nokia-state/state/log/log-events/li/statistics/count
                        leaf count {
                            type yang:counter32;
                            description "Number of times an event of this type has been generated.";
                        }

                        ///nokia-state/state/log/log-events/li/statistics/drop
                        leaf drop {
                            type yang:counter32;
                            description "Indicates the number of times an event of this type has been dropped.";
                        }

                    } // container statistics

                } // list li

                ///nokia-state/state/log/log-events/lldp
                list lldp {
                    key "event";
                    description "Enter the lldp list instance";

                    ///nokia-state/state/log/log-events/lldp/event
                    leaf event {
                        type types-log:lldp-events;
                        description "Log event as a trigger for one or more EHS handlers";
                    }

                    ///nokia-state/state/log/log-events/lldp/event-id
                    leaf event-id {
                        type types-log:log-event-id;
                        description
                            "Unique arbitrary identifier for indexing event type entries within
                             an event generator application.";
                    }

                    ///nokia-state/state/log/log-events/lldp/parameters
                    leaf-list parameters {
                        type types-sros:named-item;
                        description
                            "Indicates an event's specific parameters. These parameters can
                             be passed from a triggering event to its triggered EHS script.";
                    }

                    ///nokia-state/state/log/log-events/lldp/statistics
                    container statistics {
                        description "Enter the statistics context";

                        ///nokia-state/state/log/log-events/lldp/statistics/count
                        leaf count {
                            type yang:counter32;
                            description "Number of times an event of this type has been generated.";
                        }

                        ///nokia-state/state/log/log-events/lldp/statistics/drop
                        leaf drop {
                            type yang:counter32;
                            description "Indicates the number of times an event of this type has been dropped.";
                        }

                    } // container statistics

                } // list lldp

                ///nokia-state/state/log/log-events/logger
                list logger {
                    key "event";
                    description "Enter the logger list instance";

                    ///nokia-state/state/log/log-events/logger/event
                    leaf event {
                        type types-log:logger-events;
                        description "Log event as a trigger for one or more EHS handlers";
                    }

                    ///nokia-state/state/log/log-events/logger/event-id
                    leaf event-id {
                        type types-log:log-event-id;
                        description
                            "Unique arbitrary identifier for indexing event type entries within
                             an event generator application.";
                    }

                    ///nokia-state/state/log/log-events/logger/parameters
                    leaf-list parameters {
                        type types-sros:named-item;
                        description
                            "Indicates an event's specific parameters. These parameters can
                             be passed from a triggering event to its triggered EHS script.";
                    }

                    ///nokia-state/state/log/log-events/logger/statistics
                    container statistics {
                        description "Enter the statistics context";

                        ///nokia-state/state/log/log-events/logger/statistics/count
                        leaf count {
                            type yang:counter32;
                            description "Number of times an event of this type has been generated.";
                        }

                        ///nokia-state/state/log/log-events/logger/statistics/drop
                        leaf drop {
                            type yang:counter32;
                            description "Indicates the number of times an event of this type has been dropped.";
                        }

                    } // container statistics

                } // list logger

                ///nokia-state/state/log/log-events/macsec
                list macsec {
                    key "event";
                    description "Enter the macsec list instance";

                    ///nokia-state/state/log/log-events/macsec/event
                    leaf event {
                        type types-log:macsec-events;
                        description "Log event as a trigger for one or more EHS handlers";
                    }

                    ///nokia-state/state/log/log-events/macsec/event-id
                    leaf event-id {
                        type types-log:log-event-id;
                        description
                            "Unique arbitrary identifier for indexing event type entries within
                             an event generator application.";
                    }

                    ///nokia-state/state/log/log-events/macsec/parameters
                    leaf-list parameters {
                        type types-sros:named-item;
                        description
                            "Indicates an event's specific parameters. These parameters can
                             be passed from a triggering event to its triggered EHS script.";
                    }

                    ///nokia-state/state/log/log-events/macsec/statistics
                    container statistics {
                        description "Enter the statistics context";

                        ///nokia-state/state/log/log-events/macsec/statistics/count
                        leaf count {
                            type yang:counter32;
                            description "Number of times an event of this type has been generated.";
                        }

                        ///nokia-state/state/log/log-events/macsec/statistics/drop
                        leaf drop {
                            type yang:counter32;
                            description "Indicates the number of times an event of this type has been dropped.";
                        }

                    } // container statistics

                } // list macsec

                ///nokia-state/state/log/log-events/mcpath
                list mcpath {
                    key "event";
                    description "Enter the mcpath list instance";

                    ///nokia-state/state/log/log-events/mcpath/event
                    leaf event {
                        type types-log:mcpath-events;
                        description "Log event as a trigger for one or more EHS handlers";
                    }

                    ///nokia-state/state/log/log-events/mcpath/event-id
                    leaf event-id {
                        type types-log:log-event-id;
                        description
                            "Unique arbitrary identifier for indexing event type entries within
                             an event generator application.";
                    }

                    ///nokia-state/state/log/log-events/mcpath/parameters
                    leaf-list parameters {
                        type types-sros:named-item;
                        description
                            "Indicates an event's specific parameters. These parameters can
                             be passed from a triggering event to its triggered EHS script.";
                    }

                    ///nokia-state/state/log/log-events/mcpath/statistics
                    container statistics {
                        description "Enter the statistics context";

                        ///nokia-state/state/log/log-events/mcpath/statistics/count
                        leaf count {
                            type yang:counter32;
                            description "Number of times an event of this type has been generated.";
                        }

                        ///nokia-state/state/log/log-events/mcpath/statistics/drop
                        leaf drop {
                            type yang:counter32;
                            description "Indicates the number of times an event of this type has been dropped.";
                        }

                    } // container statistics

                } // list mcpath

                ///nokia-state/state/log/log-events/mc-redundancy
                list mc-redundancy {
                    key "event";
                    description "Enter the mc-redundancy list instance";

                    ///nokia-state/state/log/log-events/mc-redundancy/event
                    leaf event {
                        type types-log:mc-redundancy-events;
                        description "Log event as a trigger for one or more EHS handlers";
                    }

                    ///nokia-state/state/log/log-events/mc-redundancy/event-id
                    leaf event-id {
                        type types-log:log-event-id;
                        description
                            "Unique arbitrary identifier for indexing event type entries within
                             an event generator application.";
                    }

                    ///nokia-state/state/log/log-events/mc-redundancy/parameters
                    leaf-list parameters {
                        type types-sros:named-item;
                        description
                            "Indicates an event's specific parameters. These parameters can
                             be passed from a triggering event to its triggered EHS script.";
                    }

                    ///nokia-state/state/log/log-events/mc-redundancy/statistics
                    container statistics {
                        description "Enter the statistics context";

                        ///nokia-state/state/log/log-events/mc-redundancy/statistics/count
                        leaf count {
                            type yang:counter32;
                            description "Number of times an event of this type has been generated.";
                        }

                        ///nokia-state/state/log/log-events/mc-redundancy/statistics/drop
                        leaf drop {
                            type yang:counter32;
                            description "Indicates the number of times an event of this type has been dropped.";
                        }

                    } // container statistics

                } // list mc-redundancy

                ///nokia-state/state/log/log-events/mgmt-core
                list mgmt-core {
                    key "event";
                    description "Enter the mgmt-core list instance";

                    ///nokia-state/state/log/log-events/mgmt-core/event
                    leaf event {
                        type types-log:mgmt-core-events;
                        description "Log event as a trigger for one or more EHS handlers";
                    }

                    ///nokia-state/state/log/log-events/mgmt-core/event-id
                    leaf event-id {
                        type types-log:log-event-id;
                        description
                            "Unique arbitrary identifier for indexing event type entries within
                             an event generator application.";
                    }

                    ///nokia-state/state/log/log-events/mgmt-core/parameters
                    leaf-list parameters {
                        type types-sros:named-item;
                        description
                            "Indicates an event's specific parameters. These parameters can
                             be passed from a triggering event to its triggered EHS script.";
                    }

                    ///nokia-state/state/log/log-events/mgmt-core/statistics
                    container statistics {
                        description "Enter the statistics context";

                        ///nokia-state/state/log/log-events/mgmt-core/statistics/count
                        leaf count {
                            type yang:counter32;
                            description "Number of times an event of this type has been generated.";
                        }

                        ///nokia-state/state/log/log-events/mgmt-core/statistics/drop
                        leaf drop {
                            type yang:counter32;
                            description "Indicates the number of times an event of this type has been dropped.";
                        }

                    } // container statistics

                } // list mgmt-core

                ///nokia-state/state/log/log-events/mirror
                list mirror {
                    key "event";
                    description "Enter the mirror list instance";

                    ///nokia-state/state/log/log-events/mirror/event
                    leaf event {
                        type types-log:mirror-events;
                        description "Log event as a trigger for one or more EHS handlers";
                    }

                    ///nokia-state/state/log/log-events/mirror/event-id
                    leaf event-id {
                        type types-log:log-event-id;
                        description
                            "Unique arbitrary identifier for indexing event type entries within
                             an event generator application.";
                    }

                    ///nokia-state/state/log/log-events/mirror/parameters
                    leaf-list parameters {
                        type types-sros:named-item;
                        description
                            "Indicates an event's specific parameters. These parameters can
                             be passed from a triggering event to its triggered EHS script.";
                    }

                    ///nokia-state/state/log/log-events/mirror/statistics
                    container statistics {
                        description "Enter the statistics context";

                        ///nokia-state/state/log/log-events/mirror/statistics/count
                        leaf count {
                            type yang:counter32;
                            description "Number of times an event of this type has been generated.";
                        }

                        ///nokia-state/state/log/log-events/mirror/statistics/drop
                        leaf drop {
                            type yang:counter32;
                            description "Indicates the number of times an event of this type has been dropped.";
                        }

                    } // container statistics

                } // list mirror

                ///nokia-state/state/log/log-events/mld
                list mld {
                    key "event";
                    description "Enter the mld list instance";

                    ///nokia-state/state/log/log-events/mld/event
                    leaf event {
                        type types-log:mld-events;
                        description "Log event as a trigger for one or more EHS handlers";
                    }

                    ///nokia-state/state/log/log-events/mld/event-id
                    leaf event-id {
                        type types-log:log-event-id;
                        description
                            "Unique arbitrary identifier for indexing event type entries within
                             an event generator application.";
                    }

                    ///nokia-state/state/log/log-events/mld/parameters
                    leaf-list parameters {
                        type types-sros:named-item;
                        description
                            "Indicates an event's specific parameters. These parameters can
                             be passed from a triggering event to its triggered EHS script.";
                    }

                    ///nokia-state/state/log/log-events/mld/statistics
                    container statistics {
                        description "Enter the statistics context";

                        ///nokia-state/state/log/log-events/mld/statistics/count
                        leaf count {
                            type yang:counter32;
                            description "Number of times an event of this type has been generated.";
                        }

                        ///nokia-state/state/log/log-events/mld/statistics/drop
                        leaf drop {
                            type yang:counter32;
                            description "Indicates the number of times an event of this type has been dropped.";
                        }

                    } // container statistics

                } // list mld

                ///nokia-state/state/log/log-events/mld-snooping
                list mld-snooping {
                    key "event";
                    description "Enter the mld-snooping list instance";

                    ///nokia-state/state/log/log-events/mld-snooping/event
                    leaf event {
                        type types-log:mld-snooping-events;
                        description "Log event as a trigger for one or more EHS handlers";
                    }

                    ///nokia-state/state/log/log-events/mld-snooping/event-id
                    leaf event-id {
                        type types-log:log-event-id;
                        description
                            "Unique arbitrary identifier for indexing event type entries within
                             an event generator application.";
                    }

                    ///nokia-state/state/log/log-events/mld-snooping/parameters
                    leaf-list parameters {
                        type types-sros:named-item;
                        description
                            "Indicates an event's specific parameters. These parameters can
                             be passed from a triggering event to its triggered EHS script.";
                    }

                    ///nokia-state/state/log/log-events/mld-snooping/statistics
                    container statistics {
                        description "Enter the statistics context";

                        ///nokia-state/state/log/log-events/mld-snooping/statistics/count
                        leaf count {
                            type yang:counter32;
                            description "Number of times an event of this type has been generated.";
                        }

                        ///nokia-state/state/log/log-events/mld-snooping/statistics/drop
                        leaf drop {
                            type yang:counter32;
                            description "Indicates the number of times an event of this type has been dropped.";
                        }

                    } // container statistics

                } // list mld-snooping

                ///nokia-state/state/log/log-events/mpls
                list mpls {
                    key "event";
                    description "Enter the mpls list instance";

                    ///nokia-state/state/log/log-events/mpls/event
                    leaf event {
                        type types-log:mpls-events;
                        description "Log event as a trigger for one or more EHS handlers";
                    }

                    ///nokia-state/state/log/log-events/mpls/event-id
                    leaf event-id {
                        type types-log:log-event-id;
                        description
                            "Unique arbitrary identifier for indexing event type entries within
                             an event generator application.";
                    }

                    ///nokia-state/state/log/log-events/mpls/parameters
                    leaf-list parameters {
                        type types-sros:named-item;
                        description
                            "Indicates an event's specific parameters. These parameters can
                             be passed from a triggering event to its triggered EHS script.";
                    }

                    ///nokia-state/state/log/log-events/mpls/statistics
                    container statistics {
                        description "Enter the statistics context";

                        ///nokia-state/state/log/log-events/mpls/statistics/count
                        leaf count {
                            type yang:counter32;
                            description "Number of times an event of this type has been generated.";
                        }

                        ///nokia-state/state/log/log-events/mpls/statistics/drop
                        leaf drop {
                            type yang:counter32;
                            description "Indicates the number of times an event of this type has been dropped.";
                        }

                    } // container statistics

                } // list mpls

                ///nokia-state/state/log/log-events/mpls-tp
                list mpls-tp {
                    key "event";
                    description "Enter the mpls-tp list instance";

                    ///nokia-state/state/log/log-events/mpls-tp/event
                    leaf event {
                        type types-log:mpls-tp-events;
                        description "Log event as a trigger for one or more EHS handlers";
                    }

                    ///nokia-state/state/log/log-events/mpls-tp/event-id
                    leaf event-id {
                        type types-log:log-event-id;
                        description
                            "Unique arbitrary identifier for indexing event type entries within
                             an event generator application.";
                    }

                    ///nokia-state/state/log/log-events/mpls-tp/parameters
                    leaf-list parameters {
                        type types-sros:named-item;
                        description
                            "Indicates an event's specific parameters. These parameters can
                             be passed from a triggering event to its triggered EHS script.";
                    }

                    ///nokia-state/state/log/log-events/mpls-tp/statistics
                    container statistics {
                        description "Enter the statistics context";

                        ///nokia-state/state/log/log-events/mpls-tp/statistics/count
                        leaf count {
                            type yang:counter32;
                            description "Number of times an event of this type has been generated.";
                        }

                        ///nokia-state/state/log/log-events/mpls-tp/statistics/drop
                        leaf drop {
                            type yang:counter32;
                            description "Indicates the number of times an event of this type has been dropped.";
                        }

                    } // container statistics

                } // list mpls-tp

                ///nokia-state/state/log/log-events/msdp
                list msdp {
                    key "event";
                    description "Enter the msdp list instance";

                    ///nokia-state/state/log/log-events/msdp/event
                    leaf event {
                        type types-log:msdp-events;
                        description "Log event as a trigger for one or more EHS handlers";
                    }

                    ///nokia-state/state/log/log-events/msdp/event-id
                    leaf event-id {
                        type types-log:log-event-id;
                        description
                            "Unique arbitrary identifier for indexing event type entries within
                             an event generator application.";
                    }

                    ///nokia-state/state/log/log-events/msdp/parameters
                    leaf-list parameters {
                        type types-sros:named-item;
                        description
                            "Indicates an event's specific parameters. These parameters can
                             be passed from a triggering event to its triggered EHS script.";
                    }

                    ///nokia-state/state/log/log-events/msdp/statistics
                    container statistics {
                        description "Enter the statistics context";

                        ///nokia-state/state/log/log-events/msdp/statistics/count
                        leaf count {
                            type yang:counter32;
                            description "Number of times an event of this type has been generated.";
                        }

                        ///nokia-state/state/log/log-events/msdp/statistics/drop
                        leaf drop {
                            type yang:counter32;
                            description "Indicates the number of times an event of this type has been dropped.";
                        }

                    } // container statistics

                } // list msdp

                ///nokia-state/state/log/log-events/nat
                list nat {
                    key "event";
                    description "Enter the nat list instance";

                    ///nokia-state/state/log/log-events/nat/event
                    leaf event {
                        type types-log:nat-events;
                        description "Log event as a trigger for one or more EHS handlers";
                    }

                    ///nokia-state/state/log/log-events/nat/event-id
                    leaf event-id {
                        type types-log:log-event-id;
                        description
                            "Unique arbitrary identifier for indexing event type entries within
                             an event generator application.";
                    }

                    ///nokia-state/state/log/log-events/nat/parameters
                    leaf-list parameters {
                        type types-sros:named-item;
                        description
                            "Indicates an event's specific parameters. These parameters can
                             be passed from a triggering event to its triggered EHS script.";
                    }

                    ///nokia-state/state/log/log-events/nat/statistics
                    container statistics {
                        description "Enter the statistics context";

                        ///nokia-state/state/log/log-events/nat/statistics/count
                        leaf count {
                            type yang:counter32;
                            description "Number of times an event of this type has been generated.";
                        }

                        ///nokia-state/state/log/log-events/nat/statistics/drop
                        leaf drop {
                            type yang:counter32;
                            description "Indicates the number of times an event of this type has been dropped.";
                        }

                    } // container statistics

                } // list nat

                ///nokia-state/state/log/log-events/ntp
                list ntp {
                    key "event";
                    description "Enter the ntp list instance";

                    ///nokia-state/state/log/log-events/ntp/event
                    leaf event {
                        type types-log:ntp-events;
                        description "Log event as a trigger for one or more EHS handlers";
                    }

                    ///nokia-state/state/log/log-events/ntp/event-id
                    leaf event-id {
                        type types-log:log-event-id;
                        description
                            "Unique arbitrary identifier for indexing event type entries within
                             an event generator application.";
                    }

                    ///nokia-state/state/log/log-events/ntp/parameters
                    leaf-list parameters {
                        type types-sros:named-item;
                        description
                            "Indicates an event's specific parameters. These parameters can
                             be passed from a triggering event to its triggered EHS script.";
                    }

                    ///nokia-state/state/log/log-events/ntp/statistics
                    container statistics {
                        description "Enter the statistics context";

                        ///nokia-state/state/log/log-events/ntp/statistics/count
                        leaf count {
                            type yang:counter32;
                            description "Number of times an event of this type has been generated.";
                        }

                        ///nokia-state/state/log/log-events/ntp/statistics/drop
                        leaf drop {
                            type yang:counter32;
                            description "Indicates the number of times an event of this type has been dropped.";
                        }

                    } // container statistics

                } // list ntp

                ///nokia-state/state/log/log-events/oam
                list oam {
                    key "event";
                    description "Enter the oam list instance";

                    ///nokia-state/state/log/log-events/oam/event
                    leaf event {
                        type types-log:oam-events;
                        description "Log event as a trigger for one or more EHS handlers";
                    }

                    ///nokia-state/state/log/log-events/oam/event-id
                    leaf event-id {
                        type types-log:log-event-id;
                        description
                            "Unique arbitrary identifier for indexing event type entries within
                             an event generator application.";
                    }

                    ///nokia-state/state/log/log-events/oam/parameters
                    leaf-list parameters {
                        type types-sros:named-item;
                        description
                            "Indicates an event's specific parameters. These parameters can
                             be passed from a triggering event to its triggered EHS script.";
                    }

                    ///nokia-state/state/log/log-events/oam/statistics
                    container statistics {
                        description "Enter the statistics context";

                        ///nokia-state/state/log/log-events/oam/statistics/count
                        leaf count {
                            type yang:counter32;
                            description "Number of times an event of this type has been generated.";
                        }

                        ///nokia-state/state/log/log-events/oam/statistics/drop
                        leaf drop {
                            type yang:counter32;
                            description "Indicates the number of times an event of this type has been dropped.";
                        }

                    } // container statistics

                } // list oam

                ///nokia-state/state/log/log-events/openflow
                list openflow {
                    key "event";
                    description "Enter the openflow list instance";

                    ///nokia-state/state/log/log-events/openflow/event
                    leaf event {
                        type types-log:openflow-events;
                        description "Log event as a trigger for one or more EHS handlers";
                    }

                    ///nokia-state/state/log/log-events/openflow/event-id
                    leaf event-id {
                        type types-log:log-event-id;
                        description
                            "Unique arbitrary identifier for indexing event type entries within
                             an event generator application.";
                    }

                    ///nokia-state/state/log/log-events/openflow/parameters
                    leaf-list parameters {
                        type types-sros:named-item;
                        description
                            "Indicates an event's specific parameters. These parameters can
                             be passed from a triggering event to its triggered EHS script.";
                    }

                    ///nokia-state/state/log/log-events/openflow/statistics
                    container statistics {
                        description "Enter the statistics context";

                        ///nokia-state/state/log/log-events/openflow/statistics/count
                        leaf count {
                            type yang:counter32;
                            description "Number of times an event of this type has been generated.";
                        }

                        ///nokia-state/state/log/log-events/openflow/statistics/drop
                        leaf drop {
                            type yang:counter32;
                            description "Indicates the number of times an event of this type has been dropped.";
                        }

                    } // container statistics

                } // list openflow

                ///nokia-state/state/log/log-events/ospf
                list ospf {
                    key "event";
                    description "Enter the ospf list instance";

                    ///nokia-state/state/log/log-events/ospf/event
                    leaf event {
                        type types-log:ospf-events;
                        description "Log event as a trigger for one or more EHS handlers";
                    }

                    ///nokia-state/state/log/log-events/ospf/event-id
                    leaf event-id {
                        type types-log:log-event-id;
                        description
                            "Unique arbitrary identifier for indexing event type entries within
                             an event generator application.";
                    }

                    ///nokia-state/state/log/log-events/ospf/parameters
                    leaf-list parameters {
                        type types-sros:named-item;
                        description
                            "Indicates an event's specific parameters. These parameters can
                             be passed from a triggering event to its triggered EHS script.";
                    }

                    ///nokia-state/state/log/log-events/ospf/statistics
                    container statistics {
                        description "Enter the statistics context";

                        ///nokia-state/state/log/log-events/ospf/statistics/count
                        leaf count {
                            type yang:counter32;
                            description "Number of times an event of this type has been generated.";
                        }

                        ///nokia-state/state/log/log-events/ospf/statistics/drop
                        leaf drop {
                            type yang:counter32;
                            description "Indicates the number of times an event of this type has been dropped.";
                        }

                    } // container statistics

                } // list ospf

                ///nokia-state/state/log/log-events/pcap
                list pcap {
                    key "event";
                    description "Enter the pcap list instance";

                    ///nokia-state/state/log/log-events/pcap/event
                    leaf event {
                        type types-log:pcap-events;
                        description "Log event as a trigger for one or more EHS handlers";
                    }

                    ///nokia-state/state/log/log-events/pcap/event-id
                    leaf event-id {
                        type types-log:log-event-id;
                        description
                            "Unique arbitrary identifier for indexing event type entries within
                             an event generator application.";
                    }

                    ///nokia-state/state/log/log-events/pcap/parameters
                    leaf-list parameters {
                        type types-sros:named-item;
                        description
                            "Indicates an event's specific parameters. These parameters can
                             be passed from a triggering event to its triggered EHS script.";
                    }

                    ///nokia-state/state/log/log-events/pcap/statistics
                    container statistics {
                        description "Enter the statistics context";

                        ///nokia-state/state/log/log-events/pcap/statistics/count
                        leaf count {
                            type yang:counter32;
                            description "Number of times an event of this type has been generated.";
                        }

                        ///nokia-state/state/log/log-events/pcap/statistics/drop
                        leaf drop {
                            type yang:counter32;
                            description "Indicates the number of times an event of this type has been dropped.";
                        }

                    } // container statistics

                } // list pcap

                ///nokia-state/state/log/log-events/pcep
                list pcep {
                    key "event";
                    description "Enter the pcep list instance";

                    ///nokia-state/state/log/log-events/pcep/event
                    leaf event {
                        type types-log:pcep-events;
                        description "PCEP module events";
                    }

                    ///nokia-state/state/log/log-events/pcep/event-id
                    leaf event-id {
                        type types-log:log-event-id;
                        description
                            "Unique arbitrary identifier for indexing event type entries within
                             an event generator application.";
                    }

                    ///nokia-state/state/log/log-events/pcep/parameters
                    leaf-list parameters {
                        type types-sros:named-item;
                        description
                            "Indicates an event's specific parameters. These parameters can
                             be passed from a triggering event to its triggered EHS script.";
                    }

                    ///nokia-state/state/log/log-events/pcep/statistics
                    container statistics {
                        description "Enter the statistics context";

                        ///nokia-state/state/log/log-events/pcep/statistics/count
                        leaf count {
                            type yang:counter32;
                            description "Number of times an event of this type has been generated.";
                        }

                        ///nokia-state/state/log/log-events/pcep/statistics/drop
                        leaf drop {
                            type yang:counter32;
                            description "Indicates the number of times an event of this type has been dropped.";
                        }

                    } // container statistics

                } // list pcep

                ///nokia-state/state/log/log-events/pfcp
                list pfcp {
                    key "event";
                    description "Enter the pfcp list instance";

                    ///nokia-state/state/log/log-events/pfcp/event
                    leaf event {
                        type types-log:pfcp-events;
                        description "PFCP events";
                    }

                    ///nokia-state/state/log/log-events/pfcp/event-id
                    leaf event-id {
                        type types-log:log-event-id;
                        description
                            "Unique arbitrary identifier for indexing event type entries within
                             an event generator application.";
                    }

                    ///nokia-state/state/log/log-events/pfcp/parameters
                    leaf-list parameters {
                        type types-sros:named-item;
                        description
                            "Indicates an event's specific parameters. These parameters can
                             be passed from a triggering event to its triggered EHS script.";
                    }

                    ///nokia-state/state/log/log-events/pfcp/statistics
                    container statistics {
                        description "Enter the statistics context";

                        ///nokia-state/state/log/log-events/pfcp/statistics/count
                        leaf count {
                            type yang:counter32;
                            description "Number of times an event of this type has been generated.";
                        }

                        ///nokia-state/state/log/log-events/pfcp/statistics/drop
                        leaf drop {
                            type yang:counter32;
                            description "Indicates the number of times an event of this type has been dropped.";
                        }

                    } // container statistics

                } // list pfcp

                ///nokia-state/state/log/log-events/pim
                list pim {
                    key "event";
                    description "Enter the pim list instance";

                    ///nokia-state/state/log/log-events/pim/event
                    leaf event {
                        type types-log:pim-events;
                        description "Log event as a trigger for one or more EHS handlers";
                    }

                    ///nokia-state/state/log/log-events/pim/event-id
                    leaf event-id {
                        type types-log:log-event-id;
                        description
                            "Unique arbitrary identifier for indexing event type entries within
                             an event generator application.";
                    }

                    ///nokia-state/state/log/log-events/pim/parameters
                    leaf-list parameters {
                        type types-sros:named-item;
                        description
                            "Indicates an event's specific parameters. These parameters can
                             be passed from a triggering event to its triggered EHS script.";
                    }

                    ///nokia-state/state/log/log-events/pim/statistics
                    container statistics {
                        description "Enter the statistics context";

                        ///nokia-state/state/log/log-events/pim/statistics/count
                        leaf count {
                            type yang:counter32;
                            description "Number of times an event of this type has been generated.";
                        }

                        ///nokia-state/state/log/log-events/pim/statistics/drop
                        leaf drop {
                            type yang:counter32;
                            description "Indicates the number of times an event of this type has been dropped.";
                        }

                    } // container statistics

                } // list pim

                ///nokia-state/state/log/log-events/pim-snooping
                list pim-snooping {
                    key "event";
                    description "Enter the pim-snooping list instance";

                    ///nokia-state/state/log/log-events/pim-snooping/event
                    leaf event {
                        type types-log:pim-snooping-events;
                        description "Log event as a trigger for one or more EHS handlers";
                    }

                    ///nokia-state/state/log/log-events/pim-snooping/event-id
                    leaf event-id {
                        type types-log:log-event-id;
                        description
                            "Unique arbitrary identifier for indexing event type entries within
                             an event generator application.";
                    }

                    ///nokia-state/state/log/log-events/pim-snooping/parameters
                    leaf-list parameters {
                        type types-sros:named-item;
                        description
                            "Indicates an event's specific parameters. These parameters can
                             be passed from a triggering event to its triggered EHS script.";
                    }

                    ///nokia-state/state/log/log-events/pim-snooping/statistics
                    container statistics {
                        description "Enter the statistics context";

                        ///nokia-state/state/log/log-events/pim-snooping/statistics/count
                        leaf count {
                            type yang:counter32;
                            description "Number of times an event of this type has been generated.";
                        }

                        ///nokia-state/state/log/log-events/pim-snooping/statistics/drop
                        leaf drop {
                            type yang:counter32;
                            description "Indicates the number of times an event of this type has been dropped.";
                        }

                    } // container statistics

                } // list pim-snooping

                ///nokia-state/state/log/log-events/port
                list port {
                    key "event";
                    description "Enter the port list instance";

                    ///nokia-state/state/log/log-events/port/event
                    leaf event {
                        type types-log:port-events;
                        description "Log event as a trigger for one or more EHS handlers";
                    }

                    ///nokia-state/state/log/log-events/port/event-id
                    leaf event-id {
                        type types-log:log-event-id;
                        description
                            "Unique arbitrary identifier for indexing event type entries within
                             an event generator application.";
                    }

                    ///nokia-state/state/log/log-events/port/parameters
                    leaf-list parameters {
                        type types-sros:named-item;
                        description
                            "Indicates an event's specific parameters. These parameters can
                             be passed from a triggering event to its triggered EHS script.";
                    }

                    ///nokia-state/state/log/log-events/port/statistics
                    container statistics {
                        description "Enter the statistics context";

                        ///nokia-state/state/log/log-events/port/statistics/count
                        leaf count {
                            type yang:counter32;
                            description "Number of times an event of this type has been generated.";
                        }

                        ///nokia-state/state/log/log-events/port/statistics/drop
                        leaf drop {
                            type yang:counter32;
                            description "Indicates the number of times an event of this type has been dropped.";
                        }

                    } // container statistics

                } // list port

                ///nokia-state/state/log/log-events/pppoe
                list pppoe {
                    key "event";
                    description "Enter the pppoe list instance";

                    ///nokia-state/state/log/log-events/pppoe/event
                    leaf event {
                        type types-log:pppoe-events;
                        description "Log event as a trigger for one or more EHS handlers";
                    }

                    ///nokia-state/state/log/log-events/pppoe/event-id
                    leaf event-id {
                        type types-log:log-event-id;
                        description
                            "Unique arbitrary identifier for indexing event type entries within
                             an event generator application.";
                    }

                    ///nokia-state/state/log/log-events/pppoe/parameters
                    leaf-list parameters {
                        type types-sros:named-item;
                        description
                            "Indicates an event's specific parameters. These parameters can
                             be passed from a triggering event to its triggered EHS script.";
                    }

                    ///nokia-state/state/log/log-events/pppoe/statistics
                    container statistics {
                        description "Enter the statistics context";

                        ///nokia-state/state/log/log-events/pppoe/statistics/count
                        leaf count {
                            type yang:counter32;
                            description "Number of times an event of this type has been generated.";
                        }

                        ///nokia-state/state/log/log-events/pppoe/statistics/drop
                        leaf drop {
                            type yang:counter32;
                            description "Indicates the number of times an event of this type has been dropped.";
                        }

                    } // container statistics

                } // list pppoe

                ///nokia-state/state/log/log-events/pppoe-clnt
                list pppoe-clnt {
                    key "event";
                    description "Enter the pppoe-clnt list instance";

                    ///nokia-state/state/log/log-events/pppoe-clnt/event
                    leaf event {
                        type types-log:pppoe-clnt-events;
                        description "Log event as a trigger for one or more EHS handlers";
                    }

                    ///nokia-state/state/log/log-events/pppoe-clnt/event-id
                    leaf event-id {
                        type types-log:log-event-id;
                        description
                            "Unique arbitrary identifier for indexing event type entries within
                             an event generator application.";
                    }

                    ///nokia-state/state/log/log-events/pppoe-clnt/parameters
                    leaf-list parameters {
                        type types-sros:named-item;
                        description
                            "Indicates an event's specific parameters. These parameters can
                             be passed from a triggering event to its triggered EHS script.";
                    }

                    ///nokia-state/state/log/log-events/pppoe-clnt/statistics
                    container statistics {
                        description "Enter the statistics context";

                        ///nokia-state/state/log/log-events/pppoe-clnt/statistics/count
                        leaf count {
                            type yang:counter32;
                            description "Number of times an event of this type has been generated.";
                        }

                        ///nokia-state/state/log/log-events/pppoe-clnt/statistics/drop
                        leaf drop {
                            type yang:counter32;
                            description "Indicates the number of times an event of this type has been dropped.";
                        }

                    } // container statistics

                } // list pppoe-clnt

                ///nokia-state/state/log/log-events/ptp
                list ptp {
                    key "event";
                    description "Enter the ptp list instance";

                    ///nokia-state/state/log/log-events/ptp/event
                    leaf event {
                        type types-log:ptp-events;
                        description "Log event as a trigger for one or more EHS handlers";
                    }

                    ///nokia-state/state/log/log-events/ptp/event-id
                    leaf event-id {
                        type types-log:log-event-id;
                        description
                            "Unique arbitrary identifier for indexing event type entries within
                             an event generator application.";
                    }

                    ///nokia-state/state/log/log-events/ptp/parameters
                    leaf-list parameters {
                        type types-sros:named-item;
                        description
                            "Indicates an event's specific parameters. These parameters can
                             be passed from a triggering event to its triggered EHS script.";
                    }

                    ///nokia-state/state/log/log-events/ptp/statistics
                    container statistics {
                        description "Enter the statistics context";

                        ///nokia-state/state/log/log-events/ptp/statistics/count
                        leaf count {
                            type yang:counter32;
                            description "Number of times an event of this type has been generated.";
                        }

                        ///nokia-state/state/log/log-events/ptp/statistics/drop
                        leaf drop {
                            type yang:counter32;
                            description "Indicates the number of times an event of this type has been dropped.";
                        }

                    } // container statistics

                } // list ptp

                ///nokia-state/state/log/log-events/python
                list python {
                    key "event";
                    description "Enter the python list instance";

                    ///nokia-state/state/log/log-events/python/event
                    leaf event {
                        type types-log:python-events;
                        description "Python module events";
                    }

                    ///nokia-state/state/log/log-events/python/event-id
                    leaf event-id {
                        type types-log:log-event-id;
                        description
                            "Unique arbitrary identifier for indexing event type entries within
                             an event generator application.";
                    }

                    ///nokia-state/state/log/log-events/python/parameters
                    leaf-list parameters {
                        type types-sros:named-item;
                        description
                            "Indicates an event's specific parameters. These parameters can
                             be passed from a triggering event to its triggered EHS script.";
                    }

                    ///nokia-state/state/log/log-events/python/statistics
                    container statistics {
                        description "Enter the statistics context";

                        ///nokia-state/state/log/log-events/python/statistics/count
                        leaf count {
                            type yang:counter32;
                            description "Number of times an event of this type has been generated.";
                        }

                        ///nokia-state/state/log/log-events/python/statistics/drop
                        leaf drop {
                            type yang:counter32;
                            description "Indicates the number of times an event of this type has been dropped.";
                        }

                    } // container statistics

                } // list python

                ///nokia-state/state/log/log-events/radius
                list radius {
                    key "event";
                    description "Enter the radius list instance";

                    ///nokia-state/state/log/log-events/radius/event
                    leaf event {
                        type types-log:radius-events;
                        description "Log event as a trigger for one or more EHS handlers";
                    }

                    ///nokia-state/state/log/log-events/radius/event-id
                    leaf event-id {
                        type types-log:log-event-id;
                        description
                            "Unique arbitrary identifier for indexing event type entries within
                             an event generator application.";
                    }

                    ///nokia-state/state/log/log-events/radius/parameters
                    leaf-list parameters {
                        type types-sros:named-item;
                        description
                            "Indicates an event's specific parameters. These parameters can
                             be passed from a triggering event to its triggered EHS script.";
                    }

                    ///nokia-state/state/log/log-events/radius/statistics
                    container statistics {
                        description "Enter the statistics context";

                        ///nokia-state/state/log/log-events/radius/statistics/count
                        leaf count {
                            type yang:counter32;
                            description "Number of times an event of this type has been generated.";
                        }

                        ///nokia-state/state/log/log-events/radius/statistics/drop
                        leaf drop {
                            type yang:counter32;
                            description "Indicates the number of times an event of this type has been dropped.";
                        }

                    } // container statistics

                } // list radius

                ///nokia-state/state/log/log-events/rip
                list rip {
                    key "event";
                    description "Enter the rip list instance";

                    ///nokia-state/state/log/log-events/rip/event
                    leaf event {
                        type types-log:rip-events;
                        description "Log event as a trigger for one or more EHS handlers";
                    }

                    ///nokia-state/state/log/log-events/rip/event-id
                    leaf event-id {
                        type types-log:log-event-id;
                        description
                            "Unique arbitrary identifier for indexing event type entries within
                             an event generator application.";
                    }

                    ///nokia-state/state/log/log-events/rip/parameters
                    leaf-list parameters {
                        type types-sros:named-item;
                        description
                            "Indicates an event's specific parameters. These parameters can
                             be passed from a triggering event to its triggered EHS script.";
                    }

                    ///nokia-state/state/log/log-events/rip/statistics
                    container statistics {
                        description "Enter the statistics context";

                        ///nokia-state/state/log/log-events/rip/statistics/count
                        leaf count {
                            type yang:counter32;
                            description "Number of times an event of this type has been generated.";
                        }

                        ///nokia-state/state/log/log-events/rip/statistics/drop
                        leaf drop {
                            type yang:counter32;
                            description "Indicates the number of times an event of this type has been dropped.";
                        }

                    } // container statistics

                } // list rip

                ///nokia-state/state/log/log-events/ripng
                list ripng {
                    key "event";
                    description "Enter the ripng list instance";

                    ///nokia-state/state/log/log-events/ripng/event
                    leaf event {
                        type types-log:ripng-events;
                        description "Log event as a trigger for one or more EHS handlers";
                    }

                    ///nokia-state/state/log/log-events/ripng/event-id
                    leaf event-id {
                        type types-log:log-event-id;
                        description
                            "Unique arbitrary identifier for indexing event type entries within
                             an event generator application.";
                    }

                    ///nokia-state/state/log/log-events/ripng/parameters
                    leaf-list parameters {
                        type types-sros:named-item;
                        description
                            "Indicates an event's specific parameters. These parameters can
                             be passed from a triggering event to its triggered EHS script.";
                    }

                    ///nokia-state/state/log/log-events/ripng/statistics
                    container statistics {
                        description "Enter the statistics context";

                        ///nokia-state/state/log/log-events/ripng/statistics/count
                        leaf count {
                            type yang:counter32;
                            description "Number of times an event of this type has been generated.";
                        }

                        ///nokia-state/state/log/log-events/ripng/statistics/drop
                        leaf drop {
                            type yang:counter32;
                            description "Indicates the number of times an event of this type has been dropped.";
                        }

                    } // container statistics

                } // list ripng

                ///nokia-state/state/log/log-events/route-policy
                list route-policy {
                    key "event";
                    description "Enter the route-policy list instance";

                    ///nokia-state/state/log/log-events/route-policy/event
                    leaf event {
                        type types-log:route-policy-events;
                        description "Log event as a trigger for one or more EHS handlers";
                    }

                    ///nokia-state/state/log/log-events/route-policy/event-id
                    leaf event-id {
                        type types-log:log-event-id;
                        description
                            "Unique arbitrary identifier for indexing event type entries within
                             an event generator application.";
                    }

                    ///nokia-state/state/log/log-events/route-policy/parameters
                    leaf-list parameters {
                        type types-sros:named-item;
                        description
                            "Indicates an event's specific parameters. These parameters can
                             be passed from a triggering event to its triggered EHS script.";
                    }

                    ///nokia-state/state/log/log-events/route-policy/statistics
                    container statistics {
                        description "Enter the statistics context";

                        ///nokia-state/state/log/log-events/route-policy/statistics/count
                        leaf count {
                            type yang:counter32;
                            description "Number of times an event of this type has been generated.";
                        }

                        ///nokia-state/state/log/log-events/route-policy/statistics/drop
                        leaf drop {
                            type yang:counter32;
                            description "Indicates the number of times an event of this type has been dropped.";
                        }

                    } // container statistics

                } // list route-policy

                ///nokia-state/state/log/log-events/rpki
                list rpki {
                    key "event";
                    description "Enter the rpki list instance";

                    ///nokia-state/state/log/log-events/rpki/event
                    leaf event {
                        type types-log:rpki-events;
                        description "Log event as a trigger for one or more EHS handlers";
                    }

                    ///nokia-state/state/log/log-events/rpki/event-id
                    leaf event-id {
                        type types-log:log-event-id;
                        description
                            "Unique arbitrary identifier for indexing event type entries within
                             an event generator application.";
                    }

                    ///nokia-state/state/log/log-events/rpki/parameters
                    leaf-list parameters {
                        type types-sros:named-item;
                        description
                            "Indicates an event's specific parameters. These parameters can
                             be passed from a triggering event to its triggered EHS script.";
                    }

                    ///nokia-state/state/log/log-events/rpki/statistics
                    container statistics {
                        description "Enter the statistics context";

                        ///nokia-state/state/log/log-events/rpki/statistics/count
                        leaf count {
                            type yang:counter32;
                            description "Number of times an event of this type has been generated.";
                        }

                        ///nokia-state/state/log/log-events/rpki/statistics/drop
                        leaf drop {
                            type yang:counter32;
                            description "Indicates the number of times an event of this type has been dropped.";
                        }

                    } // container statistics

                } // list rpki

                ///nokia-state/state/log/log-events/rsvp
                list rsvp {
                    key "event";
                    description "Enter the rsvp list instance";

                    ///nokia-state/state/log/log-events/rsvp/event
                    leaf event {
                        type types-log:rsvp-events;
                        description "Log event as a trigger for one or more EHS handlers";
                    }

                    ///nokia-state/state/log/log-events/rsvp/event-id
                    leaf event-id {
                        type types-log:log-event-id;
                        description
                            "Unique arbitrary identifier for indexing event type entries within
                             an event generator application.";
                    }

                    ///nokia-state/state/log/log-events/rsvp/parameters
                    leaf-list parameters {
                        type types-sros:named-item;
                        description
                            "Indicates an event's specific parameters. These parameters can
                             be passed from a triggering event to its triggered EHS script.";
                    }

                    ///nokia-state/state/log/log-events/rsvp/statistics
                    container statistics {
                        description "Enter the statistics context";

                        ///nokia-state/state/log/log-events/rsvp/statistics/count
                        leaf count {
                            type yang:counter32;
                            description "Number of times an event of this type has been generated.";
                        }

                        ///nokia-state/state/log/log-events/rsvp/statistics/drop
                        leaf drop {
                            type yang:counter32;
                            description "Indicates the number of times an event of this type has been dropped.";
                        }

                    } // container statistics

                } // list rsvp

                ///nokia-state/state/log/log-events/satellite
                list satellite {
                    key "event";
                    description "Enter the satellite list instance";

                    ///nokia-state/state/log/log-events/satellite/event
                    leaf event {
                        type types-log:satellite-events;
                        description "Log event as a trigger for one or more EHS handlers";
                    }

                    ///nokia-state/state/log/log-events/satellite/event-id
                    leaf event-id {
                        type types-log:log-event-id;
                        description
                            "Unique arbitrary identifier for indexing event type entries within
                             an event generator application.";
                    }

                    ///nokia-state/state/log/log-events/satellite/parameters
                    leaf-list parameters {
                        type types-sros:named-item;
                        description
                            "Indicates an event's specific parameters. These parameters can
                             be passed from a triggering event to its triggered EHS script.";
                    }

                    ///nokia-state/state/log/log-events/satellite/statistics
                    container statistics {
                        description "Enter the statistics context";

                        ///nokia-state/state/log/log-events/satellite/statistics/count
                        leaf count {
                            type yang:counter32;
                            description "Number of times an event of this type has been generated.";
                        }

                        ///nokia-state/state/log/log-events/satellite/statistics/drop
                        leaf drop {
                            type yang:counter32;
                            description "Indicates the number of times an event of this type has been dropped.";
                        }

                    } // container statistics

                } // list satellite

                ///nokia-state/state/log/log-events/security
                list security {
                    key "event";
                    description "Enter the security list instance";

                    ///nokia-state/state/log/log-events/security/event
                    leaf event {
                        type types-log:security-events;
                        description "Log event as a trigger for one or more EHS handlers";
                    }

                    ///nokia-state/state/log/log-events/security/event-id
                    leaf event-id {
                        type types-log:log-event-id;
                        description
                            "Unique arbitrary identifier for indexing event type entries within
                             an event generator application.";
                    }

                    ///nokia-state/state/log/log-events/security/parameters
                    leaf-list parameters {
                        type types-sros:named-item;
                        description
                            "Indicates an event's specific parameters. These parameters can
                             be passed from a triggering event to its triggered EHS script.";
                    }

                    ///nokia-state/state/log/log-events/security/statistics
                    container statistics {
                        description "Enter the statistics context";

                        ///nokia-state/state/log/log-events/security/statistics/count
                        leaf count {
                            type yang:counter32;
                            description "Number of times an event of this type has been generated.";
                        }

                        ///nokia-state/state/log/log-events/security/statistics/drop
                        leaf drop {
                            type yang:counter32;
                            description "Indicates the number of times an event of this type has been dropped.";
                        }

                    } // container statistics

                } // list security

                ///nokia-state/state/log/log-events/sflow
                list sflow {
                    key "event";
                    description "Enter the sflow list instance";

                    ///nokia-state/state/log/log-events/sflow/event
                    leaf event {
                        type types-log:sflow-events;
                        description "Log event as a trigger for one or more EHS handlers";
                    }

                    ///nokia-state/state/log/log-events/sflow/event-id
                    leaf event-id {
                        type types-log:log-event-id;
                        description
                            "Unique arbitrary identifier for indexing event type entries within
                             an event generator application.";
                    }

                    ///nokia-state/state/log/log-events/sflow/parameters
                    leaf-list parameters {
                        type types-sros:named-item;
                        description
                            "Indicates an event's specific parameters. These parameters can
                             be passed from a triggering event to its triggered EHS script.";
                    }

                    ///nokia-state/state/log/log-events/sflow/statistics
                    container statistics {
                        description "Enter the statistics context";

                        ///nokia-state/state/log/log-events/sflow/statistics/count
                        leaf count {
                            type yang:counter32;
                            description "Number of times an event of this type has been generated.";
                        }

                        ///nokia-state/state/log/log-events/sflow/statistics/drop
                        leaf drop {
                            type yang:counter32;
                            description "Indicates the number of times an event of this type has been dropped.";
                        }

                    } // container statistics

                } // list sflow

                ///nokia-state/state/log/log-events/snmp
                list snmp {
                    key "event";
                    description "Enter the snmp list instance";

                    ///nokia-state/state/log/log-events/snmp/event
                    leaf event {
                        type types-log:snmp-events;
                        description "Log event as a trigger for one or more EHS handlers";
                    }

                    ///nokia-state/state/log/log-events/snmp/event-id
                    leaf event-id {
                        type types-log:log-event-id;
                        description
                            "Unique arbitrary identifier for indexing event type entries within
                             an event generator application.";
                    }

                    ///nokia-state/state/log/log-events/snmp/parameters
                    leaf-list parameters {
                        type types-sros:named-item;
                        description
                            "Indicates an event's specific parameters. These parameters can
                             be passed from a triggering event to its triggered EHS script.";
                    }

                    ///nokia-state/state/log/log-events/snmp/statistics
                    container statistics {
                        description "Enter the statistics context";

                        ///nokia-state/state/log/log-events/snmp/statistics/count
                        leaf count {
                            type yang:counter32;
                            description "Number of times an event of this type has been generated.";
                        }

                        ///nokia-state/state/log/log-events/snmp/statistics/drop
                        leaf drop {
                            type yang:counter32;
                            description "Indicates the number of times an event of this type has been dropped.";
                        }

                    } // container statistics

                } // list snmp

                ///nokia-state/state/log/log-events/sr-mpls
                list sr-mpls {
                    key "event";
                    description "Enter the sr-mpls list instance";

                    ///nokia-state/state/log/log-events/sr-mpls/event
                    leaf event {
                        type types-log:sr-mpls-events;
                        description "SR MPLS event";
                    }

                    ///nokia-state/state/log/log-events/sr-mpls/event-id
                    leaf event-id {
                        type types-log:log-event-id;
                        description
                            "Unique arbitrary identifier for indexing event type entries within
                             an event generator application.";
                    }

                    ///nokia-state/state/log/log-events/sr-mpls/parameters
                    leaf-list parameters {
                        type types-sros:named-item;
                        description
                            "Indicates an event's specific parameters. These parameters can
                             be passed from a triggering event to its triggered EHS script.";
                    }

                    ///nokia-state/state/log/log-events/sr-mpls/statistics
                    container statistics {
                        description "Enter the statistics context";

                        ///nokia-state/state/log/log-events/sr-mpls/statistics/count
                        leaf count {
                            type yang:counter32;
                            description "Number of times an event of this type has been generated.";
                        }

                        ///nokia-state/state/log/log-events/sr-mpls/statistics/drop
                        leaf drop {
                            type yang:counter32;
                            description "Indicates the number of times an event of this type has been dropped.";
                        }

                    } // container statistics

                } // list sr-mpls

                ///nokia-state/state/log/log-events/srv6
                list srv6 {
                    key "event";
                    description "Enter the srv6 list instance";

                    ///nokia-state/state/log/log-events/srv6/event
                    leaf event {
                        type types-log:srv6-events;
                        description "Log event as a trigger for one or more EHS handlers";
                    }

                    ///nokia-state/state/log/log-events/srv6/event-id
                    leaf event-id {
                        type types-log:log-event-id;
                        description
                            "Unique arbitrary identifier for indexing event type entries within
                             an event generator application.";
                    }

                    ///nokia-state/state/log/log-events/srv6/parameters
                    leaf-list parameters {
                        type types-sros:named-item;
                        description
                            "Indicates an event's specific parameters. These parameters can
                             be passed from a triggering event to its triggered EHS script.";
                    }

                    ///nokia-state/state/log/log-events/srv6/statistics
                    container statistics {
                        description "Enter the statistics context";

                        ///nokia-state/state/log/log-events/srv6/statistics/count
                        leaf count {
                            type yang:counter32;
                            description "Number of times an event of this type has been generated.";
                        }

                        ///nokia-state/state/log/log-events/srv6/statistics/drop
                        leaf drop {
                            type yang:counter32;
                            description "Indicates the number of times an event of this type has been dropped.";
                        }

                    } // container statistics

                } // list srv6

                ///nokia-state/state/log/log-events/stp
                list stp {
                    key "event";
                    description "Enter the stp list instance";

                    ///nokia-state/state/log/log-events/stp/event
                    leaf event {
                        type types-log:stp-events;
                        description "Log event as a trigger for one or more EHS handlers";
                    }

                    ///nokia-state/state/log/log-events/stp/event-id
                    leaf event-id {
                        type types-log:log-event-id;
                        description
                            "Unique arbitrary identifier for indexing event type entries within
                             an event generator application.";
                    }

                    ///nokia-state/state/log/log-events/stp/parameters
                    leaf-list parameters {
                        type types-sros:named-item;
                        description
                            "Indicates an event's specific parameters. These parameters can
                             be passed from a triggering event to its triggered EHS script.";
                    }

                    ///nokia-state/state/log/log-events/stp/statistics
                    container statistics {
                        description "Enter the statistics context";

                        ///nokia-state/state/log/log-events/stp/statistics/count
                        leaf count {
                            type yang:counter32;
                            description "Number of times an event of this type has been generated.";
                        }

                        ///nokia-state/state/log/log-events/stp/statistics/drop
                        leaf drop {
                            type yang:counter32;
                            description "Indicates the number of times an event of this type has been dropped.";
                        }

                    } // container statistics

                } // list stp

                ///nokia-state/state/log/log-events/svcmgr
                list svcmgr {
                    key "event";
                    description "Enter the svcmgr list instance";

                    ///nokia-state/state/log/log-events/svcmgr/event
                    leaf event {
                        type types-log:svcmgr-events;
                        description "Log event as a trigger for one or more EHS handlers";
                    }

                    ///nokia-state/state/log/log-events/svcmgr/event-id
                    leaf event-id {
                        type types-log:log-event-id;
                        description
                            "Unique arbitrary identifier for indexing event type entries within
                             an event generator application.";
                    }

                    ///nokia-state/state/log/log-events/svcmgr/parameters
                    leaf-list parameters {
                        type types-sros:named-item;
                        description
                            "Indicates an event's specific parameters. These parameters can
                             be passed from a triggering event to its triggered EHS script.";
                    }

                    ///nokia-state/state/log/log-events/svcmgr/statistics
                    container statistics {
                        description "Enter the statistics context";

                        ///nokia-state/state/log/log-events/svcmgr/statistics/count
                        leaf count {
                            type yang:counter32;
                            description "Number of times an event of this type has been generated.";
                        }

                        ///nokia-state/state/log/log-events/svcmgr/statistics/drop
                        leaf drop {
                            type yang:counter32;
                            description "Indicates the number of times an event of this type has been dropped.";
                        }

                    } // container statistics

                } // list svcmgr

                ///nokia-state/state/log/log-events/system
                list system {
                    key "event";
                    description "Enter the system list instance";

                    ///nokia-state/state/log/log-events/system/event
                    leaf event {
                        type types-log:system-events;
                        description "Log event as a trigger for one or more EHS handlers";
                    }

                    ///nokia-state/state/log/log-events/system/event-id
                    leaf event-id {
                        type types-log:log-event-id;
                        description
                            "Unique arbitrary identifier for indexing event type entries within
                             an event generator application.";
                    }

                    ///nokia-state/state/log/log-events/system/parameters
                    leaf-list parameters {
                        type types-sros:named-item;
                        description
                            "Indicates an event's specific parameters. These parameters can
                             be passed from a triggering event to its triggered EHS script.";
                    }

                    ///nokia-state/state/log/log-events/system/statistics
                    container statistics {
                        description "Enter the statistics context";

                        ///nokia-state/state/log/log-events/system/statistics/count
                        leaf count {
                            type yang:counter32;
                            description "Number of times an event of this type has been generated.";
                        }

                        ///nokia-state/state/log/log-events/system/statistics/drop
                        leaf drop {
                            type yang:counter32;
                            description "Indicates the number of times an event of this type has been dropped.";
                        }

                    } // container statistics

                } // list system

                ///nokia-state/state/log/log-events/tls
                list tls {
                    key "event";
                    description "Enter the tls list instance";

                    ///nokia-state/state/log/log-events/tls/event
                    leaf event {
                        type types-log:tls-events;
                        description "Log event as a trigger for one or more EHS handlers";
                    }

                    ///nokia-state/state/log/log-events/tls/event-id
                    leaf event-id {
                        type types-log:log-event-id;
                        description
                            "Unique arbitrary identifier for indexing event type entries within
                             an event generator application.";
                    }

                    ///nokia-state/state/log/log-events/tls/parameters
                    leaf-list parameters {
                        type types-sros:named-item;
                        description
                            "Indicates an event's specific parameters. These parameters can
                             be passed from a triggering event to its triggered EHS script.";
                    }

                    ///nokia-state/state/log/log-events/tls/statistics
                    container statistics {
                        description "Enter the statistics context";

                        ///nokia-state/state/log/log-events/tls/statistics/count
                        leaf count {
                            type yang:counter32;
                            description "Number of times an event of this type has been generated.";
                        }

                        ///nokia-state/state/log/log-events/tls/statistics/drop
                        leaf drop {
                            type yang:counter32;
                            description "Indicates the number of times an event of this type has been dropped.";
                        }

                    } // container statistics

                } // list tls

                ///nokia-state/state/log/log-events/tree-sid
                list tree-sid {
                    key "event";
                    description "Enter the tree-sid list instance";

                    ///nokia-state/state/log/log-events/tree-sid/event
                    leaf event {
                        type types-log:treesid-events;
                        description "Log event as a trigger for one or more EHS handlers";
                    }

                    ///nokia-state/state/log/log-events/tree-sid/event-id
                    leaf event-id {
                        type types-log:log-event-id;
                        description
                            "Unique arbitrary identifier for indexing event type entries within
                             an event generator application.";
                    }

                    ///nokia-state/state/log/log-events/tree-sid/parameters
                    leaf-list parameters {
                        type types-sros:named-item;
                        description
                            "Indicates an event's specific parameters. These parameters can
                             be passed from a triggering event to its triggered EHS script.";
                    }

                    ///nokia-state/state/log/log-events/tree-sid/statistics
                    container statistics {
                        description "Enter the statistics context";

                        ///nokia-state/state/log/log-events/tree-sid/statistics/count
                        leaf count {
                            type yang:counter32;
                            description "Number of times an event of this type has been generated.";
                        }

                        ///nokia-state/state/log/log-events/tree-sid/statistics/drop
                        leaf drop {
                            type yang:counter32;
                            description "Indicates the number of times an event of this type has been dropped.";
                        }

                    } // container statistics

                } // list tree-sid

                ///nokia-state/state/log/log-events/user
                list user {
                    key "event";
                    description "Enter the user list instance";

                    ///nokia-state/state/log/log-events/user/event
                    leaf event {
                        type types-log:user-events;
                        description "Log event as a trigger for one or more EHS handlers";
                    }

                    ///nokia-state/state/log/log-events/user/event-id
                    leaf event-id {
                        type types-log:log-event-id;
                        description
                            "Unique arbitrary identifier for indexing event type entries within
                             an event generator application.";
                    }

                    ///nokia-state/state/log/log-events/user/parameters
                    leaf-list parameters {
                        type types-sros:named-item;
                        description
                            "Indicates an event's specific parameters. These parameters can
                             be passed from a triggering event to its triggered EHS script.";
                    }

                    ///nokia-state/state/log/log-events/user/statistics
                    container statistics {
                        description "Enter the statistics context";

                        ///nokia-state/state/log/log-events/user/statistics/count
                        leaf count {
                            type yang:counter32;
                            description "Number of times an event of this type has been generated.";
                        }

                        ///nokia-state/state/log/log-events/user/statistics/drop
                        leaf drop {
                            type yang:counter32;
                            description "Indicates the number of times an event of this type has been dropped.";
                        }

                    } // container statistics

                } // list user

                ///nokia-state/state/log/log-events/video
                list video {
                    key "event";
                    description "Enter the video list instance";

                    ///nokia-state/state/log/log-events/video/event
                    leaf event {
                        type types-log:video-events;
                        description "Log event as a trigger for one or more EHS handlers";
                    }

                    ///nokia-state/state/log/log-events/video/event-id
                    leaf event-id {
                        type types-log:log-event-id;
                        description
                            "Unique arbitrary identifier for indexing event type entries within
                             an event generator application.";
                    }

                    ///nokia-state/state/log/log-events/video/parameters
                    leaf-list parameters {
                        type types-sros:named-item;
                        description
                            "Indicates an event's specific parameters. These parameters can
                             be passed from a triggering event to its triggered EHS script.";
                    }

                    ///nokia-state/state/log/log-events/video/statistics
                    container statistics {
                        description "Enter the statistics context";

                        ///nokia-state/state/log/log-events/video/statistics/count
                        leaf count {
                            type yang:counter32;
                            description "Number of times an event of this type has been generated.";
                        }

                        ///nokia-state/state/log/log-events/video/statistics/drop
                        leaf drop {
                            type yang:counter32;
                            description "Indicates the number of times an event of this type has been dropped.";
                        }

                    } // container statistics

                } // list video

                ///nokia-state/state/log/log-events/vrrp
                list vrrp {
                    key "event";
                    description "Enter the vrrp list instance";

                    ///nokia-state/state/log/log-events/vrrp/event
                    leaf event {
                        type types-log:vrrp-events;
                        description "Log event as a trigger for one or more EHS handlers";
                    }

                    ///nokia-state/state/log/log-events/vrrp/event-id
                    leaf event-id {
                        type types-log:log-event-id;
                        description
                            "Unique arbitrary identifier for indexing event type entries within
                             an event generator application.";
                    }

                    ///nokia-state/state/log/log-events/vrrp/parameters
                    leaf-list parameters {
                        type types-sros:named-item;
                        description
                            "Indicates an event's specific parameters. These parameters can
                             be passed from a triggering event to its triggered EHS script.";
                    }

                    ///nokia-state/state/log/log-events/vrrp/statistics
                    container statistics {
                        description "Enter the statistics context";

                        ///nokia-state/state/log/log-events/vrrp/statistics/count
                        leaf count {
                            type yang:counter32;
                            description "Number of times an event of this type has been generated.";
                        }

                        ///nokia-state/state/log/log-events/vrrp/statistics/drop
                        leaf drop {
                            type yang:counter32;
                            description "Indicates the number of times an event of this type has been dropped.";
                        }

                    } // container statistics

                } // list vrrp

                ///nokia-state/state/log/log-events/vrtr
                list vrtr {
                    key "event";
                    description "Enter the vrtr list instance";

                    ///nokia-state/state/log/log-events/vrtr/event
                    leaf event {
                        type types-log:vrtr-events;
                        description "Log event as a trigger for one or more EHS handlers";
                    }

                    ///nokia-state/state/log/log-events/vrtr/event-id
                    leaf event-id {
                        type types-log:log-event-id;
                        description
                            "Unique arbitrary identifier for indexing event type entries within
                             an event generator application.";
                    }

                    ///nokia-state/state/log/log-events/vrtr/parameters
                    leaf-list parameters {
                        type types-sros:named-item;
                        description
                            "Indicates an event's specific parameters. These parameters can
                             be passed from a triggering event to its triggered EHS script.";
                    }

                    ///nokia-state/state/log/log-events/vrtr/statistics
                    container statistics {
                        description "Enter the statistics context";

                        ///nokia-state/state/log/log-events/vrtr/statistics/count
                        leaf count {
                            type yang:counter32;
                            description "Number of times an event of this type has been generated.";
                        }

                        ///nokia-state/state/log/log-events/vrtr/statistics/drop
                        leaf drop {
                            type yang:counter32;
                            description "Indicates the number of times an event of this type has been dropped.";
                        }

                    } // container statistics

                } // list vrtr

                ///nokia-state/state/log/log-events/wlan-gw
                list wlan-gw {
                    key "event";
                    description "Enter the wlan-gw list instance";

                    ///nokia-state/state/log/log-events/wlan-gw/event
                    leaf event {
                        type types-log:wlan-gw-events;
                        description "Log event as a trigger for one or more EHS handlers";
                    }

                    ///nokia-state/state/log/log-events/wlan-gw/event-id
                    leaf event-id {
                        type types-log:log-event-id;
                        description
                            "Unique arbitrary identifier for indexing event type entries within
                             an event generator application.";
                    }

                    ///nokia-state/state/log/log-events/wlan-gw/parameters
                    leaf-list parameters {
                        type types-sros:named-item;
                        description
                            "Indicates an event's specific parameters. These parameters can
                             be passed from a triggering event to its triggered EHS script.";
                    }

                    ///nokia-state/state/log/log-events/wlan-gw/statistics
                    container statistics {
                        description "Enter the statistics context";

                        ///nokia-state/state/log/log-events/wlan-gw/statistics/count
                        leaf count {
                            type yang:counter32;
                            description "Number of times an event of this type has been generated.";
                        }

                        ///nokia-state/state/log/log-events/wlan-gw/statistics/drop
                        leaf drop {
                            type yang:counter32;
                            description "Indicates the number of times an event of this type has been dropped.";
                        }

                    } // container statistics

                } // list wlan-gw

                ///nokia-state/state/log/log-events/wpp
                list wpp {
                    key "event";
                    description "Enter the wpp list instance";

                    ///nokia-state/state/log/log-events/wpp/event
                    leaf event {
                        type types-log:wpp-events;
                        description "Log event as a trigger for one or more EHS handlers";
                    }

                    ///nokia-state/state/log/log-events/wpp/event-id
                    leaf event-id {
                        type types-log:log-event-id;
                        description
                            "Unique arbitrary identifier for indexing event type entries within
                             an event generator application.";
                    }

                    ///nokia-state/state/log/log-events/wpp/parameters
                    leaf-list parameters {
                        type types-sros:named-item;
                        description
                            "Indicates an event's specific parameters. These parameters can
                             be passed from a triggering event to its triggered EHS script.";
                    }

                    ///nokia-state/state/log/log-events/wpp/statistics
                    container statistics {
                        description "Enter the statistics context";

                        ///nokia-state/state/log/log-events/wpp/statistics/count
                        leaf count {
                            type yang:counter32;
                            description "Number of times an event of this type has been generated.";
                        }

                        ///nokia-state/state/log/log-events/wpp/statistics/drop
                        leaf drop {
                            type yang:counter32;
                            description "Indicates the number of times an event of this type has been dropped.";
                        }

                    } // container statistics

                } // list wpp

            } // container log-events

            ///nokia-state/state/log/event-handling
            container event-handling {
                description "Enter the event-handling context";

                ///nokia-state/state/log/event-handling/summary-statistics
                container summary-statistics {
                    description "Enter the summary-statistics context";

                    ///nokia-state/state/log/event-handling/summary-statistics/success
                    leaf success {
                        type yang:counter32;
                        description
                            "Indicates the number of times the EHS system triggers a handler,
                             which can take corresponding action specified in handler's entries.";
                    }

                    ///nokia-state/state/log/event-handling/summary-statistics/error-no-entry
                    leaf error-no-entry {
                        type yang:counter32;
                        description
                            "Indicates the number of times the EHS system triggers a handler,
                             which can not take corresponding action as there is no handler's entry
                             specifying an operation to perform.";
                    }

                    ///nokia-state/state/log/event-handling/summary-statistics/error-admin-state
                    leaf error-admin-state {
                        type yang:counter32;
                        description
                            "Indicates the number of times the EHS system triggers a handler,
                             which can not take corresponding action due handler may be out-of-service.";
                    }

                    ///nokia-state/state/log/event-handling/summary-statistics/total
                    leaf total {
                        type yang:counter32;
                        description "Sum of success + error-no-entry + error-admin-state.";
                    }

                } // container summary-statistics

                ///nokia-state/state/log/event-handling/handler
                list handler {
                    key "name";
                    description "Enter the handler list instance";

                    ///nokia-state/state/log/event-handling/handler/name
                    leaf name {
                        type types-sros:named-item;
                        description "EHS handler name";
                    }

                    ///nokia-state/state/log/event-handling/handler/oper-state
                    leaf oper-state {
                        type types-sros:oper-state;
                        description "Indicates the operational state of the EHS Event Handler.";
                    }

                    ///nokia-state/state/log/event-handling/handler/statistics
                    container statistics {
                        description "Enter the statistics context";

                        ///nokia-state/state/log/event-handling/handler/statistics/success
                        leaf success {
                            type yang:counter32;
                            description
                                "Indicates the number of times the EHS system triggers the handler,
                                 which can take corresponding action specified in handler's entries.";
                        }

                        ///nokia-state/state/log/event-handling/handler/statistics/error-no-entry
                        leaf error-no-entry {
                            type yang:counter32;
                            description
                                "Indicates the number of times the EHS system triggers the handler,
                                 which can not take corresponding action as there is no handler's entry
                                 specifying an operation to perform.";
                        }

                        ///nokia-state/state/log/event-handling/handler/statistics/error-admin-state
                        leaf error-admin-state {
                            type yang:counter32;
                            description
                                "Indicates the number of times the EHS system triggers the handler,
                                 which can not take corresponding action due handler may be out-of-service.";
                        }

                        ///nokia-state/state/log/event-handling/handler/statistics/total
                        leaf total {
                            type yang:counter32;
                            description "Sum of success + error-no-entry + error-admin-state.";
                        }

                    } // container statistics

                    ///nokia-state/state/log/event-handling/handler/summary-entry-statistics
                    container summary-entry-statistics {
                        description "Enter the summary-entry-statistics context";

                        ///nokia-state/state/log/event-handling/handler/summary-entry-statistics/success
                        leaf success {
                            type yang:counter32;
                            description "Indicates the global number of successfully queued scripts by EHS handler entries.";
                        }

                        ///nokia-state/state/log/event-handling/handler/summary-entry-statistics/error-min-delay
                        leaf error-min-delay {
                            type yang:counter32;
                            description "Indicates the global number of cancelled script executions due to min-delay.";
                        }

                        ///nokia-state/state/log/event-handling/handler/summary-entry-statistics/error-launch-failure
                        leaf error-launch-failure {
                            type yang:counter32;
                            description "Indicates the global number of cancelled script executions due to launch failure.";
                        }

                        ///nokia-state/state/log/event-handling/handler/summary-entry-statistics/error-admin-state
                        leaf error-admin-state {
                            type yang:counter32;
                            description "Indicates the global number of cancelled script executions due to handler entry may be out-of-service.";
                        }

                    } // container summary-entry-statistics

                    ///nokia-state/state/log/event-handling/handler/entry
                    list entry {
                        key "id";
                        description "Enter the entry list instance";

                        ///nokia-state/state/log/event-handling/handler/entry/id
                        leaf id {
                            type uint32 {
                                range "1..1500";
                            }
                            description "EHS handler entry ID";
                        }

                        ///nokia-state/state/log/event-handling/handler/entry/oper-state
                        leaf oper-state {
                            type types-sros:oper-state;
                            description "Indicates the operational state of the EHS Event Handler Entry.";
                        }

                        ///nokia-state/state/log/event-handling/handler/entry/last-data-loss-time
                        leaf last-data-loss-time {
                            type yang:date-and-time;
                            description "Indicates the time when handler entry launch execution of action.";
                        }

                        ///nokia-state/state/log/event-handling/handler/entry/statistics
                        container statistics {
                            description "Enter the statistics context";

                            ///nokia-state/state/log/event-handling/handler/entry/statistics/success
                            leaf success {
                                type yang:counter32;
                                description "Indicates the number of successfully queued scripts by EHS handler entry.";
                            }

                            ///nokia-state/state/log/event-handling/handler/entry/statistics/error-min-delay
                            leaf error-min-delay {
                                type yang:counter32;
                                description "Indicates the number of cancelled script executions due to min-delay.";
                            }

                            ///nokia-state/state/log/event-handling/handler/entry/statistics/error-launch-failure
                            leaf error-launch-failure {
                                type yang:counter32;
                                description "Indicates the number of cancelled script executions due to launch failure.";
                            }

                            ///nokia-state/state/log/event-handling/handler/entry/statistics/error-admin-state
                            leaf error-admin-state {
                                type yang:counter32;
                                description "Indicates the number of cancelled script executions due to handler entry may be out-of-service.";
                            }

                        } // container statistics

                    } // list entry

                } // list handler

            } // container event-handling

            ///nokia-state/state/log/event-trigger
            container event-trigger {
                description "Enter the event-trigger context";

                ///nokia-state/state/log/event-trigger/summary-statistics
                container summary-statistics {
                    description "Enter the summary-statistics context";

                    ///nokia-state/state/log/event-trigger/summary-statistics/success
                    leaf success {
                        type yang:counter32;
                        description
                            "Indicates the number of not ignored logger event occurrences
                             associated with all EHS triggers.";
                    }

                    ///nokia-state/state/log/event-trigger/summary-statistics/error-no-entry
                    leaf error-no-entry {
                        type yang:counter32;
                        description
                            "Indicates the number of ignored logger event occurrences associated
                             with all EHS triggers.

                             Event is ignored due to no trigger entry configured for a trigger.";
                    }

                    ///nokia-state/state/log/event-trigger/summary-statistics/error-admin-state
                    leaf error-admin-state {
                        type yang:counter32;
                        description
                            "Indicates the number of ignored logger event occurrences associated
                             with all EHS triggers.

                             Event is ignored due to a trigger may be out-of-service.";
                    }

                    ///nokia-state/state/log/event-trigger/summary-statistics/total
                    leaf total {
                        type yang:counter32;
                        description "Sum of success + error-no-entry + error-admin-state.";
                    }

                } // container summary-statistics

                ///nokia-state/state/log/event-trigger/adp
                list adp {
                    key "event";
                    description "Enter the adp list instance";

                    ///nokia-state/state/log/event-trigger/adp/event
                    leaf event {
                        type types-log:adp-events;
                        description "Log event as a trigger for one or more EHS handlers";
                    }

                    ///nokia-state/state/log/event-trigger/adp/oper-state
                    leaf oper-state {
                        type types-sros:oper-state;
                        description "Indicates the operational state of the EHS Event Trigger.";
                    }

                    ///nokia-state/state/log/event-trigger/adp/statistics
                    container statistics {
                        description "Enter the statistics context";

                        ///nokia-state/state/log/event-trigger/adp/statistics/success
                        leaf success {
                            type yang:counter32;
                            description
                                "Indicates the number of not ignored logger event occurrences
                                 associated with EHS trigger.";
                        }

                        ///nokia-state/state/log/event-trigger/adp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/adp/statistics/error-admin-state
                        leaf error-admin-state {
                            type yang:counter32;
                            description
                                "Indicates the number of ignored logger event occurrences associated
                                 with EHS trigger.

                                 Event is ignored due to trigger may be out-of-service.";
                        }

                        ///nokia-state/state/log/event-trigger/adp/statistics/total
                        leaf total {
                            type yang:counter32;
                            description "Sum of success + error-no-entry + error-admin-state.";
                        }

                    } // container statistics

                    ///nokia-state/state/log/event-trigger/adp/summary-entry-statistics
                    container summary-entry-statistics {
                        description "Enter the summary-entry-statistics context";

                        ///nokia-state/state/log/event-trigger/adp/summary-entry-statistics/filter-match
                        leaf filter-match {
                            type yang:counter32;
                            description "Indicates the number of times a filter matches an logger event.";
                        }

                        ///nokia-state/state/log/event-trigger/adp/summary-entry-statistics/filter-fail
                        leaf filter-fail {
                            type yang:counter32;
                            description "Indicates the number of times a filter does not match an logger event.";
                        }

                        ///nokia-state/state/log/event-trigger/adp/summary-entry-statistics/error-admin-state
                        leaf error-admin-state {
                            type yang:counter32;
                            description
                                "Indicates the number of times the logger event will be ignored due to
                                 admin state of EHS trigger entries is out-of-service.";
                        }

                        ///nokia-state/state/log/event-trigger/adp/summary-entry-statistics/error-filter
                        leaf error-filter {
                            type yang:counter32;
                            description
                                "Indicates the number of times the logger event will be ignored due to filter
                                 is not operational or is not configured in EHS trigger entries.";
                        }

                        ///nokia-state/state/log/event-trigger/adp/summary-entry-statistics/error-handler
                        leaf error-handler {
                            type yang:counter32;
                            description
                                "Indicates the number of times the logger event will be ignored due to handler
                                 is not operational or is not configured in EHS trigger entries.";
                        }

                        ///nokia-state/state/log/event-trigger/adp/summary-entry-statistics/trigger-count
                        leaf trigger-count {
                            type yang:counter32;
                            description "Indicates the number of times script execution is triggered after filter match.";
                        }

                        ///nokia-state/state/log/event-trigger/adp/summary-entry-statistics/debounce-count
                        leaf debounce-count {
                            type yang:counter32;
                            description "Indicates the number of times script is not executed due to debounce rule.";
                        }

                    } // container summary-entry-statistics

                    ///nokia-state/state/log/event-trigger/adp/entry
                    list entry {
                        key "id";
                        description "Enter the entry list instance";

                        ///nokia-state/state/log/event-trigger/adp/entry/id
                        leaf id {
                            type uint32 {
                                range "1..1500";
                            }
                            description "ID of the EHS event trigger entry";
                        }

                        ///nokia-state/state/log/event-trigger/adp/entry/oper-state
                        leaf oper-state {
                            type types-sros:oper-state;
                            description "Indicates the operational state of the EHS Event Trigger Entry.";
                        }

                        ///nokia-state/state/log/event-trigger/adp/entry/statistics
                        container statistics {
                            description "Enter the statistics context";

                            ///nokia-state/state/log/event-trigger/adp/entry/statistics/filter-match
                            leaf filter-match {
                                type yang:counter32;
                                description
                                    "Indicates the number of times a filter, for the specified trigger entry,
                                     matches an logger event.";
                            }

                            ///nokia-state/state/log/event-trigger/adp/entry/statistics/filter-fail
                            leaf filter-fail {
                                type yang:counter32;
                                description
                                    "Indicates the number of times a filter, for the specified trigger entry,
                                     does not match an logger event.";
                            }

                            ///nokia-state/state/log/event-trigger/adp/entry/statistics/error-admin-state
                            leaf error-admin-state {
                                type yang:counter32;
                                description
                                    "Indicates the number of times the logger event will be ignored due to
                                     admin state of EHS trigger entry is out-of-service.";
                            }

                            ///nokia-state/state/log/event-trigger/adp/entry/statistics/error-filter
                            leaf error-filter {
                                type yang:counter32;
                                description
                                    "Indicates the number of times the logger event will be ignored due to filter
                                     is not operational or is not configured in EHS trigger entry.";
                            }

                            ///nokia-state/state/log/event-trigger/adp/entry/statistics/error-handler
                            leaf error-handler {
                                type yang:counter32;
                                description
                                    "Indicates the number of times the logger event will be ignored due to handler
                                     is not operational or is not configured in EHS trigger entry.";
                            }

                            ///nokia-state/state/log/event-trigger/adp/entry/statistics/trigger-count
                            leaf trigger-count {
                                type yang:counter32;
                                description
                                    "Indicates the number of times script execution is triggered after filter match
                                     for the specified trigger entry.";
                            }

                            ///nokia-state/state/log/event-trigger/adp/entry/statistics/debounce-count
                            leaf debounce-count {
                                type yang:counter32;
                                description
                                    "Indicates the number of times script is not executed due to debounce rule
                                     for the specified trigger entry.";
                            }

                        } // container statistics

                    } // list entry

                } // list adp

                ///nokia-state/state/log/event-trigger/anysec
                list anysec {
                    key "event";
                    description "Enter the anysec list instance";

                    ///nokia-state/state/log/event-trigger/anysec/event
                    leaf event {
                        type types-log:anysec-events;
                        description "ANYSec module event";
                    }

                    ///nokia-state/state/log/event-trigger/anysec/oper-state
                    leaf oper-state {
                        type types-sros:oper-state;
                        description "Indicates the operational state of the EHS Event Trigger.";
                    }

                    ///nokia-state/state/log/event-trigger/anysec/statistics
                    container statistics {
                        description "Enter the statistics context";

                        ///nokia-state/state/log/event-trigger/anysec/statistics/success
                        leaf success {
                            type yang:counter32;
                            description
                                "Indicates the number of not ignored logger event occurrences
                                 associated with EHS trigger.";
                        }

                        ///nokia-state/state/log/event-trigger/anysec/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/anysec/statistics/error-admin-state
                        leaf error-admin-state {
                            type yang:counter32;
                            description
                                "Indicates the number of ignored logger event occurrences associated
                                 with EHS trigger.

                                 Event is ignored due to trigger may be out-of-service.";
                        }

                        ///nokia-state/state/log/event-trigger/anysec/statistics/total
                        leaf total {
                            type yang:counter32;
                            description "Sum of success + error-no-entry + error-admin-state.";
                        }

                    } // container statistics

                    ///nokia-state/state/log/event-trigger/anysec/summary-entry-statistics
                    container summary-entry-statistics {
                        description "Enter the summary-entry-statistics context";

                        ///nokia-state/state/log/event-trigger/anysec/summary-entry-statistics/filter-match
                        leaf filter-match {
                            type yang:counter32;
                            description "Indicates the number of times a filter matches an logger event.";
                        }

                        ///nokia-state/state/log/event-trigger/anysec/summary-entry-statistics/filter-fail
                        leaf filter-fail {
                            type yang:counter32;
                            description "Indicates the number of times a filter does not match an logger event.";
                        }

                        ///nokia-state/state/log/event-trigger/anysec/summary-entry-statistics/error-admin-state
                        leaf error-admin-state {
                            type yang:counter32;
                            description
                                "Indicates the number of times the logger event will be ignored due to
                                 admin state of EHS trigger entries is out-of-service.";
                        }

                        ///nokia-state/state/log/event-trigger/anysec/summary-entry-statistics/error-filter
                        leaf error-filter {
                            type yang:counter32;
                            description
                                "Indicates the number of times the logger event will be ignored due to filter
                                 is not operational or is not configured in EHS trigger entries.";
                        }

                        ///nokia-state/state/log/event-trigger/anysec/summary-entry-statistics/error-handler
                        leaf error-handler {
                            type yang:counter32;
                            description
                                "Indicates the number of times the logger event will be ignored due to handler
                                 is not operational or is not configured in EHS trigger entries.";
                        }

                        ///nokia-state/state/log/event-trigger/anysec/summary-entry-statistics/trigger-count
                        leaf trigger-count {
                            type yang:counter32;
                            description "Indicates the number of times script execution is triggered after filter match.";
                        }

                        ///nokia-state/state/log/event-trigger/anysec/summary-entry-statistics/debounce-count
                        leaf debounce-count {
                            type yang:counter32;
                            description "Indicates the number of times script is not executed due to debounce rule.";
                        }

                    } // container summary-entry-statistics

                    ///nokia-state/state/log/event-trigger/anysec/entry
                    list entry {
                        key "id";
                        description "Enter the entry list instance";

                        ///nokia-state/state/log/event-trigger/anysec/entry/id
                        leaf id {
                            type uint32 {
                                range "1..1500";
                            }
                            description "ID of the EHS event trigger entry";
                        }

                        ///nokia-state/state/log/event-trigger/anysec/entry/oper-state
                        leaf oper-state {
                            type types-sros:oper-state;
                            description "Indicates the operational state of the EHS Event Trigger Entry.";
                        }

                        ///nokia-state/state/log/event-trigger/anysec/entry/statistics
                        container statistics {
                            description "Enter the statistics context";

                            ///nokia-state/state/log/event-trigger/anysec/entry/statistics/filter-match
                            leaf filter-match {
                                type yang:counter32;
                                description
                                    "Indicates the number of times a filter, for the specified trigger entry,
                                     matches an logger event.";
                            }

                            ///nokia-state/state/log/event-trigger/anysec/entry/statistics/filter-fail
                            leaf filter-fail {
                                type yang:counter32;
                                description
                                    "Indicates the number of times a filter, for the specified trigger entry,
                                     does not match an logger event.";
                            }

                            ///nokia-state/state/log/event-trigger/anysec/entry/statistics/error-admin-state
                            leaf error-admin-state {
                                type yang:counter32;
                                description
                                    "Indicates the number of times the logger event will be ignored due to
                                     admin state of EHS trigger entry is out-of-service.";
                            }

                            ///nokia-state/state/log/event-trigger/anysec/entry/statistics/error-filter
                            leaf error-filter {
                                type yang:counter32;
                                description
                                    "Indicates the number of times the logger event will be ignored due to filter
                                     is not operational or is not configured in EHS trigger entry.";
                            }

                            ///nokia-state/state/log/event-trigger/anysec/entry/statistics/error-handler
                            leaf error-handler {
                                type yang:counter32;
                                description
                                    "Indicates the number of times the logger event will be ignored due to handler
                                     is not operational or is not configured in EHS trigger entry.";
                            }

                            ///nokia-state/state/log/event-trigger/anysec/entry/statistics/trigger-count
                            leaf trigger-count {
                                type yang:counter32;
                                description
                                    "Indicates the number of times script execution is triggered after filter match
                                     for the specified trigger entry.";
                            }

                            ///nokia-state/state/log/event-trigger/anysec/entry/statistics/debounce-count
                            leaf debounce-count {
                                type yang:counter32;
                                description
                                    "Indicates the number of times script is not executed due to debounce rule
                                     for the specified trigger entry.";
                            }

                        } // container statistics

                    } // list entry

                } // list anysec

                ///nokia-state/state/log/event-trigger/application-assurance
                list application-assurance {
                    key "event";
                    description "Enter the application-assurance list instance";

                    ///nokia-state/state/log/event-trigger/application-assurance/event
                    leaf event {
                        type types-log:application-assurance-events;
                        description "Log event as a trigger for one or more EHS handlers";
                    }

                    ///nokia-state/state/log/event-trigger/application-assurance/oper-state
                    leaf oper-state {
                        type types-sros:oper-state;
                        description "Indicates the operational state of the EHS Event Trigger.";
                    }

                    ///nokia-state/state/log/event-trigger/application-assurance/statistics
                    container statistics {
                        description "Enter the statistics context";

                        ///nokia-state/state/log/event-trigger/application-assurance/statistics/success
                        leaf success {
                            type yang:counter32;
                            description
                                "Indicates the number of not ignored logger event occurrences
                                 associated with EHS trigger.";
                        }

                        ///nokia-state/state/log/event-trigger/application-assurance/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/application-assurance/statistics/error-admin-state
                        leaf error-admin-state {
                            type yang:counter32;
                            description
                                "Indicates the number of ignored logger event occurrences associated
                                 with EHS trigger.

                                 Event is ignored due to trigger may be out-of-service.";
                        }

                        ///nokia-state/state/log/event-trigger/application-assurance/statistics/total
                        leaf total {
                            type yang:counter32;
                            description "Sum of success + error-no-entry + error-admin-state.";
                        }

                    } // container statistics

                    ///nokia-state/state/log/event-trigger/application-assurance/summary-entry-statistics
                    container summary-entry-statistics {
                        description "Enter the summary-entry-statistics context";

                        ///nokia-state/state/log/event-trigger/application-assurance/summary-entry-statistics/filter-match
                        leaf filter-match {
                            type yang:counter32;
                            description "Indicates the number of times a filter matches an logger event.";
                        }

                        ///nokia-state/state/log/event-trigger/application-assurance/summary-entry-statistics/filter-fail
                        leaf filter-fail {
                            type yang:counter32;
                            description "Indicates the number of times a filter does not match an logger event.";
                        }

                        ///nokia-state/state/log/event-trigger/application-assurance/summary-entry-statistics/error-admin-state
                        leaf error-admin-state {
                            type yang:counter32;
                            description
                                "Indicates the number of times the logger event will be ignored due to
                                 admin state of EHS trigger entries is out-of-service.";
                        }

                        ///nokia-state/state/log/event-trigger/application-assurance/summary-entry-statistics/error-filter
                        leaf error-filter {
                            type yang:counter32;
                            description
                                "Indicates the number of times the logger event will be ignored due to filter
                                 is not operational or is not configured in EHS trigger entries.";
                        }

                        ///nokia-state/state/log/event-trigger/application-assurance/summary-entry-statistics/error-handler
                        leaf error-handler {
                            type yang:counter32;
                            description
                                "Indicates the number of times the logger event will be ignored due to handler
                                 is not operational or is not configured in EHS trigger entries.";
                        }

                        ///nokia-state/state/log/event-trigger/application-assurance/summary-entry-statistics/trigger-count
                        leaf trigger-count {
                            type yang:counter32;
                            description "Indicates the number of times script execution is triggered after filter match.";
                        }

                        ///nokia-state/state/log/event-trigger/application-assurance/summary-entry-statistics/debounce-count
                        leaf debounce-count {
                            type yang:counter32;
                            description "Indicates the number of times script is not executed due to debounce rule.";
                        }

                    } // container summary-entry-statistics

                    ///nokia-state/state/log/event-trigger/application-assurance/entry
                    list entry {
                        key "id";
                        description "Enter the entry list instance";

                        ///nokia-state/state/log/event-trigger/application-assurance/entry/id
                        leaf id {
                            type uint32 {
                                range "1..1500";
                            }
                            description "ID of the EHS event trigger entry";
                        }

                        ///nokia-state/state/log/event-trigger/application-assurance/entry/oper-state
                        leaf oper-state {
                            type types-sros:oper-state;
                            description "Indicates the operational state of the EHS Event Trigger Entry.";
                        }

                        ///nokia-state/state/log/event-trigger/application-assurance/entry/statistics
                        container statistics {
                            description "Enter the statistics context";

                            ///nokia-state/state/log/event-trigger/application-assurance/entry/statistics/filter-match
                            leaf filter-match {
                                type yang:counter32;
                                description
                                    "Indicates the number of times a filter, for the specified trigger entry,
                                     matches an logger event.";
                            }

                            ///nokia-state/state/log/event-trigger/application-assurance/entry/statistics/filter-fail
                            leaf filter-fail {
                                type yang:counter32;
                                description
                                    "Indicates the number of times a filter, for the specified trigger entry,
                                     does not match an logger event.";
                            }

                            ///nokia-state/state/log/event-trigger/application-assurance/entry/statistics/error-admin-state
                            leaf error-admin-state {
                                type yang:counter32;
                                description
                                    "Indicates the number of times the logger event will be ignored due to
                                     admin state of EHS trigger entry is out-of-service.";
                            }

                            ///nokia-state/state/log/event-trigger/application-assurance/entry/statistics/error-filter
                            leaf error-filter {
                                type yang:counter32;
                                description
                                    "Indicates the number of times the logger event will be ignored due to filter
                                     is not operational or is not configured in EHS trigger entry.";
                            }

                            ///nokia-state/state/log/event-trigger/application-assurance/entry/statistics/error-handler
                            leaf error-handler {
                                type yang:counter32;
                                description
                                    "Indicates the number of times the logger event will be ignored due to handler
                                     is not operational or is not configured in EHS trigger entry.";
                            }

                            ///nokia-state/state/log/event-trigger/application-assurance/entry/statistics/trigger-count
                            leaf trigger-count {
                                type yang:counter32;
                                description
                                    "Indicates the number of times script execution is triggered after filter match
                                     for the specified trigger entry.";
                            }

                            ///nokia-state/state/log/event-trigger/application-assurance/entry/statistics/debounce-count
                            leaf debounce-count {
                                type yang:counter32;
                                description
                                    "Indicates the number of times script is not executed due to debounce rule
                                     for the specified trigger entry.";
                            }

                        } // container statistics

                    } // list entry

                } // list application-assurance

                ///nokia-state/state/log/event-trigger/aps
                list aps {
                    key "event";
                    description "Enter the aps list instance";

                    ///nokia-state/state/log/event-trigger/aps/event
                    leaf event {
                        type types-log:aps-events;
                        description "Log event as a trigger for one or more EHS handlers";
                    }

                    ///nokia-state/state/log/event-trigger/aps/oper-state
                    leaf oper-state {
                        type types-sros:oper-state;
                        description "Indicates the operational state of the EHS Event Trigger.";
                    }

                    ///nokia-state/state/log/event-trigger/aps/statistics
                    container statistics {
                        description "Enter the statistics context";

                        ///nokia-state/state/log/event-trigger/aps/statistics/success
                        leaf success {
                            type yang:counter32;
                            description
                                "Indicates the number of not ignored logger event occurrences
                                 associated with EHS trigger.";
                        }

                        ///nokia-state/state/log/event-trigger/aps/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/aps/statistics/error-admin-state
                        leaf error-admin-state {
                            type yang:counter32;
                            description
                                "Indicates the number of ignored logger event occurrences associated
                                 with EHS trigger.

                                 Event is ignored due to trigger may be out-of-service.";
                        }

                        ///nokia-state/state/log/event-trigger/aps/statistics/total
                        leaf total {
                            type yang:counter32;
                            description "Sum of success + error-no-entry + error-admin-state.";
                        }

                    } // container statistics

                    ///nokia-state/state/log/event-trigger/aps/summary-entry-statistics
                    container summary-entry-statistics {
                        description "Enter the summary-entry-statistics context";

                        ///nokia-state/state/log/event-trigger/aps/summary-entry-statistics/filter-match
                        leaf filter-match {
                            type yang:counter32;
                            description "Indicates the number of times a filter matches an logger event.";
                        }

                        ///nokia-state/state/log/event-trigger/aps/summary-entry-statistics/filter-fail
                        leaf filter-fail {
                            type yang:counter32;
                            description "Indicates the number of times a filter does not match an logger event.";
                        }

                        ///nokia-state/state/log/event-trigger/aps/summary-entry-statistics/error-admin-state
                        leaf error-admin-state {
                            type yang:counter32;
                            description
                                "Indicates the number of times the logger event will be ignored due to
                                 admin state of EHS trigger entries is out-of-service.";
                        }

                        ///nokia-state/state/log/event-trigger/aps/summary-entry-statistics/error-filter
                        leaf error-filter {
                            type yang:counter32;
                            description
                                "Indicates the number of times the logger event will be ignored due to filter
                                 is not operational or is not configured in EHS trigger entries.";
                        }

                        ///nokia-state/state/log/event-trigger/aps/summary-entry-statistics/error-handler
                        leaf error-handler {
                            type yang:counter32;
                            description
                                "Indicates the number of times the logger event will be ignored due to handler
                                 is not operational or is not configured in EHS trigger entries.";
                        }

                        ///nokia-state/state/log/event-trigger/aps/summary-entry-statistics/trigger-count
                        leaf trigger-count {
                            type yang:counter32;
                            description "Indicates the number of times script execution is triggered after filter match.";
                        }

                        ///nokia-state/state/log/event-trigger/aps/summary-entry-statistics/debounce-count
                        leaf debounce-count {
                            type yang:counter32;
                            description "Indicates the number of times script is not executed due to debounce rule.";
                        }

                    } // container summary-entry-statistics

                    ///nokia-state/state/log/event-trigger/aps/entry
                    list entry {
                        key "id";
                        description "Enter the entry list instance";

                        ///nokia-state/state/log/event-trigger/aps/entry/id
                        leaf id {
                            type uint32 {
                                range "1..1500";
                            }
                            description "ID of the EHS event trigger entry";
                        }

                        ///nokia-state/state/log/event-trigger/aps/entry/oper-state
                        leaf oper-state {
                            type types-sros:oper-state;
                            description "Indicates the operational state of the EHS Event Trigger Entry.";
                        }

                        ///nokia-state/state/log/event-trigger/aps/entry/statistics
                        container statistics {
                            description "Enter the statistics context";

                            ///nokia-state/state/log/event-trigger/aps/entry/statistics/filter-match
                            leaf filter-match {
                                type yang:counter32;
                                description
                                    "Indicates the number of times a filter, for the specified trigger entry,
                                     matches an logger event.";
                            }

                            ///nokia-state/state/log/event-trigger/aps/entry/statistics/filter-fail
                            leaf filter-fail {
                                type yang:counter32;
                                description
                                    "Indicates the number of times a filter, for the specified trigger entry,
                                     does not match an logger event.";
                            }

                            ///nokia-state/state/log/event-trigger/aps/entry/statistics/error-admin-state
                            leaf error-admin-state {
                                type yang:counter32;
                                description
                                    "Indicates the number of times the logger event will be ignored due to
                                     admin state of EHS trigger entry is out-of-service.";
                            }

                            ///nokia-state/state/log/event-trigger/aps/entry/statistics/error-filter
                            leaf error-filter {
                                type yang:counter32;
                                description
                                    "Indicates the number of times the logger event will be ignored due to filter
                                     is not operational or is not configured in EHS trigger entry.";
                            }

                            ///nokia-state/state/log/event-trigger/aps/entry/statistics/error-handler
                            leaf error-handler {
                                type yang:counter32;
                                description
                                    "Indicates the number of times the logger event will be ignored due to handler
                                     is not operational or is not configured in EHS trigger entry.";
                            }

                            ///nokia-state/state/log/event-trigger/aps/entry/statistics/trigger-count
                            leaf trigger-count {
                                type yang:counter32;
                                description
                                    "Indicates the number of times script execution is triggered after filter match
                                     for the specified trigger entry.";
                            }

                            ///nokia-state/state/log/event-trigger/aps/entry/statistics/debounce-count
                            leaf debounce-count {
                                type yang:counter32;
                                description
                                    "Indicates the number of times script is not executed due to debounce rule
                                     for the specified trigger entry.";
                            }

                        } // container statistics

                    } // list entry

                } // list aps

                ///nokia-state/state/log/event-trigger/auto-prov
                list auto-prov {
                    key "event";
                    description "Enter the auto-prov list instance";

                    ///nokia-state/state/log/event-trigger/auto-prov/event
                    leaf event {
                        type types-log:auto-prov-events;
                        description "Log event as a trigger for one or more EHS handlers";
                    }

                    ///nokia-state/state/log/event-trigger/auto-prov/oper-state
                    leaf oper-state {
                        type types-sros:oper-state;
                        description "Indicates the operational state of the EHS Event Trigger.";
                    }

                    ///nokia-state/state/log/event-trigger/auto-prov/statistics
                    container statistics {
                        description "Enter the statistics context";

                        ///nokia-state/state/log/event-trigger/auto-prov/statistics/success
                        leaf success {
                            type yang:counter32;
                            description
                                "Indicates the number of not ignored logger event occurrences
                                 associated with EHS trigger.";
                        }

                        ///nokia-state/state/log/event-trigger/auto-prov/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/auto-prov/statistics/error-admin-state
                        leaf error-admin-state {
                            type yang:counter32;
                            description
                                "Indicates the number of ignored logger event occurrences associated
                                 with EHS trigger.

                                 Event is ignored due to trigger may be out-of-service.";
                        }

                        ///nokia-state/state/log/event-trigger/auto-prov/statistics/total
                        leaf total {
                            type yang:counter32;
                            description "Sum of success + error-no-entry + error-admin-state.";
                        }

                    } // container statistics

                    ///nokia-state/state/log/event-trigger/auto-prov/summary-entry-statistics
                    container summary-entry-statistics {
                        description "Enter the summary-entry-statistics context";

                        ///nokia-state/state/log/event-trigger/auto-prov/summary-entry-statistics/filter-match
                        leaf filter-match {
                            type yang:counter32;
                            description "Indicates the number of times a filter matches an logger event.";
                        }

                        ///nokia-state/state/log/event-trigger/auto-prov/summary-entry-statistics/filter-fail
                        leaf filter-fail {
                            type yang:counter32;
                            description "Indicates the number of times a filter does not match an logger event.";
                        }

                        ///nokia-state/state/log/event-trigger/auto-prov/summary-entry-statistics/error-admin-state
                        leaf error-admin-state {
                            type yang:counter32;
                            description
                                "Indicates the number of times the logger event will be ignored due to
                                 admin state of EHS trigger entries is out-of-service.";
                        }

                        ///nokia-state/state/log/event-trigger/auto-prov/summary-entry-statistics/error-filter
                        leaf error-filter {
                            type yang:counter32;
                            description
                                "Indicates the number of times the logger event will be ignored due to filter
                                 is not operational or is not configured in EHS trigger entries.";
                        }

                        ///nokia-state/state/log/event-trigger/auto-prov/summary-entry-statistics/error-handler
                        leaf error-handler {
                            type yang:counter32;
                            description
                                "Indicates the number of times the logger event will be ignored due to handler
                                 is not operational or is not configured in EHS trigger entries.";
                        }

                        ///nokia-state/state/log/event-trigger/auto-prov/summary-entry-statistics/trigger-count
                        leaf trigger-count {
                            type yang:counter32;
                            description "Indicates the number of times script execution is triggered after filter match.";
                        }

                        ///nokia-state/state/log/event-trigger/auto-prov/summary-entry-statistics/debounce-count
                        leaf debounce-count {
                            type yang:counter32;
                            description "Indicates the number of times script is not executed due to debounce rule.";
                        }

                    } // container summary-entry-statistics

                    ///nokia-state/state/log/event-trigger/auto-prov/entry
                    list entry {
                        key "id";
                        description "Enter the entry list instance";

                        ///nokia-state/state/log/event-trigger/auto-prov/entry/id
                        leaf id {
                            type uint32 {
                                range "1..1500";
                            }
                            description "ID of the EHS event trigger entry";
                        }

                        ///nokia-state/state/log/event-trigger/auto-prov/entry/oper-state
                        leaf oper-state {
                            type types-sros:oper-state;
                            description "Indicates the operational state of the EHS Event Trigger Entry.";
                        }

                        ///nokia-state/state/log/event-trigger/auto-prov/entry/statistics
                        container statistics {
                            description "Enter the statistics context";

                            ///nokia-state/state/log/event-trigger/auto-prov/entry/statistics/filter-match
                            leaf filter-match {
                                type yang:counter32;
                                description
                                    "Indicates the number of times a filter, for the specified trigger entry,
                                     matches an logger event.";
                            }

                            ///nokia-state/state/log/event-trigger/auto-prov/entry/statistics/filter-fail
                            leaf filter-fail {
                                type yang:counter32;
                                description
                                    "Indicates the number of times a filter, for the specified trigger entry,
                                     does not match an logger event.";
                            }

                            ///nokia-state/state/log/event-trigger/auto-prov/entry/statistics/error-admin-state
                            leaf error-admin-state {
                                type yang:counter32;
                                description
                                    "Indicates the number of times the logger event will be ignored due to
                                     admin state of EHS trigger entry is out-of-service.";
                            }

                            ///nokia-state/state/log/event-trigger/auto-prov/entry/statistics/error-filter
                            leaf error-filter {
                                type yang:counter32;
                                description
                                    "Indicates the number of times the logger event will be ignored due to filter
                                     is not operational or is not configured in EHS trigger entry.";
                            }

                            ///nokia-state/state/log/event-trigger/auto-prov/entry/statistics/error-handler
                            leaf error-handler {
                                type yang:counter32;
                                description
                                    "Indicates the number of times the logger event will be ignored due to handler
                                     is not operational or is not configured in EHS trigger entry.";
                            }

                            ///nokia-state/state/log/event-trigger/auto-prov/entry/statistics/trigger-count
                            leaf trigger-count {
                                type yang:counter32;
                                description
                                    "Indicates the number of times script execution is triggered after filter match
                                     for the specified trigger entry.";
                            }

                            ///nokia-state/state/log/event-trigger/auto-prov/entry/statistics/debounce-count
                            leaf debounce-count {
                                type yang:counter32;
                                description
                                    "Indicates the number of times script is not executed due to debounce rule
                                     for the specified trigger entry.";
                            }

                        } // container statistics

                    } // list entry

                } // list auto-prov

                ///nokia-state/state/log/event-trigger/bfd
                list bfd {
                    key "event";
                    description "Enter the bfd list instance";

                    ///nokia-state/state/log/event-trigger/bfd/event
                    leaf event {
                        type types-log:bfd-events;
                        description "Log event as a trigger for one or more EHS handlers";
                    }

                    ///nokia-state/state/log/event-trigger/bfd/oper-state
                    leaf oper-state {
                        type types-sros:oper-state;
                        description "Indicates the operational state of the EHS Event Trigger.";
                    }

                    ///nokia-state/state/log/event-trigger/bfd/statistics
                    container statistics {
                        description "Enter the statistics context";

                        ///nokia-state/state/log/event-trigger/bfd/statistics/success
                        leaf success {
                            type yang:counter32;
                            description
                                "Indicates the number of not ignored logger event occurrences
                                 associated with EHS trigger.";
                        }

                        ///nokia-state/state/log/event-trigger/bfd/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/bfd/statistics/error-admin-state
                        leaf error-admin-state {
                            type yang:counter32;
                            description
                                "Indicates the number of ignored logger event occurrences associated
                                 with EHS trigger.

                                 Event is ignored due to trigger may be out-of-service.";
                        }

                        ///nokia-state/state/log/event-trigger/bfd/statistics/total
                        leaf total {
                            type yang:counter32;
                            description "Sum of success + error-no-entry + error-admin-state.";
                        }

                    } // container statistics

                    ///nokia-state/state/log/event-trigger/bfd/summary-entry-statistics
                    container summary-entry-statistics {
                        description "Enter the summary-entry-statistics context";

                        ///nokia-state/state/log/event-trigger/bfd/summary-entry-statistics/filter-match
                        leaf filter-match {
                            type yang:counter32;
                            description "Indicates the number of times a filter matches an logger event.";
                        }

                        ///nokia-state/state/log/event-trigger/bfd/summary-entry-statistics/filter-fail
                        leaf filter-fail {
                            type yang:counter32;
                            description "Indicates the number of times a filter does not match an logger event.";
                        }

                        ///nokia-state/state/log/event-trigger/bfd/summary-entry-statistics/error-admin-state
                        leaf error-admin-state {
                            type yang:counter32;
                            description
                                "Indicates the number of times the logger event will be ignored due to
                                 admin state of EHS trigger entries is out-of-service.";
                        }

                        ///nokia-state/state/log/event-trigger/bfd/summary-entry-statistics/error-filter
                        leaf error-filter {
                            type yang:counter32;
                            description
                                "Indicates the number of times the logger event will be ignored due to filter
                                 is not operational or is not configured in EHS trigger entries.";
                        }

                        ///nokia-state/state/log/event-trigger/bfd/summary-entry-statistics/error-handler
                        leaf error-handler {
                            type yang:counter32;
                            description
                                "Indicates the number of times the logger event will be ignored due to handler
                                 is not operational or is not configured in EHS trigger entries.";
                        }

                        ///nokia-state/state/log/event-trigger/bfd/summary-entry-statistics/trigger-count
                        leaf trigger-count {
                            type yang:counter32;
                            description "Indicates the number of times script execution is triggered after filter match.";
                        }

                        ///nokia-state/state/log/event-trigger/bfd/summary-entry-statistics/debounce-count
                        leaf debounce-count {
                            type yang:counter32;
                            description "Indicates the number of times script is not executed due to debounce rule.";
                        }

                    } // container summary-entry-statistics

                    ///nokia-state/state/log/event-trigger/bfd/entry
                    list entry {
                        key "id";
                        description "Enter the entry list instance";

                        ///nokia-state/state/log/event-trigger/bfd/entry/id
                        leaf id {
                            type uint32 {
                                range "1..1500";
                            }
                            description "ID of the EHS event trigger entry";
                        }

                        ///nokia-state/state/log/event-trigger/bfd/entry/oper-state
                        leaf oper-state {
                            type types-sros:oper-state;
                            description "Indicates the operational state of the EHS Event Trigger Entry.";
                        }

                        ///nokia-state/state/log/event-trigger/bfd/entry/statistics
                        container statistics {
                            description "Enter the statistics context";

                            ///nokia-state/state/log/event-trigger/bfd/entry/statistics/filter-match
                            leaf filter-match {
                                type yang:counter32;
                                description
                                    "Indicates the number of times a filter, for the specified trigger entry,
                                     matches an logger event.";
                            }

                            ///nokia-state/state/log/event-trigger/bfd/entry/statistics/filter-fail
                            leaf filter-fail {
                                type yang:counter32;
                                description
                                    "Indicates the number of times a filter, for the specified trigger entry,
                                     does not match an logger event.";
                            }

                            ///nokia-state/state/log/event-trigger/bfd/entry/statistics/error-admin-state
                            leaf error-admin-state {
                                type yang:counter32;
                                description
                                    "Indicates the number of times the logger event will be ignored due to
                                     admin state of EHS trigger entry is out-of-service.";
                            }

                            ///nokia-state/state/log/event-trigger/bfd/entry/statistics/error-filter
                            leaf error-filter {
                                type yang:counter32;
                                description
                                    "Indicates the number of times the logger event will be ignored due to filter
                                     is not operational or is not configured in EHS trigger entry.";
                            }

                            ///nokia-state/state/log/event-trigger/bfd/entry/statistics/error-handler
                            leaf error-handler {
                                type yang:counter32;
                                description
                                    "Indicates the number of times the logger event will be ignored due to handler
                                     is not operational or is not configured in EHS trigger entry.";
                            }

                            ///nokia-state/state/log/event-trigger/bfd/entry/statistics/trigger-count
                            leaf trigger-count {
                                type yang:counter32;
                                description
                                    "Indicates the number of times script execution is triggered after filter match
                                     for the specified trigger entry.";
                            }

                            ///nokia-state/state/log/event-trigger/bfd/entry/statistics/debounce-count
                            leaf debounce-count {
                                type yang:counter32;
                                description
                                    "Indicates the number of times script is not executed due to debounce rule
                                     for the specified trigger entry.";
                            }

                        } // container statistics

                    } // list entry

                } // list bfd

                ///nokia-state/state/log/event-trigger/bgp
                list bgp {
                    key "event";
                    description "Enter the bgp list instance";

                    ///nokia-state/state/log/event-trigger/bgp/event
                    leaf event {
                        type types-log:bgp-events;
                        description "Log event as a trigger for one or more EHS handlers";
                    }

                    ///nokia-state/state/log/event-trigger/bgp/oper-state
                    leaf oper-state {
                        type types-sros:oper-state;
                        description "Indicates the operational state of the EHS Event Trigger.";
                    }

                    ///nokia-state/state/log/event-trigger/bgp/statistics
                    container statistics {
                        description "Enter the statistics context";

                        ///nokia-state/state/log/event-trigger/bgp/statistics/success
                        leaf success {
                            type yang:counter32;
                            description
                                "Indicates the number of not ignored logger event occurrences
                                 associated with EHS trigger.";
                        }

                        ///nokia-state/state/log/event-trigger/bgp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/bgp/statistics/error-admin-state
                        leaf error-admin-state {
                            type yang:counter32;
                            description
                                "Indicates the number of ignored logger event occurrences associated
                                 with EHS trigger.

                                 Event is ignored due to trigger may be out-of-service.";
                        }

                        ///nokia-state/state/log/event-trigger/bgp/statistics/total
                        leaf total {
                            type yang:counter32;
                            description "Sum of success + error-no-entry + error-admin-state.";
                        }

                    } // container statistics

                    ///nokia-state/state/log/event-trigger/bgp/summary-entry-statistics
                    container summary-entry-statistics {
                        description "Enter the summary-entry-statistics context";

                        ///nokia-state/state/log/event-trigger/bgp/summary-entry-statistics/filter-match
                        leaf filter-match {
                            type yang:counter32;
                            description "Indicates the number of times a filter matches an logger event.";
                        }

                        ///nokia-state/state/log/event-trigger/bgp/summary-entry-statistics/filter-fail
                        leaf filter-fail {
                            type yang:counter32;
                            description "Indicates the number of times a filter does not match an logger event.";
                        }

                        ///nokia-state/state/log/event-trigger/bgp/summary-entry-statistics/error-admin-state
                        leaf error-admin-state {
                            type yang:counter32;
                            description
                                "Indicates the number of times the logger event will be ignored due to
                                 admin state of EHS trigger entries is out-of-service.";
                        }

                        ///nokia-state/state/log/event-trigger/bgp/summary-entry-statistics/error-filter
                        leaf error-filter {
                            type yang:counter32;
                            description
                                "Indicates the number of times the logger event will be ignored due to filter
                                 is not operational or is not configured in EHS trigger entries.";
                        }

                        ///nokia-state/state/log/event-trigger/bgp/summary-entry-statistics/error-handler
                        leaf error-handler {
                            type yang:counter32;
                            description
                                "Indicates the number of times the logger event will be ignored due to handler
                                 is not operational or is not configured in EHS trigger entries.";
                        }

                        ///nokia-state/state/log/event-trigger/bgp/summary-entry-statistics/trigger-count
                        leaf trigger-count {
                            type yang:counter32;
                            description "Indicates the number of times script execution is triggered after filter match.";
                        }

                        ///nokia-state/state/log/event-trigger/bgp/summary-entry-statistics/debounce-count
                        leaf debounce-count {
                            type yang:counter32;
                            description "Indicates the number of times script is not executed due to debounce rule.";
                        }

                    } // container summary-entry-statistics

                    ///nokia-state/state/log/event-trigger/bgp/entry
                    list entry {
                        key "id";
                        description "Enter the entry list instance";

                        ///nokia-state/state/log/event-trigger/bgp/entry/id
                        leaf id {
                            type uint32 {
                                range "1..1500";
                            }
                            description "ID of the EHS event trigger entry";
                        }

                        ///nokia-state/state/log/event-trigger/bgp/entry/oper-state
                        leaf oper-state {
                            type types-sros:oper-state;
                            description "Indicates the operational state of the EHS Event Trigger Entry.";
                        }

                        ///nokia-state/state/log/event-trigger/bgp/entry/statistics
                        container statistics {
                            description "Enter the statistics context";

                            ///nokia-state/state/log/event-trigger/bgp/entry/statistics/filter-match
                            leaf filter-match {
                                type yang:counter32;
                                description
                                    "Indicates the number of times a filter, for the specified trigger entry,
                                     matches an logger event.";
                            }

                            ///nokia-state/state/log/event-trigger/bgp/entry/statistics/filter-fail
                            leaf filter-fail {
                                type yang:counter32;
                                description
                                    "Indicates the number of times a filter, for the specified trigger entry,
                                     does not match an logger event.";
                            }

                            ///nokia-state/state/log/event-trigger/bgp/entry/statistics/error-admin-state
                            leaf error-admin-state {
                                type yang:counter32;
                                description
                                    "Indicates the number of times the logger event will be ignored due to
                                     admin state of EHS trigger entry is out-of-service.";
                            }

                            ///nokia-state/state/log/event-trigger/bgp/entry/statistics/error-filter
                            leaf error-filter {
                                type yang:counter32;
                                description
                                    "Indicates the number of times the logger event will be ignored due to filter
                                     is not operational or is not configured in EHS trigger entry.";
                            }

                            ///nokia-state/state/log/event-trigger/bgp/entry/statistics/error-handler
                            leaf error-handler {
                                type yang:counter32;
                                description
                                    "Indicates the number of times the logger event will be ignored due to handler
                                     is not operational or is not configured in EHS trigger entry.";
                            }

                            ///nokia-state/state/log/event-trigger/bgp/entry/statistics/trigger-count
                            leaf trigger-count {
                                type yang:counter32;
                                description
                                    "Indicates the number of times script execution is triggered after filter match
                                     for the specified trigger entry.";
                            }

                            ///nokia-state/state/log/event-trigger/bgp/entry/statistics/debounce-count
                            leaf debounce-count {
                                type yang:counter32;
                                description
                                    "Indicates the number of times script is not executed due to debounce rule
                                     for the specified trigger entry.";
                            }

                        } // container statistics

                    } // list entry

                } // list bgp

                ///nokia-state/state/log/event-trigger/bier
                list bier {
                    key "event";
                    description "Enter the bier list instance";

                    ///nokia-state/state/log/event-trigger/bier/event
                    leaf event {
                        type types-log:bier-events;
                        description "Log event as a trigger for one or more EHS handlers";
                    }

                    ///nokia-state/state/log/event-trigger/bier/oper-state
                    leaf oper-state {
                        type types-sros:oper-state;
                        description "Indicates the operational state of the EHS Event Trigger.";
                    }

                    ///nokia-state/state/log/event-trigger/bier/statistics
                    container statistics {
                        description "Enter the statistics context";

                        ///nokia-state/state/log/event-trigger/bier/statistics/success
                        leaf success {
                            type yang:counter32;
                            description
                                "Indicates the number of not ignored logger event occurrences
                                 associated with EHS trigger.";
                        }

                        ///nokia-state/state/log/event-trigger/bier/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/bier/statistics/error-admin-state
                        leaf error-admin-state {
                            type yang:counter32;
                            description
                                "Indicates the number of ignored logger event occurrences associated
                                 with EHS trigger.

                                 Event is ignored due to trigger may be out-of-service.";
                        }

                        ///nokia-state/state/log/event-trigger/bier/statistics/total
                        leaf total {
                            type yang:counter32;
                            description "Sum of success + error-no-entry + error-admin-state.";
                        }

                    } // container statistics

                    ///nokia-state/state/log/event-trigger/bier/summary-entry-statistics
                    container summary-entry-statistics {
                        description "Enter the summary-entry-statistics context";

                        ///nokia-state/state/log/event-trigger/bier/summary-entry-statistics/filter-match
                        leaf filter-match {
                            type yang:counter32;
                            description "Indicates the number of times a filter matches an logger event.";
                        }

                        ///nokia-state/state/log/event-trigger/bier/summary-entry-statistics/filter-fail
                        leaf filter-fail {
                            type yang:counter32;
                            description "Indicates the number of times a filter does not match an logger event.";
                        }

                        ///nokia-state/state/log/event-trigger/bier/summary-entry-statistics/error-admin-state
                        leaf error-admin-state {
                            type yang:counter32;
                            description
                                "Indicates the number of times the logger event will be ignored due to
                                 admin state of EHS trigger entries is out-of-service.";
                        }

                        ///nokia-state/state/log/event-trigger/bier/summary-entry-statistics/error-filter
                        leaf error-filter {
                            type yang:counter32;
                            description
                                "Indicates the number of times the logger event will be ignored due to filter
                                 is not operational or is not configured in EHS trigger entries.";
                        }

                        ///nokia-state/state/log/event-trigger/bier/summary-entry-statistics/error-handler
                        leaf error-handler {
                            type yang:counter32;
                            description
                                "Indicates the number of times the logger event will be ignored due to handler
                                 is not operational or is not configured in EHS trigger entries.";
                        }

                        ///nokia-state/state/log/event-trigger/bier/summary-entry-statistics/trigger-count
                        leaf trigger-count {
                            type yang:counter32;
                            description "Indicates the number of times script execution is triggered after filter match.";
                        }

                        ///nokia-state/state/log/event-trigger/bier/summary-entry-statistics/debounce-count
                        leaf debounce-count {
                            type yang:counter32;
                            description "Indicates the number of times script is not executed due to debounce rule.";
                        }

                    } // container summary-entry-statistics

                    ///nokia-state/state/log/event-trigger/bier/entry
                    list entry {
                        key "id";
                        description "Enter the entry list instance";

                        ///nokia-state/state/log/event-trigger/bier/entry/id
                        leaf id {
                            type uint32 {
                                range "1..1500";
                            }
                            description "ID of the EHS event trigger entry";
                        }

                        ///nokia-state/state/log/event-trigger/bier/entry/oper-state
                        leaf oper-state {
                            type types-sros:oper-state;
                            description "Indicates the operational state of the EHS Event Trigger Entry.";
                        }

                        ///nokia-state/state/log/event-trigger/bier/entry/statistics
                        container statistics {
                            description "Enter the statistics context";

                            ///nokia-state/state/log/event-trigger/bier/entry/statistics/filter-match
                            leaf filter-match {
                                type yang:counter32;
                                description
                                    "Indicates the number of times a filter, for the specified trigger entry,
                                     matches an logger event.";
                            }

                            ///nokia-state/state/log/event-trigger/bier/entry/statistics/filter-fail
                            leaf filter-fail {
                                type yang:counter32;
                                description
                                    "Indicates the number of times a filter, for the specified trigger entry,
                                     does not match an logger event.";
                            }

                            ///nokia-state/state/log/event-trigger/bier/entry/statistics/error-admin-state
                            leaf error-admin-state {
                                type yang:counter32;
                                description
                                    "Indicates the number of times the logger event will be ignored due to
                                     admin state of EHS trigger entry is out-of-service.";
                            }

                            ///nokia-state/state/log/event-trigger/bier/entry/statistics/error-filter
                            leaf error-filter {
                                type yang:counter32;
                                description
                                    "Indicates the number of times the logger event will be ignored due to filter
                                     is not operational or is not configured in EHS trigger entry.";
                            }

                            ///nokia-state/state/log/event-trigger/bier/entry/statistics/error-handler
                            leaf error-handler {
                                type yang:counter32;
                                description
                                    "Indicates the number of times the logger event will be ignored due to handler
                                     is not operational or is not configured in EHS trigger entry.";
                            }

                            ///nokia-state/state/log/event-trigger/bier/entry/statistics/trigger-count
                            leaf trigger-count {
                                type yang:counter32;
                                description
                                    "Indicates the number of times script execution is triggered after filter match
                                     for the specified trigger entry.";
                            }

                            ///nokia-state/state/log/event-trigger/bier/entry/statistics/debounce-count
                            leaf debounce-count {
                                type yang:counter32;
                                description
                                    "Indicates the number of times script is not executed due to debounce rule
                                     for the specified trigger entry.";
                            }

                        } // container statistics

                    } // list entry

                } // list bier

                ///nokia-state/state/log/event-trigger/calltrace
                list calltrace {
                    key "event";
                    description "Enter the calltrace list instance";

                    ///nokia-state/state/log/event-trigger/calltrace/event
                    leaf event {
                        type types-log:calltrace-events;
                        description "Log event as a trigger for one or more EHS handlers";
                    }

                    ///nokia-state/state/log/event-trigger/calltrace/oper-state
                    leaf oper-state {
                        type types-sros:oper-state;
                        description "Indicates the operational state of the EHS Event Trigger.";
                    }

                    ///nokia-state/state/log/event-trigger/calltrace/statistics
                    container statistics {
                        description "Enter the statistics context";

                        ///nokia-state/state/log/event-trigger/calltrace/statistics/success
                        leaf success {
                            type yang:counter32;
                            description
                                "Indicates the number of not ignored logger event occurrences
                                 associated with EHS trigger.";
                        }

                        ///nokia-state/state/log/event-trigger/calltrace/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/calltrace/statistics/error-admin-state
                        leaf error-admin-state {
                            type yang:counter32;
                            description
                                "Indicates the number of ignored logger event occurrences associated
                                 with EHS trigger.

                                 Event is ignored due to trigger may be out-of-service.";
                        }

                        ///nokia-state/state/log/event-trigger/calltrace/statistics/total
                        leaf total {
                            type yang:counter32;
                            description "Sum of success + error-no-entry + error-admin-state.";
                        }

                    } // container statistics

                    ///nokia-state/state/log/event-trigger/calltrace/summary-entry-statistics
                    container summary-entry-statistics {
                        description "Enter the summary-entry-statistics context";

                        ///nokia-state/state/log/event-trigger/calltrace/summary-entry-statistics/filter-match
                        leaf filter-match {
                            type yang:counter32;
                            description "Indicates the number of times a filter matches an logger event.";
                        }

                        ///nokia-state/state/log/event-trigger/calltrace/summary-entry-statistics/filter-fail
                        leaf filter-fail {
                            type yang:counter32;
                            description "Indicates the number of times a filter does not match an logger event.";
                        }

                        ///nokia-state/state/log/event-trigger/calltrace/summary-entry-statistics/error-admin-state
                        leaf error-admin-state {
                            type yang:counter32;
                            description
                                "Indicates the number of times the logger event will be ignored due to
                                 admin state of EHS trigger entries is out-of-service.";
                        }

                        ///nokia-state/state/log/event-trigger/calltrace/summary-entry-statistics/error-filter
                        leaf error-filter {
                            type yang:counter32;
                            description
                                "Indicates the number of times the logger event will be ignored due to filter
                                 is not operational or is not configured in EHS trigger entries.";
                        }

                        ///nokia-state/state/log/event-trigger/calltrace/summary-entry-statistics/error-handler
                        leaf error-handler {
                            type yang:counter32;
                            description
                                "Indicates the number of times the logger event will be ignored due to handler
                                 is not operational or is not configured in EHS trigger entries.";
                        }

                        ///nokia-state/state/log/event-trigger/calltrace/summary-entry-statistics/trigger-count
                        leaf trigger-count {
                            type yang:counter32;
                            description "Indicates the number of times script execution is triggered after filter match.";
                        }

                        ///nokia-state/state/log/event-trigger/calltrace/summary-entry-statistics/debounce-count
                        leaf debounce-count {
                            type yang:counter32;
                            description "Indicates the number of times script is not executed due to debounce rule.";
                        }

                    } // container summary-entry-statistics

                    ///nokia-state/state/log/event-trigger/calltrace/entry
                    list entry {
                        key "id";
                        description "Enter the entry list instance";

                        ///nokia-state/state/log/event-trigger/calltrace/entry/id
                        leaf id {
                            type uint32 {
                                range "1..1500";
                            }
                            description "ID of the EHS event trigger entry";
                        }

                        ///nokia-state/state/log/event-trigger/calltrace/entry/oper-state
                        leaf oper-state {
                            type types-sros:oper-state;
                            description "Indicates the operational state of the EHS Event Trigger Entry.";
                        }

                        ///nokia-state/state/log/event-trigger/calltrace/entry/statistics
                        container statistics {
                            description "Enter the statistics context";

                            ///nokia-state/state/log/event-trigger/calltrace/entry/statistics/filter-match
                            leaf filter-match {
                                type yang:counter32;
                                description
                                    "Indicates the number of times a filter, for the specified trigger entry,
                                     matches an logger event.";
                            }

                            ///nokia-state/state/log/event-trigger/calltrace/entry/statistics/filter-fail
                            leaf filter-fail {
                                type yang:counter32;
                                description
                                    "Indicates the number of times a filter, for the specified trigger entry,
                                     does not match an logger event.";
                            }

                            ///nokia-state/state/log/event-trigger/calltrace/entry/statistics/error-admin-state
                            leaf error-admin-state {
                                type yang:counter32;
                                description
                                    "Indicates the number of times the logger event will be ignored due to
                                     admin state of EHS trigger entry is out-of-service.";
                            }

                            ///nokia-state/state/log/event-trigger/calltrace/entry/statistics/error-filter
                            leaf error-filter {
                                type yang:counter32;
                                description
                                    "Indicates the number of times the logger event will be ignored due to filter
                                     is not operational or is not configured in EHS trigger entry.";
                            }

                            ///nokia-state/state/log/event-trigger/calltrace/entry/statistics/error-handler
                            leaf error-handler {
                                type yang:counter32;
                                description
                                    "Indicates the number of times the logger event will be ignored due to handler
                                     is not operational or is not configured in EHS trigger entry.";
                            }

                            ///nokia-state/state/log/event-trigger/calltrace/entry/statistics/trigger-count
                            leaf trigger-count {
                                type yang:counter32;
                                description
                                    "Indicates the number of times script execution is triggered after filter match
                                     for the specified trigger entry.";
                            }

                            ///nokia-state/state/log/event-trigger/calltrace/entry/statistics/debounce-count
                            leaf debounce-count {
                                type yang:counter32;
                                description
                                    "Indicates the number of times script is not executed due to debounce rule
                                     for the specified trigger entry.";
                            }

                        } // container statistics

                    } // list entry

                } // list calltrace

                ///nokia-state/state/log/event-trigger/cflowd
                list cflowd {
                    key "event";
                    description "Enter the cflowd list instance";

                    ///nokia-state/state/log/event-trigger/cflowd/event
                    leaf event {
                        type types-log:cflowd-events;
                        description "Log event as a trigger for one or more EHS handlers";
                    }

                    ///nokia-state/state/log/event-trigger/cflowd/oper-state
                    leaf oper-state {
                        type types-sros:oper-state;
                        description "Indicates the operational state of the EHS Event Trigger.";
                    }

                    ///nokia-state/state/log/event-trigger/cflowd/statistics
                    container statistics {
                        description "Enter the statistics context";

                        ///nokia-state/state/log/event-trigger/cflowd/statistics/success
                        leaf success {
                            type yang:counter32;
                            description
                                "Indicates the number of not ignored logger event occurrences
                                 associated with EHS trigger.";
                        }

                        ///nokia-state/state/log/event-trigger/cflowd/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/cflowd/statistics/error-admin-state
                        leaf error-admin-state {
                            type yang:counter32;
                            description
                                "Indicates the number of ignored logger event occurrences associated
                                 with EHS trigger.

                                 Event is ignored due to trigger may be out-of-service.";
                        }

                        ///nokia-state/state/log/event-trigger/cflowd/statistics/total
                        leaf total {
                            type yang:counter32;
                            description "Sum of success + error-no-entry + error-admin-state.";
                        }

                    } // container statistics

                    ///nokia-state/state/log/event-trigger/cflowd/summary-entry-statistics
                    container summary-entry-statistics {
                        description "Enter the summary-entry-statistics context";

                        ///nokia-state/state/log/event-trigger/cflowd/summary-entry-statistics/filter-match
                        leaf filter-match {
                            type yang:counter32;
                            description "Indicates the number of times a filter matches an logger event.";
                        }

                        ///nokia-state/state/log/event-trigger/cflowd/summary-entry-statistics/filter-fail
                        leaf filter-fail {
                            type yang:counter32;
                            description "Indicates the number of times a filter does not match an logger event.";
                        }

                        ///nokia-state/state/log/event-trigger/cflowd/summary-entry-statistics/error-admin-state
                        leaf error-admin-state {
                            type yang:counter32;
                            description
                                "Indicates the number of times the logger event will be ignored due to
                                 admin state of EHS trigger entries is out-of-service.";
                        }

                        ///nokia-state/state/log/event-trigger/cflowd/summary-entry-statistics/error-filter
                        leaf error-filter {
                            type yang:counter32;
                            description
                                "Indicates the number of times the logger event will be ignored due to filter
                                 is not operational or is not configured in EHS trigger entries.";
                        }

                        ///nokia-state/state/log/event-trigger/cflowd/summary-entry-statistics/error-handler
                        leaf error-handler {
                            type yang:counter32;
                            description
                                "Indicates the number of times the logger event will be ignored due to handler
                                 is not operational or is not configured in EHS trigger entries.";
                        }

                        ///nokia-state/state/log/event-trigger/cflowd/summary-entry-statistics/trigger-count
                        leaf trigger-count {
                            type yang:counter32;
                            description "Indicates the number of times script execution is triggered after filter match.";
                        }

                        ///nokia-state/state/log/event-trigger/cflowd/summary-entry-statistics/debounce-count
                        leaf debounce-count {
                            type yang:counter32;
                            description "Indicates the number of times script is not executed due to debounce rule.";
                        }

                    } // container summary-entry-statistics

                    ///nokia-state/state/log/event-trigger/cflowd/entry
                    list entry {
                        key "id";
                        description "Enter the entry list instance";

                        ///nokia-state/state/log/event-trigger/cflowd/entry/id
                        leaf id {
                            type uint32 {
                                range "1..1500";
                            }
                            description "ID of the EHS event trigger entry";
                        }

                        ///nokia-state/state/log/event-trigger/cflowd/entry/oper-state
                        leaf oper-state {
                            type types-sros:oper-state;
                            description "Indicates the operational state of the EHS Event Trigger Entry.";
                        }

                        ///nokia-state/state/log/event-trigger/cflowd/entry/statistics
                        container statistics {
                            description "Enter the statistics context";

                            ///nokia-state/state/log/event-trigger/cflowd/entry/statistics/filter-match
                            leaf filter-match {
                                type yang:counter32;
                                description
                                    "Indicates the number of times a filter, for the specified trigger entry,
                                     matches an logger event.";
                            }

                            ///nokia-state/state/log/event-trigger/cflowd/entry/statistics/filter-fail
                            leaf filter-fail {
                                type yang:counter32;
                                description
                                    "Indicates the number of times a filter, for the specified trigger entry,
                                     does not match an logger event.";
                            }

                            ///nokia-state/state/log/event-trigger/cflowd/entry/statistics/error-admin-state
                            leaf error-admin-state {
                                type yang:counter32;
                                description
                                    "Indicates the number of times the logger event will be ignored due to
                                     admin state of EHS trigger entry is out-of-service.";
                            }

                            ///nokia-state/state/log/event-trigger/cflowd/entry/statistics/error-filter
                            leaf error-filter {
                                type yang:counter32;
                                description
                                    "Indicates the number of times the logger event will be ignored due to filter
                                     is not operational or is not configured in EHS trigger entry.";
                            }

                            ///nokia-state/state/log/event-trigger/cflowd/entry/statistics/error-handler
                            leaf error-handler {
                                type yang:counter32;
                                description
                                    "Indicates the number of times the logger event will be ignored due to handler
                                     is not operational or is not configured in EHS trigger entry.";
                            }

                            ///nokia-state/state/log/event-trigger/cflowd/entry/statistics/trigger-count
                            leaf trigger-count {
                                type yang:counter32;
                                description
                                    "Indicates the number of times script execution is triggered after filter match
                                     for the specified trigger entry.";
                            }

                            ///nokia-state/state/log/event-trigger/cflowd/entry/statistics/debounce-count
                            leaf debounce-count {
                                type yang:counter32;
                                description
                                    "Indicates the number of times script is not executed due to debounce rule
                                     for the specified trigger entry.";
                            }

                        } // container statistics

                    } // list entry

                } // list cflowd

                ///nokia-state/state/log/event-trigger/chassis
                list chassis {
                    key "event";
                    description "Enter the chassis list instance";

                    ///nokia-state/state/log/event-trigger/chassis/event
                    leaf event {
                        type types-log:chassis-events;
                        description "Log event as a trigger for one or more EHS handlers";
                    }

                    ///nokia-state/state/log/event-trigger/chassis/oper-state
                    leaf oper-state {
                        type types-sros:oper-state;
                        description "Indicates the operational state of the EHS Event Trigger.";
                    }

                    ///nokia-state/state/log/event-trigger/chassis/statistics
                    container statistics {
                        description "Enter the statistics context";

                        ///nokia-state/state/log/event-trigger/chassis/statistics/success
                        leaf success {
                            type yang:counter32;
                            description
                                "Indicates the number of not ignored logger event occurrences
                                 associated with EHS trigger.";
                        }

                        ///nokia-state/state/log/event-trigger/chassis/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/chassis/statistics/error-admin-state
                        leaf error-admin-state {
                            type yang:counter32;
                            description
                                "Indicates the number of ignored logger event occurrences associated
                                 with EHS trigger.

                                 Event is ignored due to trigger may be out-of-service.";
                        }

                        ///nokia-state/state/log/event-trigger/chassis/statistics/total
                        leaf total {
                            type yang:counter32;
                            description "Sum of success + error-no-entry + error-admin-state.";
                        }

                    } // container statistics

                    ///nokia-state/state/log/event-trigger/chassis/summary-entry-statistics
                    container summary-entry-statistics {
                        description "Enter the summary-entry-statistics context";

                        ///nokia-state/state/log/event-trigger/chassis/summary-entry-statistics/filter-match
                        leaf filter-match {
                            type yang:counter32;
                            description "Indicates the number of times a filter matches an logger event.";
                        }

                        ///nokia-state/state/log/event-trigger/chassis/summary-entry-statistics/filter-fail
                        leaf filter-fail {
                            type yang:counter32;
                            description "Indicates the number of times a filter does not match an logger event.";
                        }

                        ///nokia-state/state/log/event-trigger/chassis/summary-entry-statistics/error-admin-state
                        leaf error-admin-state {
                            type yang:counter32;
                            description
                                "Indicates the number of times the logger event will be ignored due to
                                 admin state of EHS trigger entries is out-of-service.";
                        }

                        ///nokia-state/state/log/event-trigger/chassis/summary-entry-statistics/error-filter
                        leaf error-filter {
                            type yang:counter32;
                            description
                                "Indicates the number of times the logger event will be ignored due to filter
                                 is not operational or is not configured in EHS trigger entries.";
                        }

                        ///nokia-state/state/log/event-trigger/chassis/summary-entry-statistics/error-handler
                        leaf error-handler {
                            type yang:counter32;
                            description
                                "Indicates the number of times the logger event will be ignored due to handler
                                 is not operational or is not configured in EHS trigger entries.";
                        }

                        ///nokia-state/state/log/event-trigger/chassis/summary-entry-statistics/trigger-count
                        leaf trigger-count {
                            type yang:counter32;
                            description "Indicates the number of times script execution is triggered after filter match.";
                        }

                        ///nokia-state/state/log/event-trigger/chassis/summary-entry-statistics/debounce-count
                        leaf debounce-count {
                            type yang:counter32;
                            description "Indicates the number of times script is not executed due to debounce rule.";
                        }

                    } // container summary-entry-statistics

                    ///nokia-state/state/log/event-trigger/chassis/entry
                    list entry {
                        key "id";
                        description "Enter the entry list instance";

                        ///nokia-state/state/log/event-trigger/chassis/entry/id
                        leaf id {
                            type uint32 {
                                range "1..1500";
                            }
                            description "ID of the EHS event trigger entry";
                        }

                        ///nokia-state/state/log/event-trigger/chassis/entry/oper-state
                        leaf oper-state {
                            type types-sros:oper-state;
                            description "Indicates the operational state of the EHS Event Trigger Entry.";
                        }

                        ///nokia-state/state/log/event-trigger/chassis/entry/statistics
                        container statistics {
                            description "Enter the statistics context";

                            ///nokia-state/state/log/event-trigger/chassis/entry/statistics/filter-match
                            leaf filter-match {
                                type yang:counter32;
                                description
                                    "Indicates the number of times a filter, for the specified trigger entry,
                                     matches an logger event.";
                            }

                            ///nokia-state/state/log/event-trigger/chassis/entry/statistics/filter-fail
                            leaf filter-fail {
                                type yang:counter32;
                                description
                                    "Indicates the number of times a filter, for the specified trigger entry,
                                     does not match an logger event.";
                            }

                            ///nokia-state/state/log/event-trigger/chassis/entry/statistics/error-admin-state
                            leaf error-admin-state {
                                type yang:counter32;
                                description
                                    "Indicates the number of times the logger event will be ignored due to
                                     admin state of EHS trigger entry is out-of-service.";
                            }

                            ///nokia-state/state/log/event-trigger/chassis/entry/statistics/error-filter
                            leaf error-filter {
                                type yang:counter32;
                                description
                                    "Indicates the number of times the logger event will be ignored due to filter
                                     is not operational or is not configured in EHS trigger entry.";
                            }

                            ///nokia-state/state/log/event-trigger/chassis/entry/statistics/error-handler
                            leaf error-handler {
                                type yang:counter32;
                                description
                                    "Indicates the number of times the logger event will be ignored due to handler
                                     is not operational or is not configured in EHS trigger entry.";
                            }

                            ///nokia-state/state/log/event-trigger/chassis/entry/statistics/trigger-count
                            leaf trigger-count {
                                type yang:counter32;
                                description
                                    "Indicates the number of times script execution is triggered after filter match
                                     for the specified trigger entry.";
                            }

                            ///nokia-state/state/log/event-trigger/chassis/entry/statistics/debounce-count
                            leaf debounce-count {
                                type yang:counter32;
                                description
                                    "Indicates the number of times script is not executed due to debounce rule
                                     for the specified trigger entry.";
                            }

                        } // container statistics

                    } // list entry

                } // list chassis

                ///nokia-state/state/log/event-trigger/debug
                list debug {
                    key "event";
                    description "Enter the debug list instance";

                    ///nokia-state/state/log/event-trigger/debug/event
                    leaf event {
                        type types-log:debug-events;
                        description "Log event as a trigger for one or more EHS handlers";
                    }

                    ///nokia-state/state/log/event-trigger/debug/oper-state
                    leaf oper-state {
                        type types-sros:oper-state;
                        description "Indicates the operational state of the EHS Event Trigger.";
                    }

                    ///nokia-state/state/log/event-trigger/debug/statistics
                    container statistics {
                        description "Enter the statistics context";

                        ///nokia-state/state/log/event-trigger/debug/statistics/success
                        leaf success {
                            type yang:counter32;
                            description
                                "Indicates the number of not ignored logger event occurrences
                                 associated with EHS trigger.";
                        }

                        ///nokia-state/state/log/event-trigger/debug/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/debug/statistics/error-admin-state
                        leaf error-admin-state {
                            type yang:counter32;
                            description
                                "Indicates the number of ignored logger event occurrences associated
                                 with EHS trigger.

                                 Event is ignored due to trigger may be out-of-service.";
                        }

                        ///nokia-state/state/log/event-trigger/debug/statistics/total
                        leaf total {
                            type yang:counter32;
                            description "Sum of success + error-no-entry + error-admin-state.";
                        }

                    } // container statistics

                    ///nokia-state/state/log/event-trigger/debug/summary-entry-statistics
                    container summary-entry-statistics {
                        description "Enter the summary-entry-statistics context";

                        ///nokia-state/state/log/event-trigger/debug/summary-entry-statistics/filter-match
                        leaf filter-match {
                            type yang:counter32;
                            description "Indicates the number of times a filter matches an logger event.";
                        }

                        ///nokia-state/state/log/event-trigger/debug/summary-entry-statistics/filter-fail
                        leaf filter-fail {
                            type yang:counter32;
                            description "Indicates the number of times a filter does not match an logger event.";
                        }

                        ///nokia-state/state/log/event-trigger/debug/summary-entry-statistics/error-admin-state
                        leaf error-admin-state {
                            type yang:counter32;
                            description
                                "Indicates the number of times the logger event will be ignored due to
                                 admin state of EHS trigger entries is out-of-service.";
                        }

                        ///nokia-state/state/log/event-trigger/debug/summary-entry-statistics/error-filter
                        leaf error-filter {
                            type yang:counter32;
                            description
                                "Indicates the number of times the logger event will be ignored due to filter
                                 is not operational or is not configured in EHS trigger entries.";
                        }

                        ///nokia-state/state/log/event-trigger/debug/summary-entry-statistics/error-handler
                        leaf error-handler {
                            type yang:counter32;
                            description
                                "Indicates the number of times the logger event will be ignored due to handler
                                 is not operational or is not configured in EHS trigger entries.";
                        }

                        ///nokia-state/state/log/event-trigger/debug/summary-entry-statistics/trigger-count
                        leaf trigger-count {
                            type yang:counter32;
                            description "Indicates the number of times script execution is triggered after filter match.";
                        }

                        ///nokia-state/state/log/event-trigger/debug/summary-entry-statistics/debounce-count
                        leaf debounce-count {
                            type yang:counter32;
                            description "Indicates the number of times script is not executed due to debounce rule.";
                        }

                    } // container summary-entry-statistics

                    ///nokia-state/state/log/event-trigger/debug/entry
                    list entry {
                        key "id";
                        description "Enter the entry list instance";

                        ///nokia-state/state/log/event-trigger/debug/entry/id
                        leaf id {
                            type uint32 {
                                range "1..1500";
                            }
                            description "ID of the EHS event trigger entry";
                        }

                        ///nokia-state/state/log/event-trigger/debug/entry/oper-state
                        leaf oper-state {
                            type types-sros:oper-state;
                            description "Indicates the operational state of the EHS Event Trigger Entry.";
                        }

                        ///nokia-state/state/log/event-trigger/debug/entry/statistics
                        container statistics {
                            description "Enter the statistics context";

                            ///nokia-state/state/log/event-trigger/debug/entry/statistics/filter-match
                            leaf filter-match {
                                type yang:counter32;
                                description
                                    "Indicates the number of times a filter, for the specified trigger entry,
                                     matches an logger event.";
                            }

                            ///nokia-state/state/log/event-trigger/debug/entry/statistics/filter-fail
                            leaf filter-fail {
                                type yang:counter32;
                                description
                                    "Indicates the number of times a filter, for the specified trigger entry,
                                     does not match an logger event.";
                            }

                            ///nokia-state/state/log/event-trigger/debug/entry/statistics/error-admin-state
                            leaf error-admin-state {
                                type yang:counter32;
                                description
                                    "Indicates the number of times the logger event will be ignored due to
                                     admin state of EHS trigger entry is out-of-service.";
                            }

                            ///nokia-state/state/log/event-trigger/debug/entry/statistics/error-filter
                            leaf error-filter {
                                type yang:counter32;
                                description
                                    "Indicates the number of times the logger event will be ignored due to filter
                                     is not operational or is not configured in EHS trigger entry.";
                            }

                            ///nokia-state/state/log/event-trigger/debug/entry/statistics/error-handler
                            leaf error-handler {
                                type yang:counter32;
                                description
                                    "Indicates the number of times the logger event will be ignored due to handler
                                     is not operational or is not configured in EHS trigger entry.";
                            }

                            ///nokia-state/state/log/event-trigger/debug/entry/statistics/trigger-count
                            leaf trigger-count {
                                type yang:counter32;
                                description
                                    "Indicates the number of times script execution is triggered after filter match
                                     for the specified trigger entry.";
                            }

                            ///nokia-state/state/log/event-trigger/debug/entry/statistics/debounce-count
                            leaf debounce-count {
                                type yang:counter32;
                                description
                                    "Indicates the number of times script is not executed due to debounce rule
                                     for the specified trigger entry.";
                            }

                        } // container statistics

                    } // list entry

                } // list debug

                ///nokia-state/state/log/event-trigger/dhcp
                list dhcp {
                    key "event";
                    description "Enter the dhcp list instance";

                    ///nokia-state/state/log/event-trigger/dhcp/event
                    leaf event {
                        type types-log:dhcp-events;
                        description "Log event as a trigger for one or more EHS handlers";
                    }

                    ///nokia-state/state/log/event-trigger/dhcp/oper-state
                    leaf oper-state {
                        type types-sros:oper-state;
                        description "Indicates the operational state of the EHS Event Trigger.";
                    }

                    ///nokia-state/state/log/event-trigger/dhcp/statistics
                    container statistics {
                        description "Enter the statistics context";

                        ///nokia-state/state/log/event-trigger/dhcp/statistics/success
                        leaf success {
                            type yang:counter32;
                            description
                                "Indicates the number of not ignored logger event occurrences
                                 associated with EHS trigger.";
                        }

                        ///nokia-state/state/log/event-trigger/dhcp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/dhcp/statistics/error-admin-state
                        leaf error-admin-state {
                            type yang:counter32;
                            description
                                "Indicates the number of ignored logger event occurrences associated
                                 with EHS trigger.

                                 Event is ignored due to trigger may be out-of-service.";
                        }

                        ///nokia-state/state/log/event-trigger/dhcp/statistics/total
                        leaf total {
                            type yang:counter32;
                            description "Sum of success + error-no-entry + error-admin-state.";
                        }

                    } // container statistics

                    ///nokia-state/state/log/event-trigger/dhcp/summary-entry-statistics
                    container summary-entry-statistics {
                        description "Enter the summary-entry-statistics context";

                        ///nokia-state/state/log/event-trigger/dhcp/summary-entry-statistics/filter-match
                        leaf filter-match {
                            type yang:counter32;
                            description "Indicates the number of times a filter matches an logger event.";
                        }

                        ///nokia-state/state/log/event-trigger/dhcp/summary-entry-statistics/filter-fail
                        leaf filter-fail {
                            type yang:counter32;
                            description "Indicates the number of times a filter does not match an logger event.";
                        }

                        ///nokia-state/state/log/event-trigger/dhcp/summary-entry-statistics/error-admin-state
                        leaf error-admin-state {
                            type yang:counter32;
                            description
                                "Indicates the number of times the logger event will be ignored due to
                                 admin state of EHS trigger entries is out-of-service.";
                        }

                        ///nokia-state/state/log/event-trigger/dhcp/summary-entry-statistics/error-filter
                        leaf error-filter {
                            type yang:counter32;
                            description
                                "Indicates the number of times the logger event will be ignored due to filter
                                 is not operational or is not configured in EHS trigger entries.";
                        }

                        ///nokia-state/state/log/event-trigger/dhcp/summary-entry-statistics/error-handler
                        leaf error-handler {
                            type yang:counter32;
                            description
                                "Indicates the number of times the logger event will be ignored due to handler
                                 is not operational or is not configured in EHS trigger entries.";
                        }

                        ///nokia-state/state/log/event-trigger/dhcp/summary-entry-statistics/trigger-count
                        leaf trigger-count {
                            type yang:counter32;
                            description "Indicates the number of times script execution is triggered after filter match.";
                        }

                        ///nokia-state/state/log/event-trigger/dhcp/summary-entry-statistics/debounce-count
                        leaf debounce-count {
                            type yang:counter32;
                            description "Indicates the number of times script is not executed due to debounce rule.";
                        }

                    } // container summary-entry-statistics

                    ///nokia-state/state/log/event-trigger/dhcp/entry
                    list entry {
                        key "id";
                        description "Enter the entry list instance";

                        ///nokia-state/state/log/event-trigger/dhcp/entry/id
                        leaf id {
                            type uint32 {
                                range "1..1500";
                            }
                            description "ID of the EHS event trigger entry";
                        }

                        ///nokia-state/state/log/event-trigger/dhcp/entry/oper-state
                        leaf oper-state {
                            type types-sros:oper-state;
                            description "Indicates the operational state of the EHS Event Trigger Entry.";
                        }

                        ///nokia-state/state/log/event-trigger/dhcp/entry/statistics
                        container statistics {
                            description "Enter the statistics context";

                            ///nokia-state/state/log/event-trigger/dhcp/entry/statistics/filter-match
                            leaf filter-match {
                                type yang:counter32;
                                description
                                    "Indicates the number of times a filter, for the specified trigger entry,
                                     matches an logger event.";
                            }

                            ///nokia-state/state/log/event-trigger/dhcp/entry/statistics/filter-fail
                            leaf filter-fail {
                                type yang:counter32;
                                description
                                    "Indicates the number of times a filter, for the specified trigger entry,
                                     does not match an logger event.";
                            }

                            ///nokia-state/state/log/event-trigger/dhcp/entry/statistics/error-admin-state
                            leaf error-admin-state {
                                type yang:counter32;
                                description
                                    "Indicates the number of times the logger event will be ignored due to
                                     admin state of EHS trigger entry is out-of-service.";
                            }

                            ///nokia-state/state/log/event-trigger/dhcp/entry/statistics/error-filter
                            leaf error-filter {
                                type yang:counter32;
                                description
                                    "Indicates the number of times the logger event will be ignored due to filter
                                     is not operational or is not configured in EHS trigger entry.";
                            }

                            ///nokia-state/state/log/event-trigger/dhcp/entry/statistics/error-handler
                            leaf error-handler {
                                type yang:counter32;
                                description
                                    "Indicates the number of times the logger event will be ignored due to handler
                                     is not operational or is not configured in EHS trigger entry.";
                            }

                            ///nokia-state/state/log/event-trigger/dhcp/entry/statistics/trigger-count
                            leaf trigger-count {
                                type yang:counter32;
                                description
                                    "Indicates the number of times script execution is triggered after filter match
                                     for the specified trigger entry.";
                            }

                            ///nokia-state/state/log/event-trigger/dhcp/entry/statistics/debounce-count
                            leaf debounce-count {
                                type yang:counter32;
                                description
                                    "Indicates the number of times script is not executed due to debounce rule
                                     for the specified trigger entry.";
                            }

                        } // container statistics

                    } // list entry

                } // list dhcp

                ///nokia-state/state/log/event-trigger/dhcps
                list dhcps {
                    key "event";
                    description "Enter the dhcps list instance";

                    ///nokia-state/state/log/event-trigger/dhcps/event
                    leaf event {
                        type types-log:dhcps-events;
                        description "Log event as a trigger for one or more EHS handlers";
                    }

                    ///nokia-state/state/log/event-trigger/dhcps/oper-state
                    leaf oper-state {
                        type types-sros:oper-state;
                        description "Indicates the operational state of the EHS Event Trigger.";
                    }

                    ///nokia-state/state/log/event-trigger/dhcps/statistics
                    container statistics {
                        description "Enter the statistics context";

                        ///nokia-state/state/log/event-trigger/dhcps/statistics/success
                        leaf success {
                            type yang:counter32;
                            description
                                "Indicates the number of not ignored logger event occurrences
                                 associated with EHS trigger.";
                        }

                        ///nokia-state/state/log/event-trigger/dhcps/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/dhcps/statistics/error-admin-state
                        leaf error-admin-state {
                            type yang:counter32;
                            description
                                "Indicates the number of ignored logger event occurrences associated
                                 with EHS trigger.

                                 Event is ignored due to trigger may be out-of-service.";
                        }

                        ///nokia-state/state/log/event-trigger/dhcps/statistics/total
                        leaf total {
                            type yang:counter32;
                            description "Sum of success + error-no-entry + error-admin-state.";
                        }

                    } // container statistics

                    ///nokia-state/state/log/event-trigger/dhcps/summary-entry-statistics
                    container summary-entry-statistics {
                        description "Enter the summary-entry-statistics context";

                        ///nokia-state/state/log/event-trigger/dhcps/summary-entry-statistics/filter-match
                        leaf filter-match {
                            type yang:counter32;
                            description "Indicates the number of times a filter matches an logger event.";
                        }

                        ///nokia-state/state/log/event-trigger/dhcps/summary-entry-statistics/filter-fail
                        leaf filter-fail {
                            type yang:counter32;
                            description "Indicates the number of times a filter does not match an logger event.";
                        }

                        ///nokia-state/state/log/event-trigger/dhcps/summary-entry-statistics/error-admin-state
                        leaf error-admin-state {
                            type yang:counter32;
                            description
                                "Indicates the number of times the logger event will be ignored due to
                                 admin state of EHS trigger entries is out-of-service.";
                        }

                        ///nokia-state/state/log/event-trigger/dhcps/summary-entry-statistics/error-filter
                        leaf error-filter {
                            type yang:counter32;
                            description
                                "Indicates the number of times the logger event will be ignored due to filter
                                 is not operational or is not configured in EHS trigger entries.";
                        }

                        ///nokia-state/state/log/event-trigger/dhcps/summary-entry-statistics/error-handler
                        leaf error-handler {
                            type yang:counter32;
                            description
                                "Indicates the number of times the logger event will be ignored due to handler
                                 is not operational or is not configured in EHS trigger entries.";
                        }

                        ///nokia-state/state/log/event-trigger/dhcps/summary-entry-statistics/trigger-count
                        leaf trigger-count {
                            type yang:counter32;
                            description "Indicates the number of times script execution is triggered after filter match.";
                        }

                        ///nokia-state/state/log/event-trigger/dhcps/summary-entry-statistics/debounce-count
                        leaf debounce-count {
                            type yang:counter32;
                            description "Indicates the number of times script is not executed due to debounce rule.";
                        }

                    } // container summary-entry-statistics

                    ///nokia-state/state/log/event-trigger/dhcps/entry
                    list entry {
                        key "id";
                        description "Enter the entry list instance";

                        ///nokia-state/state/log/event-trigger/dhcps/entry/id
                        leaf id {
                            type uint32 {
                                range "1..1500";
                            }
                            description "ID of the EHS event trigger entry";
                        }

                        ///nokia-state/state/log/event-trigger/dhcps/entry/oper-state
                        leaf oper-state {
                            type types-sros:oper-state;
                            description "Indicates the operational state of the EHS Event Trigger Entry.";
                        }

                        ///nokia-state/state/log/event-trigger/dhcps/entry/statistics
                        container statistics {
                            description "Enter the statistics context";

                            ///nokia-state/state/log/event-trigger/dhcps/entry/statistics/filter-match
                            leaf filter-match {
                                type yang:counter32;
                                description
                                    "Indicates the number of times a filter, for the specified trigger entry,
                                     matches an logger event.";
                            }

                            ///nokia-state/state/log/event-trigger/dhcps/entry/statistics/filter-fail
                            leaf filter-fail {
                                type yang:counter32;
                                description
                                    "Indicates the number of times a filter, for the specified trigger entry,
                                     does not match an logger event.";
                            }

                            ///nokia-state/state/log/event-trigger/dhcps/entry/statistics/error-admin-state
                            leaf error-admin-state {
                                type yang:counter32;
                                description
                                    "Indicates the number of times the logger event will be ignored due to
                                     admin state of EHS trigger entry is out-of-service.";
                            }

                            ///nokia-state/state/log/event-trigger/dhcps/entry/statistics/error-filter
                            leaf error-filter {
                                type yang:counter32;
                                description
                                    "Indicates the number of times the logger event will be ignored due to filter
                                     is not operational or is not configured in EHS trigger entry.";
                            }

                            ///nokia-state/state/log/event-trigger/dhcps/entry/statistics/error-handler
                            leaf error-handler {
                                type yang:counter32;
                                description
                                    "Indicates the number of times the logger event will be ignored due to handler
                                     is not operational or is not configured in EHS trigger entry.";
                            }

                            ///nokia-state/state/log/event-trigger/dhcps/entry/statistics/trigger-count
                            leaf trigger-count {
                                type yang:counter32;
                                description
                                    "Indicates the number of times script execution is triggered after filter match
                                     for the specified trigger entry.";
                            }

                            ///nokia-state/state/log/event-trigger/dhcps/entry/statistics/debounce-count
                            leaf debounce-count {
                                type yang:counter32;
                                description
                                    "Indicates the number of times script is not executed due to debounce rule
                                     for the specified trigger entry.";
                            }

                        } // container statistics

                    } // list entry

                } // list dhcps

                ///nokia-state/state/log/event-trigger/diameter
                list diameter {
                    key "event";
                    description "Enter the diameter list instance";

                    ///nokia-state/state/log/event-trigger/diameter/event
                    leaf event {
                        type types-log:diameter-events;
                        description "Log event as a trigger for one or more EHS handlers";
                    }

                    ///nokia-state/state/log/event-trigger/diameter/oper-state
                    leaf oper-state {
                        type types-sros:oper-state;
                        description "Indicates the operational state of the EHS Event Trigger.";
                    }

                    ///nokia-state/state/log/event-trigger/diameter/statistics
                    container statistics {
                        description "Enter the statistics context";

                        ///nokia-state/state/log/event-trigger/diameter/statistics/success
                        leaf success {
                            type yang:counter32;
                            description
                                "Indicates the number of not ignored logger event occurrences
                                 associated with EHS trigger.";
                        }

                        ///nokia-state/state/log/event-trigger/diameter/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/diameter/statistics/error-admin-state
                        leaf error-admin-state {
                            type yang:counter32;
                            description
                                "Indicates the number of ignored logger event occurrences associated
                                 with EHS trigger.

                                 Event is ignored due to trigger may be out-of-service.";
                        }

                        ///nokia-state/state/log/event-trigger/diameter/statistics/total
                        leaf total {
                            type yang:counter32;
                            description "Sum of success + error-no-entry + error-admin-state.";
                        }

                    } // container statistics

                    ///nokia-state/state/log/event-trigger/diameter/summary-entry-statistics
                    container summary-entry-statistics {
                        description "Enter the summary-entry-statistics context";

                        ///nokia-state/state/log/event-trigger/diameter/summary-entry-statistics/filter-match
                        leaf filter-match {
                            type yang:counter32;
                            description "Indicates the number of times a filter matches an logger event.";
                        }

                        ///nokia-state/state/log/event-trigger/diameter/summary-entry-statistics/filter-fail
                        leaf filter-fail {
                            type yang:counter32;
                            description "Indicates the number of times a filter does not match an logger event.";
                        }

                        ///nokia-state/state/log/event-trigger/diameter/summary-entry-statistics/error-admin-state
                        leaf error-admin-state {
                            type yang:counter32;
                            description
                                "Indicates the number of times the logger event will be ignored due to
                                 admin state of EHS trigger entries is out-of-service.";
                        }

                        ///nokia-state/state/log/event-trigger/diameter/summary-entry-statistics/error-filter
                        leaf error-filter {
                            type yang:counter32;
                            description
                                "Indicates the number of times the logger event will be ignored due to filter
                                 is not operational or is not configured in EHS trigger entries.";
                        }

                        ///nokia-state/state/log/event-trigger/diameter/summary-entry-statistics/error-handler
                        leaf error-handler {
                            type yang:counter32;
                            description
                                "Indicates the number of times the logger event will be ignored due to handler
                                 is not operational or is not configured in EHS trigger entries.";
                        }

                        ///nokia-state/state/log/event-trigger/diameter/summary-entry-statistics/trigger-count
                        leaf trigger-count {
                            type yang:counter32;
                            description "Indicates the number of times script execution is triggered after filter match.";
                        }

                        ///nokia-state/state/log/event-trigger/diameter/summary-entry-statistics/debounce-count
                        leaf debounce-count {
                            type yang:counter32;
                            description "Indicates the number of times script is not executed due to debounce rule.";
                        }

                    } // container summary-entry-statistics

                    ///nokia-state/state/log/event-trigger/diameter/entry
                    list entry {
                        key "id";
                        description "Enter the entry list instance";

                        ///nokia-state/state/log/event-trigger/diameter/entry/id
                        leaf id {
                            type uint32 {
                                range "1..1500";
                            }
                            description "ID of the EHS event trigger entry";
                        }

                        ///nokia-state/state/log/event-trigger/diameter/entry/oper-state
                        leaf oper-state {
                            type types-sros:oper-state;
                            description "Indicates the operational state of the EHS Event Trigger Entry.";
                        }

                        ///nokia-state/state/log/event-trigger/diameter/entry/statistics
                        container statistics {
                            description "Enter the statistics context";

                            ///nokia-state/state/log/event-trigger/diameter/entry/statistics/filter-match
                            leaf filter-match {
                                type yang:counter32;
                                description
                                    "Indicates the number of times a filter, for the specified trigger entry,
                                     matches an logger event.";
                            }

                            ///nokia-state/state/log/event-trigger/diameter/entry/statistics/filter-fail
                            leaf filter-fail {
                                type yang:counter32;
                                description
                                    "Indicates the number of times a filter, for the specified trigger entry,
                                     does not match an logger event.";
                            }

                            ///nokia-state/state/log/event-trigger/diameter/entry/statistics/error-admin-state
                            leaf error-admin-state {
                                type yang:counter32;
                                description
                                    "Indicates the number of times the logger event will be ignored due to
                                     admin state of EHS trigger entry is out-of-service.";
                            }

                            ///nokia-state/state/log/event-trigger/diameter/entry/statistics/error-filter
                            leaf error-filter {
                                type yang:counter32;
                                description
                                    "Indicates the number of times the logger event will be ignored due to filter
                                     is not operational or is not configured in EHS trigger entry.";
                            }

                            ///nokia-state/state/log/event-trigger/diameter/entry/statistics/error-handler
                            leaf error-handler {
                                type yang:counter32;
                                description
                                    "Indicates the number of times the logger event will be ignored due to handler
                                     is not operational or is not configured in EHS trigger entry.";
                            }

                            ///nokia-state/state/log/event-trigger/diameter/entry/statistics/trigger-count
                            leaf trigger-count {
                                type yang:counter32;
                                description
                                    "Indicates the number of times script execution is triggered after filter match
                                     for the specified trigger entry.";
                            }

                            ///nokia-state/state/log/event-trigger/diameter/entry/statistics/debounce-count
                            leaf debounce-count {
                                type yang:counter32;
                                description
                                    "Indicates the number of times script is not executed due to debounce rule
                                     for the specified trigger entry.";
                            }

                        } // container statistics

                    } // list entry

                } // list diameter

                ///nokia-state/state/log/event-trigger/dot1x
                list dot1x {
                    key "event";
                    description "Enter the dot1x list instance";

                    ///nokia-state/state/log/event-trigger/dot1x/event
                    leaf event {
                        type types-log:dot1x-events;
                        description "Events for dynsvc module.";
                    }

                    ///nokia-state/state/log/event-trigger/dot1x/oper-state
                    leaf oper-state {
                        type types-sros:oper-state;
                        description "Indicates the operational state of the EHS Event Trigger.";
                    }

                    ///nokia-state/state/log/event-trigger/dot1x/statistics
                    container statistics {
                        description "Enter the statistics context";

                        ///nokia-state/state/log/event-trigger/dot1x/statistics/success
                        leaf success {
                            type yang:counter32;
                            description
                                "Indicates the number of not ignored logger event occurrences
                                 associated with EHS trigger.";
                        }

                        ///nokia-state/state/log/event-trigger/dot1x/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/dot1x/statistics/error-admin-state
                        leaf error-admin-state {
                            type yang:counter32;
                            description
                                "Indicates the number of ignored logger event occurrences associated
                                 with EHS trigger.

                                 Event is ignored due to trigger may be out-of-service.";
                        }

                        ///nokia-state/state/log/event-trigger/dot1x/statistics/total
                        leaf total {
                            type yang:counter32;
                            description "Sum of success + error-no-entry + error-admin-state.";
                        }

                    } // container statistics

                    ///nokia-state/state/log/event-trigger/dot1x/summary-entry-statistics
                    container summary-entry-statistics {
                        description "Enter the summary-entry-statistics context";

                        ///nokia-state/state/log/event-trigger/dot1x/summary-entry-statistics/filter-match
                        leaf filter-match {
                            type yang:counter32;
                            description "Indicates the number of times a filter matches an logger event.";
                        }

                        ///nokia-state/state/log/event-trigger/dot1x/summary-entry-statistics/filter-fail
                        leaf filter-fail {
                            type yang:counter32;
                            description "Indicates the number of times a filter does not match an logger event.";
                        }

                        ///nokia-state/state/log/event-trigger/dot1x/summary-entry-statistics/error-admin-state
                        leaf error-admin-state {
                            type yang:counter32;
                            description
                                "Indicates the number of times the logger event will be ignored due to
                                 admin state of EHS trigger entries is out-of-service.";
                        }

                        ///nokia-state/state/log/event-trigger/dot1x/summary-entry-statistics/error-filter
                        leaf error-filter {
                            type yang:counter32;
                            description
                                "Indicates the number of times the logger event will be ignored due to filter
                                 is not operational or is not configured in EHS trigger entries.";
                        }

                        ///nokia-state/state/log/event-trigger/dot1x/summary-entry-statistics/error-handler
                        leaf error-handler {
                            type yang:counter32;
                            description
                                "Indicates the number of times the logger event will be ignored due to handler
                                 is not operational or is not configured in EHS trigger entries.";
                        }

                        ///nokia-state/state/log/event-trigger/dot1x/summary-entry-statistics/trigger-count
                        leaf trigger-count {
                            type yang:counter32;
                            description "Indicates the number of times script execution is triggered after filter match.";
                        }

                        ///nokia-state/state/log/event-trigger/dot1x/summary-entry-statistics/debounce-count
                        leaf debounce-count {
                            type yang:counter32;
                            description "Indicates the number of times script is not executed due to debounce rule.";
                        }

                    } // container summary-entry-statistics

                    ///nokia-state/state/log/event-trigger/dot1x/entry
                    list entry {
                        key "id";
                        description "Enter the entry list instance";

                        ///nokia-state/state/log/event-trigger/dot1x/entry/id
                        leaf id {
                            type uint32 {
                                range "1..1500";
                            }
                            description "ID of the EHS event trigger entry";
                        }

                        ///nokia-state/state/log/event-trigger/dot1x/entry/oper-state
                        leaf oper-state {
                            type types-sros:oper-state;
                            description "Indicates the operational state of the EHS Event Trigger Entry.";
                        }

                        ///nokia-state/state/log/event-trigger/dot1x/entry/statistics
                        container statistics {
                            description "Enter the statistics context";

                            ///nokia-state/state/log/event-trigger/dot1x/entry/statistics/filter-match
                            leaf filter-match {
                                type yang:counter32;
                                description
                                    "Indicates the number of times a filter, for the specified trigger entry,
                                     matches an logger event.";
                            }

                            ///nokia-state/state/log/event-trigger/dot1x/entry/statistics/filter-fail
                            leaf filter-fail {
                                type yang:counter32;
                                description
                                    "Indicates the number of times a filter, for the specified trigger entry,
                                     does not match an logger event.";
                            }

                            ///nokia-state/state/log/event-trigger/dot1x/entry/statistics/error-admin-state
                            leaf error-admin-state {
                                type yang:counter32;
                                description
                                    "Indicates the number of times the logger event will be ignored due to
                                     admin state of EHS trigger entry is out-of-service.";
                            }

                            ///nokia-state/state/log/event-trigger/dot1x/entry/statistics/error-filter
                            leaf error-filter {
                                type yang:counter32;
                                description
                                    "Indicates the number of times the logger event will be ignored due to filter
                                     is not operational or is not configured in EHS trigger entry.";
                            }

                            ///nokia-state/state/log/event-trigger/dot1x/entry/statistics/error-handler
                            leaf error-handler {
                                type yang:counter32;
                                description
                                    "Indicates the number of times the logger event will be ignored due to handler
                                     is not operational or is not configured in EHS trigger entry.";
                            }

                            ///nokia-state/state/log/event-trigger/dot1x/entry/statistics/trigger-count
                            leaf trigger-count {
                                type yang:counter32;
                                description
                                    "Indicates the number of times script execution is triggered after filter match
                                     for the specified trigger entry.";
                            }

                            ///nokia-state/state/log/event-trigger/dot1x/entry/statistics/debounce-count
                            leaf debounce-count {
                                type yang:counter32;
                                description
                                    "Indicates the number of times script is not executed due to debounce rule
                                     for the specified trigger entry.";
                            }

                        } // container statistics

                    } // list entry

                } // list dot1x

                ///nokia-state/state/log/event-trigger/dynsvc
                list dynsvc {
                    key "event";
                    description "Enter the dynsvc list instance";

                    ///nokia-state/state/log/event-trigger/dynsvc/event
                    leaf event {
                        type types-log:dynsvc-events;
                        description "Log event as a trigger for one or more EHS handlers";
                    }

                    ///nokia-state/state/log/event-trigger/dynsvc/oper-state
                    leaf oper-state {
                        type types-sros:oper-state;
                        description "Indicates the operational state of the EHS Event Trigger.";
                    }

                    ///nokia-state/state/log/event-trigger/dynsvc/statistics
                    container statistics {
                        description "Enter the statistics context";

                        ///nokia-state/state/log/event-trigger/dynsvc/statistics/success
                        leaf success {
                            type yang:counter32;
                            description
                                "Indicates the number of not ignored logger event occurrences
                                 associated with EHS trigger.";
                        }

                        ///nokia-state/state/log/event-trigger/dynsvc/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/dynsvc/statistics/error-admin-state
                        leaf error-admin-state {
                            type yang:counter32;
                            description
                                "Indicates the number of ignored logger event occurrences associated
                                 with EHS trigger.

                                 Event is ignored due to trigger may be out-of-service.";
                        }

                        ///nokia-state/state/log/event-trigger/dynsvc/statistics/total
                        leaf total {
                            type yang:counter32;
                            description "Sum of success + error-no-entry + error-admin-state.";
                        }

                    } // container statistics

                    ///nokia-state/state/log/event-trigger/dynsvc/summary-entry-statistics
                    container summary-entry-statistics {
                        description "Enter the summary-entry-statistics context";

                        ///nokia-state/state/log/event-trigger/dynsvc/summary-entry-statistics/filter-match
                        leaf filter-match {
                            type yang:counter32;
                            description "Indicates the number of times a filter matches an logger event.";
                        }

                        ///nokia-state/state/log/event-trigger/dynsvc/summary-entry-statistics/filter-fail
                        leaf filter-fail {
                            type yang:counter32;
                            description "Indicates the number of times a filter does not match an logger event.";
                        }

                        ///nokia-state/state/log/event-trigger/dynsvc/summary-entry-statistics/error-admin-state
                        leaf error-admin-state {
                            type yang:counter32;
                            description
                                "Indicates the number of times the logger event will be ignored due to
                                 admin state of EHS trigger entries is out-of-service.";
                        }

                        ///nokia-state/state/log/event-trigger/dynsvc/summary-entry-statistics/error-filter
                        leaf error-filter {
                            type yang:counter32;
                            description
                                "Indicates the number of times the logger event will be ignored due to filter
                                 is not operational or is not configured in EHS trigger entries.";
                        }

                        ///nokia-state/state/log/event-trigger/dynsvc/summary-entry-statistics/error-handler
                        leaf error-handler {
                            type yang:counter32;
                            description
                                "Indicates the number of times the logger event will be ignored due to handler
                                 is not operational or is not configured in EHS trigger entries.";
                        }

                        ///nokia-state/state/log/event-trigger/dynsvc/summary-entry-statistics/trigger-count
                        leaf trigger-count {
                            type yang:counter32;
                            description "Indicates the number of times script execution is triggered after filter match.";
                        }

                        ///nokia-state/state/log/event-trigger/dynsvc/summary-entry-statistics/debounce-count
                        leaf debounce-count {
                            type yang:counter32;
                            description "Indicates the number of times script is not executed due to debounce rule.";
                        }

                    } // container summary-entry-statistics

                    ///nokia-state/state/log/event-trigger/dynsvc/entry
                    list entry {
                        key "id";
                        description "Enter the entry list instance";

                        ///nokia-state/state/log/event-trigger/dynsvc/entry/id
                        leaf id {
                            type uint32 {
                                range "1..1500";
                            }
                            description "ID of the EHS event trigger entry";
                        }

                        ///nokia-state/state/log/event-trigger/dynsvc/entry/oper-state
                        leaf oper-state {
                            type types-sros:oper-state;
                            description "Indicates the operational state of the EHS Event Trigger Entry.";
                        }

                        ///nokia-state/state/log/event-trigger/dynsvc/entry/statistics
                        container statistics {
                            description "Enter the statistics context";

                            ///nokia-state/state/log/event-trigger/dynsvc/entry/statistics/filter-match
                            leaf filter-match {
                                type yang:counter32;
                                description
                                    "Indicates the number of times a filter, for the specified trigger entry,
                                     matches an logger event.";
                            }

                            ///nokia-state/state/log/event-trigger/dynsvc/entry/statistics/filter-fail
                            leaf filter-fail {
                                type yang:counter32;
                                description
                                    "Indicates the number of times a filter, for the specified trigger entry,
                                     does not match an logger event.";
                            }

                            ///nokia-state/state/log/event-trigger/dynsvc/entry/statistics/error-admin-state
                            leaf error-admin-state {
                                type yang:counter32;
                                description
                                    "Indicates the number of times the logger event will be ignored due to
                                     admin state of EHS trigger entry is out-of-service.";
                            }

                            ///nokia-state/state/log/event-trigger/dynsvc/entry/statistics/error-filter
                            leaf error-filter {
                                type yang:counter32;
                                description
                                    "Indicates the number of times the logger event will be ignored due to filter
                                     is not operational or is not configured in EHS trigger entry.";
                            }

                            ///nokia-state/state/log/event-trigger/dynsvc/entry/statistics/error-handler
                            leaf error-handler {
                                type yang:counter32;
                                description
                                    "Indicates the number of times the logger event will be ignored due to handler
                                     is not operational or is not configured in EHS trigger entry.";
                            }

                            ///nokia-state/state/log/event-trigger/dynsvc/entry/statistics/trigger-count
                            leaf trigger-count {
                                type yang:counter32;
                                description
                                    "Indicates the number of times script execution is triggered after filter match
                                     for the specified trigger entry.";
                            }

                            ///nokia-state/state/log/event-trigger/dynsvc/entry/statistics/debounce-count
                            leaf debounce-count {
                                type yang:counter32;
                                description
                                    "Indicates the number of times script is not executed due to debounce rule
                                     for the specified trigger entry.";
                            }

                        } // container statistics

                    } // list entry

                } // list dynsvc

                ///nokia-state/state/log/event-trigger/efm-oam
                list efm-oam {
                    key "event";
                    description "Enter the efm-oam list instance";

                    ///nokia-state/state/log/event-trigger/efm-oam/event
                    leaf event {
                        type types-log:efm-oam-events;
                        description "Log event as a trigger for one or more EHS handlers";
                    }

                    ///nokia-state/state/log/event-trigger/efm-oam/oper-state
                    leaf oper-state {
                        type types-sros:oper-state;
                        description "Indicates the operational state of the EHS Event Trigger.";
                    }

                    ///nokia-state/state/log/event-trigger/efm-oam/statistics
                    container statistics {
                        description "Enter the statistics context";

                        ///nokia-state/state/log/event-trigger/efm-oam/statistics/success
                        leaf success {
                            type yang:counter32;
                            description
                                "Indicates the number of not ignored logger event occurrences
                                 associated with EHS trigger.";
                        }

                        ///nokia-state/state/log/event-trigger/efm-oam/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/efm-oam/statistics/error-admin-state
                        leaf error-admin-state {
                            type yang:counter32;
                            description
                                "Indicates the number of ignored logger event occurrences associated
                                 with EHS trigger.

                                 Event is ignored due to trigger may be out-of-service.";
                        }

                        ///nokia-state/state/log/event-trigger/efm-oam/statistics/total
                        leaf total {
                            type yang:counter32;
                            description "Sum of success + error-no-entry + error-admin-state.";
                        }

                    } // container statistics

                    ///nokia-state/state/log/event-trigger/efm-oam/summary-entry-statistics
                    container summary-entry-statistics {
                        description "Enter the summary-entry-statistics context";

                        ///nokia-state/state/log/event-trigger/efm-oam/summary-entry-statistics/filter-match
                        leaf filter-match {
                            type yang:counter32;
                            description "Indicates the number of times a filter matches an logger event.";
                        }

                        ///nokia-state/state/log/event-trigger/efm-oam/summary-entry-statistics/filter-fail
                        leaf filter-fail {
                            type yang:counter32;
                            description "Indicates the number of times a filter does not match an logger event.";
                        }

                        ///nokia-state/state/log/event-trigger/efm-oam/summary-entry-statistics/error-admin-state
                        leaf error-admin-state {
                            type yang:counter32;
                            description
                                "Indicates the number of times the logger event will be ignored due to
                                 admin state of EHS trigger entries is out-of-service.";
                        }

                        ///nokia-state/state/log/event-trigger/efm-oam/summary-entry-statistics/error-filter
                        leaf error-filter {
                            type yang:counter32;
                            description
                                "Indicates the number of times the logger event will be ignored due to filter
                                 is not operational or is not configured in EHS trigger entries.";
                        }

                        ///nokia-state/state/log/event-trigger/efm-oam/summary-entry-statistics/error-handler
                        leaf error-handler {
                            type yang:counter32;
                            description
                                "Indicates the number of times the logger event will be ignored due to handler
                                 is not operational or is not configured in EHS trigger entries.";
                        }

                        ///nokia-state/state/log/event-trigger/efm-oam/summary-entry-statistics/trigger-count
                        leaf trigger-count {
                            type yang:counter32;
                            description "Indicates the number of times script execution is triggered after filter match.";
                        }

                        ///nokia-state/state/log/event-trigger/efm-oam/summary-entry-statistics/debounce-count
                        leaf debounce-count {
                            type yang:counter32;
                            description "Indicates the number of times script is not executed due to debounce rule.";
                        }

                    } // container summary-entry-statistics

                    ///nokia-state/state/log/event-trigger/efm-oam/entry
                    list entry {
                        key "id";
                        description "Enter the entry list instance";

                        ///nokia-state/state/log/event-trigger/efm-oam/entry/id
                        leaf id {
                            type uint32 {
                                range "1..1500";
                            }
                            description "ID of the EHS event trigger entry";
                        }

                        ///nokia-state/state/log/event-trigger/efm-oam/entry/oper-state
                        leaf oper-state {
                            type types-sros:oper-state;
                            description "Indicates the operational state of the EHS Event Trigger Entry.";
                        }

                        ///nokia-state/state/log/event-trigger/efm-oam/entry/statistics
                        container statistics {
                            description "Enter the statistics context";

                            ///nokia-state/state/log/event-trigger/efm-oam/entry/statistics/filter-match
                            leaf filter-match {
                                type yang:counter32;
                                description
                                    "Indicates the number of times a filter, for the specified trigger entry,
                                     matches an logger event.";
                            }

                            ///nokia-state/state/log/event-trigger/efm-oam/entry/statistics/filter-fail
                            leaf filter-fail {
                                type yang:counter32;
                                description
                                    "Indicates the number of times a filter, for the specified trigger entry,
                                     does not match an logger event.";
                            }

                            ///nokia-state/state/log/event-trigger/efm-oam/entry/statistics/error-admin-state
                            leaf error-admin-state {
                                type yang:counter32;
                                description
                                    "Indicates the number of times the logger event will be ignored due to
                                     admin state of EHS trigger entry is out-of-service.";
                            }

                            ///nokia-state/state/log/event-trigger/efm-oam/entry/statistics/error-filter
                            leaf error-filter {
                                type yang:counter32;
                                description
                                    "Indicates the number of times the logger event will be ignored due to filter
                                     is not operational or is not configured in EHS trigger entry.";
                            }

                            ///nokia-state/state/log/event-trigger/efm-oam/entry/statistics/error-handler
                            leaf error-handler {
                                type yang:counter32;
                                description
                                    "Indicates the number of times the logger event will be ignored due to handler
                                     is not operational or is not configured in EHS trigger entry.";
                            }

                            ///nokia-state/state/log/event-trigger/efm-oam/entry/statistics/trigger-count
                            leaf trigger-count {
                                type yang:counter32;
                                description
                                    "Indicates the number of times script execution is triggered after filter match
                                     for the specified trigger entry.";
                            }

                            ///nokia-state/state/log/event-trigger/efm-oam/entry/statistics/debounce-count
                            leaf debounce-count {
                                type yang:counter32;
                                description
                                    "Indicates the number of times script is not executed due to debounce rule
                                     for the specified trigger entry.";
                            }

                        } // container statistics

                    } // list entry

                } // list efm-oam

                ///nokia-state/state/log/event-trigger/elmi
                list elmi {
                    key "event";
                    description "Enter the elmi list instance";

                    ///nokia-state/state/log/event-trigger/elmi/event
                    leaf event {
                        type types-log:elmi-events;
                        description "Log event as a trigger for one or more EHS handlers";
                    }

                    ///nokia-state/state/log/event-trigger/elmi/oper-state
                    leaf oper-state {
                        type types-sros:oper-state;
                        description "Indicates the operational state of the EHS Event Trigger.";
                    }

                    ///nokia-state/state/log/event-trigger/elmi/statistics
                    container statistics {
                        description "Enter the statistics context";

                        ///nokia-state/state/log/event-trigger/elmi/statistics/success
                        leaf success {
                            type yang:counter32;
                            description
                                "Indicates the number of not ignored logger event occurrences
                                 associated with EHS trigger.";
                        }

                        ///nokia-state/state/log/event-trigger/elmi/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/elmi/statistics/error-admin-state
                        leaf error-admin-state {
                            type yang:counter32;
                            description
                                "Indicates the number of ignored logger event occurrences associated
                                 with EHS trigger.

                                 Event is ignored due to trigger may be out-of-service.";
                        }

                        ///nokia-state/state/log/event-trigger/elmi/statistics/total
                        leaf total {
                            type yang:counter32;
                            description "Sum of success + error-no-entry + error-admin-state.";
                        }

                    } // container statistics

                    ///nokia-state/state/log/event-trigger/elmi/summary-entry-statistics
                    container summary-entry-statistics {
                        description "Enter the summary-entry-statistics context";

                        ///nokia-state/state/log/event-trigger/elmi/summary-entry-statistics/filter-match
                        leaf filter-match {
                            type yang:counter32;
                            description "Indicates the number of times a filter matches an logger event.";
                        }

                        ///nokia-state/state/log/event-trigger/elmi/summary-entry-statistics/filter-fail
                        leaf filter-fail {
                            type yang:counter32;
                            description "Indicates the number of times a filter does not match an logger event.";
                        }

                        ///nokia-state/state/log/event-trigger/elmi/summary-entry-statistics/error-admin-state
                        leaf error-admin-state {
                            type yang:counter32;
                            description
                                "Indicates the number of times the logger event will be ignored due to
                                 admin state of EHS trigger entries is out-of-service.";
                        }

                        ///nokia-state/state/log/event-trigger/elmi/summary-entry-statistics/error-filter
                        leaf error-filter {
                            type yang:counter32;
                            description
                                "Indicates the number of times the logger event will be ignored due to filter
                                 is not operational or is not configured in EHS trigger entries.";
                        }

                        ///nokia-state/state/log/event-trigger/elmi/summary-entry-statistics/error-handler
                        leaf error-handler {
                            type yang:counter32;
                            description
                                "Indicates the number of times the logger event will be ignored due to handler
                                 is not operational or is not configured in EHS trigger entries.";
                        }

                        ///nokia-state/state/log/event-trigger/elmi/summary-entry-statistics/trigger-count
                        leaf trigger-count {
                            type yang:counter32;
                            description "Indicates the number of times script execution is triggered after filter match.";
                        }

                        ///nokia-state/state/log/event-trigger/elmi/summary-entry-statistics/debounce-count
                        leaf debounce-count {
                            type yang:counter32;
                            description "Indicates the number of times script is not executed due to debounce rule.";
                        }

                    } // container summary-entry-statistics

                    ///nokia-state/state/log/event-trigger/elmi/entry
                    list entry {
                        key "id";
                        description "Enter the entry list instance";

                        ///nokia-state/state/log/event-trigger/elmi/entry/id
                        leaf id {
                            type uint32 {
                                range "1..1500";
                            }
                            description "ID of the EHS event trigger entry";
                        }

                        ///nokia-state/state/log/event-trigger/elmi/entry/oper-state
                        leaf oper-state {
                            type types-sros:oper-state;
                            description "Indicates the operational state of the EHS Event Trigger Entry.";
                        }

                        ///nokia-state/state/log/event-trigger/elmi/entry/statistics
                        container statistics {
                            description "Enter the statistics context";

                            ///nokia-state/state/log/event-trigger/elmi/entry/statistics/filter-match
                            leaf filter-match {
                                type yang:counter32;
                                description
                                    "Indicates the number of times a filter, for the specified trigger entry,
                                     matches an logger event.";
                            }

                            ///nokia-state/state/log/event-trigger/elmi/entry/statistics/filter-fail
                            leaf filter-fail {
                                type yang:counter32;
                                description
                                    "Indicates the number of times a filter, for the specified trigger entry,
                                     does not match an logger event.";
                            }

                            ///nokia-state/state/log/event-trigger/elmi/entry/statistics/error-admin-state
                            leaf error-admin-state {
                                type yang:counter32;
                                description
                                    "Indicates the number of times the logger event will be ignored due to
                                     admin state of EHS trigger entry is out-of-service.";
                            }

                            ///nokia-state/state/log/event-trigger/elmi/entry/statistics/error-filter
                            leaf error-filter {
                                type yang:counter32;
                                description
                                    "Indicates the number of times the logger event will be ignored due to filter
                                     is not operational or is not configured in EHS trigger entry.";
                            }

                            ///nokia-state/state/log/event-trigger/elmi/entry/statistics/error-handler
                            leaf error-handler {
                                type yang:counter32;
                                description
                                    "Indicates the number of times the logger event will be ignored due to handler
                                     is not operational or is not configured in EHS trigger entry.";
                            }

                            ///nokia-state/state/log/event-trigger/elmi/entry/statistics/trigger-count
                            leaf trigger-count {
                                type yang:counter32;
                                description
                                    "Indicates the number of times script execution is triggered after filter match
                                     for the specified trigger entry.";
                            }

                            ///nokia-state/state/log/event-trigger/elmi/entry/statistics/debounce-count
                            leaf debounce-count {
                                type yang:counter32;
                                description
                                    "Indicates the number of times script is not executed due to debounce rule
                                     for the specified trigger entry.";
                            }

                        } // container statistics

                    } // list entry

                } // list elmi

                ///nokia-state/state/log/event-trigger/ering
                list ering {
                    key "event";
                    description "Enter the ering list instance";

                    ///nokia-state/state/log/event-trigger/ering/event
                    leaf event {
                        type types-log:ethring-events;
                        description "Log event as a trigger for one or more EHS handlers";
                    }

                    ///nokia-state/state/log/event-trigger/ering/oper-state
                    leaf oper-state {
                        type types-sros:oper-state;
                        description "Indicates the operational state of the EHS Event Trigger.";
                    }

                    ///nokia-state/state/log/event-trigger/ering/statistics
                    container statistics {
                        description "Enter the statistics context";

                        ///nokia-state/state/log/event-trigger/ering/statistics/success
                        leaf success {
                            type yang:counter32;
                            description
                                "Indicates the number of not ignored logger event occurrences
                                 associated with EHS trigger.";
                        }

                        ///nokia-state/state/log/event-trigger/ering/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ering/statistics/error-admin-state
                        leaf error-admin-state {
                            type yang:counter32;
                            description
                                "Indicates the number of ignored logger event occurrences associated
                                 with EHS trigger.

                                 Event is ignored due to trigger may be out-of-service.";
                        }

                        ///nokia-state/state/log/event-trigger/ering/statistics/total
                        leaf total {
                            type yang:counter32;
                            description "Sum of success + error-no-entry + error-admin-state.";
                        }

                    } // container statistics

                    ///nokia-state/state/log/event-trigger/ering/summary-entry-statistics
                    container summary-entry-statistics {
                        description "Enter the summary-entry-statistics context";

                        ///nokia-state/state/log/event-trigger/ering/summary-entry-statistics/filter-match
                        leaf filter-match {
                            type yang:counter32;
                            description "Indicates the number of times a filter matches an logger event.";
                        }

                        ///nokia-state/state/log/event-trigger/ering/summary-entry-statistics/filter-fail
                        leaf filter-fail {
                            type yang:counter32;
                            description "Indicates the number of times a filter does not match an logger event.";
                        }

                        ///nokia-state/state/log/event-trigger/ering/summary-entry-statistics/error-admin-state
                        leaf error-admin-state {
                            type yang:counter32;
                            description
                                "Indicates the number of times the logger event will be ignored due to
                                 admin state of EHS trigger entries is out-of-service.";
                        }

                        ///nokia-state/state/log/event-trigger/ering/summary-entry-statistics/error-filter
                        leaf error-filter {
                            type yang:counter32;
                            description
                                "Indicates the number of times the logger event will be ignored due to filter
                                 is not operational or is not configured in EHS trigger entries.";
                        }

                        ///nokia-state/state/log/event-trigger/ering/summary-entry-statistics/error-handler
                        leaf error-handler {
                            type yang:counter32;
                            description
                                "Indicates the number of times the logger event will be ignored due to handler
                                 is not operational or is not configured in EHS trigger entries.";
                        }

                        ///nokia-state/state/log/event-trigger/ering/summary-entry-statistics/trigger-count
                        leaf trigger-count {
                            type yang:counter32;
                            description "Indicates the number of times script execution is triggered after filter match.";
                        }

                        ///nokia-state/state/log/event-trigger/ering/summary-entry-statistics/debounce-count
                        leaf debounce-count {
                            type yang:counter32;
                            description "Indicates the number of times script is not executed due to debounce rule.";
                        }

                    } // container summary-entry-statistics

                    ///nokia-state/state/log/event-trigger/ering/entry
                    list entry {
                        key "id";
                        description "Enter the entry list instance";

                        ///nokia-state/state/log/event-trigger/ering/entry/id
                        leaf id {
                            type uint32 {
                                range "1..1500";
                            }
                            description "ID of the EHS event trigger entry";
                        }

                        ///nokia-state/state/log/event-trigger/ering/entry/oper-state
                        leaf oper-state {
                            type types-sros:oper-state;
                            description "Indicates the operational state of the EHS Event Trigger Entry.";
                        }

                        ///nokia-state/state/log/event-trigger/ering/entry/statistics
                        container statistics {
                            description "Enter the statistics context";

                            ///nokia-state/state/log/event-trigger/ering/entry/statistics/filter-match
                            leaf filter-match {
                                type yang:counter32;
                                description
                                    "Indicates the number of times a filter, for the specified trigger entry,
                                     matches an logger event.";
                            }

                            ///nokia-state/state/log/event-trigger/ering/entry/statistics/filter-fail
                            leaf filter-fail {
                                type yang:counter32;
                                description
                                    "Indicates the number of times a filter, for the specified trigger entry,
                                     does not match an logger event.";
                            }

                            ///nokia-state/state/log/event-trigger/ering/entry/statistics/error-admin-state
                            leaf error-admin-state {
                                type yang:counter32;
                                description
                                    "Indicates the number of times the logger event will be ignored due to
                                     admin state of EHS trigger entry is out-of-service.";
                            }

                            ///nokia-state/state/log/event-trigger/ering/entry/statistics/error-filter
                            leaf error-filter {
                                type yang:counter32;
                                description
                                    "Indicates the number of times the logger event will be ignored due to filter
                                     is not operational or is not configured in EHS trigger entry.";
                            }

                            ///nokia-state/state/log/event-trigger/ering/entry/statistics/error-handler
                            leaf error-handler {
                                type yang:counter32;
                                description
                                    "Indicates the number of times the logger event will be ignored due to handler
                                     is not operational or is not configured in EHS trigger entry.";
                            }

                            ///nokia-state/state/log/event-trigger/ering/entry/statistics/trigger-count
                            leaf trigger-count {
                                type yang:counter32;
                                description
                                    "Indicates the number of times script execution is triggered after filter match
                                     for the specified trigger entry.";
                            }

                            ///nokia-state/state/log/event-trigger/ering/entry/statistics/debounce-count
                            leaf debounce-count {
                                type yang:counter32;
                                description
                                    "Indicates the number of times script is not executed due to debounce rule
                                     for the specified trigger entry.";
                            }

                        } // container statistics

                    } // list entry

                } // list ering

                ///nokia-state/state/log/event-trigger/eth-cfm
                list eth-cfm {
                    key "event";
                    description "Enter the eth-cfm list instance";

                    ///nokia-state/state/log/event-trigger/eth-cfm/event
                    leaf event {
                        type types-log:ethcfm-events;
                        description "Log event as a trigger for one or more EHS handlers";
                    }

                    ///nokia-state/state/log/event-trigger/eth-cfm/oper-state
                    leaf oper-state {
                        type types-sros:oper-state;
                        description "Indicates the operational state of the EHS Event Trigger.";
                    }

                    ///nokia-state/state/log/event-trigger/eth-cfm/statistics
                    container statistics {
                        description "Enter the statistics context";

                        ///nokia-state/state/log/event-trigger/eth-cfm/statistics/success
                        leaf success {
                            type yang:counter32;
                            description
                                "Indicates the number of not ignored logger event occurrences
                                 associated with EHS trigger.";
                        }

                        ///nokia-state/state/log/event-trigger/eth-cfm/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/eth-cfm/statistics/error-admin-state
                        leaf error-admin-state {
                            type yang:counter32;
                            description
                                "Indicates the number of ignored logger event occurrences associated
                                 with EHS trigger.

                                 Event is ignored due to trigger may be out-of-service.";
                        }

                        ///nokia-state/state/log/event-trigger/eth-cfm/statistics/total
                        leaf total {
                            type yang:counter32;
                            description "Sum of success + error-no-entry + error-admin-state.";
                        }

                    } // container statistics

                    ///nokia-state/state/log/event-trigger/eth-cfm/summary-entry-statistics
                    container summary-entry-statistics {
                        description "Enter the summary-entry-statistics context";

                        ///nokia-state/state/log/event-trigger/eth-cfm/summary-entry-statistics/filter-match
                        leaf filter-match {
                            type yang:counter32;
                            description "Indicates the number of times a filter matches an logger event.";
                        }

                        ///nokia-state/state/log/event-trigger/eth-cfm/summary-entry-statistics/filter-fail
                        leaf filter-fail {
                            type yang:counter32;
                            description "Indicates the number of times a filter does not match an logger event.";
                        }

                        ///nokia-state/state/log/event-trigger/eth-cfm/summary-entry-statistics/error-admin-state
                        leaf error-admin-state {
                            type yang:counter32;
                            description
                                "Indicates the number of times the logger event will be ignored due to
                                 admin state of EHS trigger entries is out-of-service.";
                        }

                        ///nokia-state/state/log/event-trigger/eth-cfm/summary-entry-statistics/error-filter
                        leaf error-filter {
                            type yang:counter32;
                            description
                                "Indicates the number of times the logger event will be ignored due to filter
                                 is not operational or is not configured in EHS trigger entries.";
                        }

                        ///nokia-state/state/log/event-trigger/eth-cfm/summary-entry-statistics/error-handler
                        leaf error-handler {
                            type yang:counter32;
                            description
                                "Indicates the number of times the logger event will be ignored due to handler
                                 is not operational or is not configured in EHS trigger entries.";
                        }

                        ///nokia-state/state/log/event-trigger/eth-cfm/summary-entry-statistics/trigger-count
                        leaf trigger-count {
                            type yang:counter32;
                            description "Indicates the number of times script execution is triggered after filter match.";
                        }

                        ///nokia-state/state/log/event-trigger/eth-cfm/summary-entry-statistics/debounce-count
                        leaf debounce-count {
                            type yang:counter32;
                            description "Indicates the number of times script is not executed due to debounce rule.";
                        }

                    } // container summary-entry-statistics

                    ///nokia-state/state/log/event-trigger/eth-cfm/entry
                    list entry {
                        key "id";
                        description "Enter the entry list instance";

                        ///nokia-state/state/log/event-trigger/eth-cfm/entry/id
                        leaf id {
                            type uint32 {
                                range "1..1500";
                            }
                            description "ID of the EHS event trigger entry";
                        }

                        ///nokia-state/state/log/event-trigger/eth-cfm/entry/oper-state
                        leaf oper-state {
                            type types-sros:oper-state;
                            description "Indicates the operational state of the EHS Event Trigger Entry.";
                        }

                        ///nokia-state/state/log/event-trigger/eth-cfm/entry/statistics
                        container statistics {
                            description "Enter the statistics context";

                            ///nokia-state/state/log/event-trigger/eth-cfm/entry/statistics/filter-match
                            leaf filter-match {
                                type yang:counter32;
                                description
                                    "Indicates the number of times a filter, for the specified trigger entry,
                                     matches an logger event.";
                            }

                            ///nokia-state/state/log/event-trigger/eth-cfm/entry/statistics/filter-fail
                            leaf filter-fail {
                                type yang:counter32;
                                description
                                    "Indicates the number of times a filter, for the specified trigger entry,
                                     does not match an logger event.";
                            }

                            ///nokia-state/state/log/event-trigger/eth-cfm/entry/statistics/error-admin-state
                            leaf error-admin-state {
                                type yang:counter32;
                                description
                                    "Indicates the number of times the logger event will be ignored due to
                                     admin state of EHS trigger entry is out-of-service.";
                            }

                            ///nokia-state/state/log/event-trigger/eth-cfm/entry/statistics/error-filter
                            leaf error-filter {
                                type yang:counter32;
                                description
                                    "Indicates the number of times the logger event will be ignored due to filter
                                     is not operational or is not configured in EHS trigger entry.";
                            }

                            ///nokia-state/state/log/event-trigger/eth-cfm/entry/statistics/error-handler
                            leaf error-handler {
                                type yang:counter32;
                                description
                                    "Indicates the number of times the logger event will be ignored due to handler
                                     is not operational or is not configured in EHS trigger entry.";
                            }

                            ///nokia-state/state/log/event-trigger/eth-cfm/entry/statistics/trigger-count
                            leaf trigger-count {
                                type yang:counter32;
                                description
                                    "Indicates the number of times script execution is triggered after filter match
                                     for the specified trigger entry.";
                            }

                            ///nokia-state/state/log/event-trigger/eth-cfm/entry/statistics/debounce-count
                            leaf debounce-count {
                                type yang:counter32;
                                description
                                    "Indicates the number of times script is not executed due to debounce rule
                                     for the specified trigger entry.";
                            }

                        } // container statistics

                    } // list entry

                } // list eth-cfm

                ///nokia-state/state/log/event-trigger/etun
                list etun {
                    key "event";
                    description "Enter the etun list instance";

                    ///nokia-state/state/log/event-trigger/etun/event
                    leaf event {
                        type types-log:etun-events;
                        description "Log event as a trigger for one or more EHS handlers";
                    }

                    ///nokia-state/state/log/event-trigger/etun/oper-state
                    leaf oper-state {
                        type types-sros:oper-state;
                        description "Indicates the operational state of the EHS Event Trigger.";
                    }

                    ///nokia-state/state/log/event-trigger/etun/statistics
                    container statistics {
                        description "Enter the statistics context";

                        ///nokia-state/state/log/event-trigger/etun/statistics/success
                        leaf success {
                            type yang:counter32;
                            description
                                "Indicates the number of not ignored logger event occurrences
                                 associated with EHS trigger.";
                        }

                        ///nokia-state/state/log/event-trigger/etun/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/etun/statistics/error-admin-state
                        leaf error-admin-state {
                            type yang:counter32;
                            description
                                "Indicates the number of ignored logger event occurrences associated
                                 with EHS trigger.

                                 Event is ignored due to trigger may be out-of-service.";
                        }

                        ///nokia-state/state/log/event-trigger/etun/statistics/total
                        leaf total {
                            type yang:counter32;
                            description "Sum of success + error-no-entry + error-admin-state.";
                        }

                    } // container statistics

                    ///nokia-state/state/log/event-trigger/etun/summary-entry-statistics
                    container summary-entry-statistics {
                        description "Enter the summary-entry-statistics context";

                        ///nokia-state/state/log/event-trigger/etun/summary-entry-statistics/filter-match
                        leaf filter-match {
                            type yang:counter32;
                            description "Indicates the number of times a filter matches an logger event.";
                        }

                        ///nokia-state/state/log/event-trigger/etun/summary-entry-statistics/filter-fail
                        leaf filter-fail {
                            type yang:counter32;
                            description "Indicates the number of times a filter does not match an logger event.";
                        }

                        ///nokia-state/state/log/event-trigger/etun/summary-entry-statistics/error-admin-state
                        leaf error-admin-state {
                            type yang:counter32;
                            description
                                "Indicates the number of times the logger event will be ignored due to
                                 admin state of EHS trigger entries is out-of-service.";
                        }

                        ///nokia-state/state/log/event-trigger/etun/summary-entry-statistics/error-filter
                        leaf error-filter {
                            type yang:counter32;
                            description
                                "Indicates the number of times the logger event will be ignored due to filter
                                 is not operational or is not configured in EHS trigger entries.";
                        }

                        ///nokia-state/state/log/event-trigger/etun/summary-entry-statistics/error-handler
                        leaf error-handler {
                            type yang:counter32;
                            description
                                "Indicates the number of times the logger event will be ignored due to handler
                                 is not operational or is not configured in EHS trigger entries.";
                        }

                        ///nokia-state/state/log/event-trigger/etun/summary-entry-statistics/trigger-count
                        leaf trigger-count {
                            type yang:counter32;
                            description "Indicates the number of times script execution is triggered after filter match.";
                        }

                        ///nokia-state/state/log/event-trigger/etun/summary-entry-statistics/debounce-count
                        leaf debounce-count {
                            type yang:counter32;
                            description "Indicates the number of times script is not executed due to debounce rule.";
                        }

                    } // container summary-entry-statistics

                    ///nokia-state/state/log/event-trigger/etun/entry
                    list entry {
                        key "id";
                        description "Enter the entry list instance";

                        ///nokia-state/state/log/event-trigger/etun/entry/id
                        leaf id {
                            type uint32 {
                                range "1..1500";
                            }
                            description "ID of the EHS event trigger entry";
                        }

                        ///nokia-state/state/log/event-trigger/etun/entry/oper-state
                        leaf oper-state {
                            type types-sros:oper-state;
                            description "Indicates the operational state of the EHS Event Trigger Entry.";
                        }

                        ///nokia-state/state/log/event-trigger/etun/entry/statistics
                        container statistics {
                            description "Enter the statistics context";

                            ///nokia-state/state/log/event-trigger/etun/entry/statistics/filter-match
                            leaf filter-match {
                                type yang:counter32;
                                description
                                    "Indicates the number of times a filter, for the specified trigger entry,
                                     matches an logger event.";
                            }

                            ///nokia-state/state/log/event-trigger/etun/entry/statistics/filter-fail
                            leaf filter-fail {
                                type yang:counter32;
                                description
                                    "Indicates the number of times a filter, for the specified trigger entry,
                                     does not match an logger event.";
                            }

                            ///nokia-state/state/log/event-trigger/etun/entry/statistics/error-admin-state
                            leaf error-admin-state {
                                type yang:counter32;
                                description
                                    "Indicates the number of times the logger event will be ignored due to
                                     admin state of EHS trigger entry is out-of-service.";
                            }

                            ///nokia-state/state/log/event-trigger/etun/entry/statistics/error-filter
                            leaf error-filter {
                                type yang:counter32;
                                description
                                    "Indicates the number of times the logger event will be ignored due to filter
                                     is not operational or is not configured in EHS trigger entry.";
                            }

                            ///nokia-state/state/log/event-trigger/etun/entry/statistics/error-handler
                            leaf error-handler {
                                type yang:counter32;
                                description
                                    "Indicates the number of times the logger event will be ignored due to handler
                                     is not operational or is not configured in EHS trigger entry.";
                            }

                            ///nokia-state/state/log/event-trigger/etun/entry/statistics/trigger-count
                            leaf trigger-count {
                                type yang:counter32;
                                description
                                    "Indicates the number of times script execution is triggered after filter match
                                     for the specified trigger entry.";
                            }

                            ///nokia-state/state/log/event-trigger/etun/entry/statistics/debounce-count
                            leaf debounce-count {
                                type yang:counter32;
                                description
                                    "Indicates the number of times script is not executed due to debounce rule
                                     for the specified trigger entry.";
                            }

                        } // container statistics

                    } // list entry

                } // list etun

                ///nokia-state/state/log/event-trigger/filter
                list filter {
                    key "event";
                    description "Enter the filter list instance";

                    ///nokia-state/state/log/event-trigger/filter/event
                    leaf event {
                        type types-log:filter-events;
                        description "Log event as a trigger for one or more EHS handlers";
                    }

                    ///nokia-state/state/log/event-trigger/filter/oper-state
                    leaf oper-state {
                        type types-sros:oper-state;
                        description "Indicates the operational state of the EHS Event Trigger.";
                    }

                    ///nokia-state/state/log/event-trigger/filter/statistics
                    container statistics {
                        description "Enter the statistics context";

                        ///nokia-state/state/log/event-trigger/filter/statistics/success
                        leaf success {
                            type yang:counter32;
                            description
                                "Indicates the number of not ignored logger event occurrences
                                 associated with EHS trigger.";
                        }

                        ///nokia-state/state/log/event-trigger/filter/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/filter/statistics/error-admin-state
                        leaf error-admin-state {
                            type yang:counter32;
                            description
                                "Indicates the number of ignored logger event occurrences associated
                                 with EHS trigger.

                                 Event is ignored due to trigger may be out-of-service.";
                        }

                        ///nokia-state/state/log/event-trigger/filter/statistics/total
                        leaf total {
                            type yang:counter32;
                            description "Sum of success + error-no-entry + error-admin-state.";
                        }

                    } // container statistics

                    ///nokia-state/state/log/event-trigger/filter/summary-entry-statistics
                    container summary-entry-statistics {
                        description "Enter the summary-entry-statistics context";

                        ///nokia-state/state/log/event-trigger/filter/summary-entry-statistics/filter-match
                        leaf filter-match {
                            type yang:counter32;
                            description "Indicates the number of times a filter matches an logger event.";
                        }

                        ///nokia-state/state/log/event-trigger/filter/summary-entry-statistics/filter-fail
                        leaf filter-fail {
                            type yang:counter32;
                            description "Indicates the number of times a filter does not match an logger event.";
                        }

                        ///nokia-state/state/log/event-trigger/filter/summary-entry-statistics/error-admin-state
                        leaf error-admin-state {
                            type yang:counter32;
                            description
                                "Indicates the number of times the logger event will be ignored due to
                                 admin state of EHS trigger entries is out-of-service.";
                        }

                        ///nokia-state/state/log/event-trigger/filter/summary-entry-statistics/error-filter
                        leaf error-filter {
                            type yang:counter32;
                            description
                                "Indicates the number of times the logger event will be ignored due to filter
                                 is not operational or is not configured in EHS trigger entries.";
                        }

                        ///nokia-state/state/log/event-trigger/filter/summary-entry-statistics/error-handler
                        leaf error-handler {
                            type yang:counter32;
                            description
                                "Indicates the number of times the logger event will be ignored due to handler
                                 is not operational or is not configured in EHS trigger entries.";
                        }

                        ///nokia-state/state/log/event-trigger/filter/summary-entry-statistics/trigger-count
                        leaf trigger-count {
                            type yang:counter32;
                            description "Indicates the number of times script execution is triggered after filter match.";
                        }

                        ///nokia-state/state/log/event-trigger/filter/summary-entry-statistics/debounce-count
                        leaf debounce-count {
                            type yang:counter32;
                            description "Indicates the number of times script is not executed due to debounce rule.";
                        }

                    } // container summary-entry-statistics

                    ///nokia-state/state/log/event-trigger/filter/entry
                    list entry {
                        key "id";
                        description "Enter the entry list instance";

                        ///nokia-state/state/log/event-trigger/filter/entry/id
                        leaf id {
                            type uint32 {
                                range "1..1500";
                            }
                            description "ID of the EHS event trigger entry";
                        }

                        ///nokia-state/state/log/event-trigger/filter/entry/oper-state
                        leaf oper-state {
                            type types-sros:oper-state;
                            description "Indicates the operational state of the EHS Event Trigger Entry.";
                        }

                        ///nokia-state/state/log/event-trigger/filter/entry/statistics
                        container statistics {
                            description "Enter the statistics context";

                            ///nokia-state/state/log/event-trigger/filter/entry/statistics/filter-match
                            leaf filter-match {
                                type yang:counter32;
                                description
                                    "Indicates the number of times a filter, for the specified trigger entry,
                                     matches an logger event.";
                            }

                            ///nokia-state/state/log/event-trigger/filter/entry/statistics/filter-fail
                            leaf filter-fail {
                                type yang:counter32;
                                description
                                    "Indicates the number of times a filter, for the specified trigger entry,
                                     does not match an logger event.";
                            }

                            ///nokia-state/state/log/event-trigger/filter/entry/statistics/error-admin-state
                            leaf error-admin-state {
                                type yang:counter32;
                                description
                                    "Indicates the number of times the logger event will be ignored due to
                                     admin state of EHS trigger entry is out-of-service.";
                            }

                            ///nokia-state/state/log/event-trigger/filter/entry/statistics/error-filter
                            leaf error-filter {
                                type yang:counter32;
                                description
                                    "Indicates the number of times the logger event will be ignored due to filter
                                     is not operational or is not configured in EHS trigger entry.";
                            }

                            ///nokia-state/state/log/event-trigger/filter/entry/statistics/error-handler
                            leaf error-handler {
                                type yang:counter32;
                                description
                                    "Indicates the number of times the logger event will be ignored due to handler
                                     is not operational or is not configured in EHS trigger entry.";
                            }

                            ///nokia-state/state/log/event-trigger/filter/entry/statistics/trigger-count
                            leaf trigger-count {
                                type yang:counter32;
                                description
                                    "Indicates the number of times script execution is triggered after filter match
                                     for the specified trigger entry.";
                            }

                            ///nokia-state/state/log/event-trigger/filter/entry/statistics/debounce-count
                            leaf debounce-count {
                                type yang:counter32;
                                description
                                    "Indicates the number of times script is not executed due to debounce rule
                                     for the specified trigger entry.";
                            }

                        } // container statistics

                    } // list entry

                } // list filter

                ///nokia-state/state/log/event-trigger/gsmp
                list gsmp {
                    key "event";
                    description "Enter the gsmp list instance";

                    ///nokia-state/state/log/event-trigger/gsmp/event
                    leaf event {
                        type types-log:gsmp-events;
                        description "Log event as a trigger for one or more EHS handlers";
                    }

                    ///nokia-state/state/log/event-trigger/gsmp/oper-state
                    leaf oper-state {
                        type types-sros:oper-state;
                        description "Indicates the operational state of the EHS Event Trigger.";
                    }

                    ///nokia-state/state/log/event-trigger/gsmp/statistics
                    container statistics {
                        description "Enter the statistics context";

                        ///nokia-state/state/log/event-trigger/gsmp/statistics/success
                        leaf success {
                            type yang:counter32;
                            description
                                "Indicates the number of not ignored logger event occurrences
                                 associated with EHS trigger.";
                        }

                        ///nokia-state/state/log/event-trigger/gsmp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/gsmp/statistics/error-admin-state
                        leaf error-admin-state {
                            type yang:counter32;
                            description
                                "Indicates the number of ignored logger event occurrences associated
                                 with EHS trigger.

                                 Event is ignored due to trigger may be out-of-service.";
                        }

                        ///nokia-state/state/log/event-trigger/gsmp/statistics/total
                        leaf total {
                            type yang:counter32;
                            description "Sum of success + error-no-entry + error-admin-state.";
                        }

                    } // container statistics

                    ///nokia-state/state/log/event-trigger/gsmp/summary-entry-statistics
                    container summary-entry-statistics {
                        description "Enter the summary-entry-statistics context";

                        ///nokia-state/state/log/event-trigger/gsmp/summary-entry-statistics/filter-match
                        leaf filter-match {
                            type yang:counter32;
                            description "Indicates the number of times a filter matches an logger event.";
                        }

                        ///nokia-state/state/log/event-trigger/gsmp/summary-entry-statistics/filter-fail
                        leaf filter-fail {
                            type yang:counter32;
                            description "Indicates the number of times a filter does not match an logger event.";
                        }

                        ///nokia-state/state/log/event-trigger/gsmp/summary-entry-statistics/error-admin-state
                        leaf error-admin-state {
                            type yang:counter32;
                            description
                                "Indicates the number of times the logger event will be ignored due to
                                 admin state of EHS trigger entries is out-of-service.";
                        }

                        ///nokia-state/state/log/event-trigger/gsmp/summary-entry-statistics/error-filter
                        leaf error-filter {
                            type yang:counter32;
                            description
                                "Indicates the number of times the logger event will be ignored due to filter
                                 is not operational or is not configured in EHS trigger entries.";
                        }

                        ///nokia-state/state/log/event-trigger/gsmp/summary-entry-statistics/error-handler
                        leaf error-handler {
                            type yang:counter32;
                            description
                                "Indicates the number of times the logger event will be ignored due to handler
                                 is not operational or is not configured in EHS trigger entries.";
                        }

                        ///nokia-state/state/log/event-trigger/gsmp/summary-entry-statistics/trigger-count
                        leaf trigger-count {
                            type yang:counter32;
                            description "Indicates the number of times script execution is triggered after filter match.";
                        }

                        ///nokia-state/state/log/event-trigger/gsmp/summary-entry-statistics/debounce-count
                        leaf debounce-count {
                            type yang:counter32;
                            description "Indicates the number of times script is not executed due to debounce rule.";
                        }

                    } // container summary-entry-statistics

                    ///nokia-state/state/log/event-trigger/gsmp/entry
                    list entry {
                        key "id";
                        description "Enter the entry list instance";

                        ///nokia-state/state/log/event-trigger/gsmp/entry/id
                        leaf id {
                            type uint32 {
                                range "1..1500";
                            }
                            description "ID of the EHS event trigger entry";
                        }

                        ///nokia-state/state/log/event-trigger/gsmp/entry/oper-state
                        leaf oper-state {
                            type types-sros:oper-state;
                            description "Indicates the operational state of the EHS Event Trigger Entry.";
                        }

                        ///nokia-state/state/log/event-trigger/gsmp/entry/statistics
                        container statistics {
                            description "Enter the statistics context";

                            ///nokia-state/state/log/event-trigger/gsmp/entry/statistics/filter-match
                            leaf filter-match {
                                type yang:counter32;
                                description
                                    "Indicates the number of times a filter, for the specified trigger entry,
                                     matches an logger event.";
                            }

                            ///nokia-state/state/log/event-trigger/gsmp/entry/statistics/filter-fail
                            leaf filter-fail {
                                type yang:counter32;
                                description
                                    "Indicates the number of times a filter, for the specified trigger entry,
                                     does not match an logger event.";
                            }

                            ///nokia-state/state/log/event-trigger/gsmp/entry/statistics/error-admin-state
                            leaf error-admin-state {
                                type yang:counter32;
                                description
                                    "Indicates the number of times the logger event will be ignored due to
                                     admin state of EHS trigger entry is out-of-service.";
                            }

                            ///nokia-state/state/log/event-trigger/gsmp/entry/statistics/error-filter
                            leaf error-filter {
                                type yang:counter32;
                                description
                                    "Indicates the number of times the logger event will be ignored due to filter
                                     is not operational or is not configured in EHS trigger entry.";
                            }

                            ///nokia-state/state/log/event-trigger/gsmp/entry/statistics/error-handler
                            leaf error-handler {
                                type yang:counter32;
                                description
                                    "Indicates the number of times the logger event will be ignored due to handler
                                     is not operational or is not configured in EHS trigger entry.";
                            }

                            ///nokia-state/state/log/event-trigger/gsmp/entry/statistics/trigger-count
                            leaf trigger-count {
                                type yang:counter32;
                                description
                                    "Indicates the number of times script execution is triggered after filter match
                                     for the specified trigger entry.";
                            }

                            ///nokia-state/state/log/event-trigger/gsmp/entry/statistics/debounce-count
                            leaf debounce-count {
                                type yang:counter32;
                                description
                                    "Indicates the number of times script is not executed due to debounce rule
                                     for the specified trigger entry.";
                            }

                        } // container statistics

                    } // list entry

                } // list gsmp

                ///nokia-state/state/log/event-trigger/igmp
                list igmp {
                    key "event";
                    description "Enter the igmp list instance";

                    ///nokia-state/state/log/event-trigger/igmp/event
                    leaf event {
                        type types-log:igmp-events;
                        description "Log event as a trigger for one or more EHS handlers";
                    }

                    ///nokia-state/state/log/event-trigger/igmp/oper-state
                    leaf oper-state {
                        type types-sros:oper-state;
                        description "Indicates the operational state of the EHS Event Trigger.";
                    }

                    ///nokia-state/state/log/event-trigger/igmp/statistics
                    container statistics {
                        description "Enter the statistics context";

                        ///nokia-state/state/log/event-trigger/igmp/statistics/success
                        leaf success {
                            type yang:counter32;
                            description
                                "Indicates the number of not ignored logger event occurrences
                                 associated with EHS trigger.";
                        }

                        ///nokia-state/state/log/event-trigger/igmp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/igmp/statistics/error-admin-state
                        leaf error-admin-state {
                            type yang:counter32;
                            description
                                "Indicates the number of ignored logger event occurrences associated
                                 with EHS trigger.

                                 Event is ignored due to trigger may be out-of-service.";
                        }

                        ///nokia-state/state/log/event-trigger/igmp/statistics/total
                        leaf total {
                            type yang:counter32;
                            description "Sum of success + error-no-entry + error-admin-state.";
                        }

                    } // container statistics

                    ///nokia-state/state/log/event-trigger/igmp/summary-entry-statistics
                    container summary-entry-statistics {
                        description "Enter the summary-entry-statistics context";

                        ///nokia-state/state/log/event-trigger/igmp/summary-entry-statistics/filter-match
                        leaf filter-match {
                            type yang:counter32;
                            description "Indicates the number of times a filter matches an logger event.";
                        }

                        ///nokia-state/state/log/event-trigger/igmp/summary-entry-statistics/filter-fail
                        leaf filter-fail {
                            type yang:counter32;
                            description "Indicates the number of times a filter does not match an logger event.";
                        }

                        ///nokia-state/state/log/event-trigger/igmp/summary-entry-statistics/error-admin-state
                        leaf error-admin-state {
                            type yang:counter32;
                            description
                                "Indicates the number of times the logger event will be ignored due to
                                 admin state of EHS trigger entries is out-of-service.";
                        }

                        ///nokia-state/state/log/event-trigger/igmp/summary-entry-statistics/error-filter
                        leaf error-filter {
                            type yang:counter32;
                            description
                                "Indicates the number of times the logger event will be ignored due to filter
                                 is not operational or is not configured in EHS trigger entries.";
                        }

                        ///nokia-state/state/log/event-trigger/igmp/summary-entry-statistics/error-handler
                        leaf error-handler {
                            type yang:counter32;
                            description
                                "Indicates the number of times the logger event will be ignored due to handler
                                 is not operational or is not configured in EHS trigger entries.";
                        }

                        ///nokia-state/state/log/event-trigger/igmp/summary-entry-statistics/trigger-count
                        leaf trigger-count {
                            type yang:counter32;
                            description "Indicates the number of times script execution is triggered after filter match.";
                        }

                        ///nokia-state/state/log/event-trigger/igmp/summary-entry-statistics/debounce-count
                        leaf debounce-count {
                            type yang:counter32;
                            description "Indicates the number of times script is not executed due to debounce rule.";
                        }

                    } // container summary-entry-statistics

                    ///nokia-state/state/log/event-trigger/igmp/entry
                    list entry {
                        key "id";
                        description "Enter the entry list instance";

                        ///nokia-state/state/log/event-trigger/igmp/entry/id
                        leaf id {
                            type uint32 {
                                range "1..1500";
                            }
                            description "ID of the EHS event trigger entry";
                        }

                        ///nokia-state/state/log/event-trigger/igmp/entry/oper-state
                        leaf oper-state {
                            type types-sros:oper-state;
                            description "Indicates the operational state of the EHS Event Trigger Entry.";
                        }

                        ///nokia-state/state/log/event-trigger/igmp/entry/statistics
                        container statistics {
                            description "Enter the statistics context";

                            ///nokia-state/state/log/event-trigger/igmp/entry/statistics/filter-match
                            leaf filter-match {
                                type yang:counter32;
                                description
                                    "Indicates the number of times a filter, for the specified trigger entry,
                                     matches an logger event.";
                            }

                            ///nokia-state/state/log/event-trigger/igmp/entry/statistics/filter-fail
                            leaf filter-fail {
                                type yang:counter32;
                                description
                                    "Indicates the number of times a filter, for the specified trigger entry,
                                     does not match an logger event.";
                            }

                            ///nokia-state/state/log/event-trigger/igmp/entry/statistics/error-admin-state
                            leaf error-admin-state {
                                type yang:counter32;
                                description
                                    "Indicates the number of times the logger event will be ignored due to
                                     admin state of EHS trigger entry is out-of-service.";
                            }

                            ///nokia-state/state/log/event-trigger/igmp/entry/statistics/error-filter
                            leaf error-filter {
                                type yang:counter32;
                                description
                                    "Indicates the number of times the logger event will be ignored due to filter
                                     is not operational or is not configured in EHS trigger entry.";
                            }

                            ///nokia-state/state/log/event-trigger/igmp/entry/statistics/error-handler
                            leaf error-handler {
                                type yang:counter32;
                                description
                                    "Indicates the number of times the logger event will be ignored due to handler
                                     is not operational or is not configured in EHS trigger entry.";
                            }

                            ///nokia-state/state/log/event-trigger/igmp/entry/statistics/trigger-count
                            leaf trigger-count {
                                type yang:counter32;
                                description
                                    "Indicates the number of times script execution is triggered after filter match
                                     for the specified trigger entry.";
                            }

                            ///nokia-state/state/log/event-trigger/igmp/entry/statistics/debounce-count
                            leaf debounce-count {
                                type yang:counter32;
                                description
                                    "Indicates the number of times script is not executed due to debounce rule
                                     for the specified trigger entry.";
                            }

                        } // container statistics

                    } // list entry

                } // list igmp

                ///nokia-state/state/log/event-trigger/igmp-snooping
                list igmp-snooping {
                    key "event";
                    description "Enter the igmp-snooping list instance";

                    ///nokia-state/state/log/event-trigger/igmp-snooping/event
                    leaf event {
                        type types-log:igmp-snooping-events;
                        description "Log event as a trigger for one or more EHS handlers";
                    }

                    ///nokia-state/state/log/event-trigger/igmp-snooping/oper-state
                    leaf oper-state {
                        type types-sros:oper-state;
                        description "Indicates the operational state of the EHS Event Trigger.";
                    }

                    ///nokia-state/state/log/event-trigger/igmp-snooping/statistics
                    container statistics {
                        description "Enter the statistics context";

                        ///nokia-state/state/log/event-trigger/igmp-snooping/statistics/success
                        leaf success {
                            type yang:counter32;
                            description
                                "Indicates the number of not ignored logger event occurrences
                                 associated with EHS trigger.";
                        }

                        ///nokia-state/state/log/event-trigger/igmp-snooping/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/igmp-snooping/statistics/error-admin-state
                        leaf error-admin-state {
                            type yang:counter32;
                            description
                                "Indicates the number of ignored logger event occurrences associated
                                 with EHS trigger.

                                 Event is ignored due to trigger may be out-of-service.";
                        }

                        ///nokia-state/state/log/event-trigger/igmp-snooping/statistics/total
                        leaf total {
                            type yang:counter32;
                            description "Sum of success + error-no-entry + error-admin-state.";
                        }

                    } // container statistics

                    ///nokia-state/state/log/event-trigger/igmp-snooping/summary-entry-statistics
                    container summary-entry-statistics {
                        description "Enter the summary-entry-statistics context";

                        ///nokia-state/state/log/event-trigger/igmp-snooping/summary-entry-statistics/filter-match
                        leaf filter-match {
                            type yang:counter32;
                            description "Indicates the number of times a filter matches an logger event.";
                        }

                        ///nokia-state/state/log/event-trigger/igmp-snooping/summary-entry-statistics/filter-fail
                        leaf filter-fail {
                            type yang:counter32;
                            description "Indicates the number of times a filter does not match an logger event.";
                        }

                        ///nokia-state/state/log/event-trigger/igmp-snooping/summary-entry-statistics/error-admin-state
                        leaf error-admin-state {
                            type yang:counter32;
                            description
                                "Indicates the number of times the logger event will be ignored due to
                                 admin state of EHS trigger entries is out-of-service.";
                        }

                        ///nokia-state/state/log/event-trigger/igmp-snooping/summary-entry-statistics/error-filter
                        leaf error-filter {
                            type yang:counter32;
                            description
                                "Indicates the number of times the logger event will be ignored due to filter
                                 is not operational or is not configured in EHS trigger entries.";
                        }

                        ///nokia-state/state/log/event-trigger/igmp-snooping/summary-entry-statistics/error-handler
                        leaf error-handler {
                            type yang:counter32;
                            description
                                "Indicates the number of times the logger event will be ignored due to handler
                                 is not operational or is not configured in EHS trigger entries.";
                        }

                        ///nokia-state/state/log/event-trigger/igmp-snooping/summary-entry-statistics/trigger-count
                        leaf trigger-count {
                            type yang:counter32;
                            description "Indicates the number of times script execution is triggered after filter match.";
                        }

                        ///nokia-state/state/log/event-trigger/igmp-snooping/summary-entry-statistics/debounce-count
                        leaf debounce-count {
                            type yang:counter32;
                            description "Indicates the number of times script is not executed due to debounce rule.";
                        }

                    } // container summary-entry-statistics

                    ///nokia-state/state/log/event-trigger/igmp-snooping/entry
                    list entry {
                        key "id";
                        description "Enter the entry list instance";

                        ///nokia-state/state/log/event-trigger/igmp-snooping/entry/id
                        leaf id {
                            type uint32 {
                                range "1..1500";
                            }
                            description "ID of the EHS event trigger entry";
                        }

                        ///nokia-state/state/log/event-trigger/igmp-snooping/entry/oper-state
                        leaf oper-state {
                            type types-sros:oper-state;
                            description "Indicates the operational state of the EHS Event Trigger Entry.";
                        }

                        ///nokia-state/state/log/event-trigger/igmp-snooping/entry/statistics
                        container statistics {
                            description "Enter the statistics context";

                            ///nokia-state/state/log/event-trigger/igmp-snooping/entry/statistics/filter-match
                            leaf filter-match {
                                type yang:counter32;
                                description
                                    "Indicates the number of times a filter, for the specified trigger entry,
                                     matches an logger event.";
                            }

                            ///nokia-state/state/log/event-trigger/igmp-snooping/entry/statistics/filter-fail
                            leaf filter-fail {
                                type yang:counter32;
                                description
                                    "Indicates the number of times a filter, for the specified trigger entry,
                                     does not match an logger event.";
                            }

                            ///nokia-state/state/log/event-trigger/igmp-snooping/entry/statistics/error-admin-state
                            leaf error-admin-state {
                                type yang:counter32;
                                description
                                    "Indicates the number of times the logger event will be ignored due to
                                     admin state of EHS trigger entry is out-of-service.";
                            }

                            ///nokia-state/state/log/event-trigger/igmp-snooping/entry/statistics/error-filter
                            leaf error-filter {
                                type yang:counter32;
                                description
                                    "Indicates the number of times the logger event will be ignored due to filter
                                     is not operational or is not configured in EHS trigger entry.";
                            }

                            ///nokia-state/state/log/event-trigger/igmp-snooping/entry/statistics/error-handler
                            leaf error-handler {
                                type yang:counter32;
                                description
                                    "Indicates the number of times the logger event will be ignored due to handler
                                     is not operational or is not configured in EHS trigger entry.";
                            }

                            ///nokia-state/state/log/event-trigger/igmp-snooping/entry/statistics/trigger-count
                            leaf trigger-count {
                                type yang:counter32;
                                description
                                    "Indicates the number of times script execution is triggered after filter match
                                     for the specified trigger entry.";
                            }

                            ///nokia-state/state/log/event-trigger/igmp-snooping/entry/statistics/debounce-count
                            leaf debounce-count {
                                type yang:counter32;
                                description
                                    "Indicates the number of times script is not executed due to debounce rule
                                     for the specified trigger entry.";
                            }

                        } // container statistics

                    } // list entry

                } // list igmp-snooping

                ///nokia-state/state/log/event-trigger/ip
                list ip {
                    key "event";
                    description "Enter the ip list instance";

                    ///nokia-state/state/log/event-trigger/ip/event
                    leaf event {
                        type types-log:ip-events;
                        description "Log event as a trigger for one or more EHS handlers";
                    }

                    ///nokia-state/state/log/event-trigger/ip/oper-state
                    leaf oper-state {
                        type types-sros:oper-state;
                        description "Indicates the operational state of the EHS Event Trigger.";
                    }

                    ///nokia-state/state/log/event-trigger/ip/statistics
                    container statistics {
                        description "Enter the statistics context";

                        ///nokia-state/state/log/event-trigger/ip/statistics/success
                        leaf success {
                            type yang:counter32;
                            description
                                "Indicates the number of not ignored logger event occurrences
                                 associated with EHS trigger.";
                        }

                        ///nokia-state/state/log/event-trigger/ip/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ip/statistics/error-admin-state
                        leaf error-admin-state {
                            type yang:counter32;
                            description
                                "Indicates the number of ignored logger event occurrences associated
                                 with EHS trigger.

                                 Event is ignored due to trigger may be out-of-service.";
                        }

                        ///nokia-state/state/log/event-trigger/ip/statistics/total
                        leaf total {
                            type yang:counter32;
                            description "Sum of success + error-no-entry + error-admin-state.";
                        }

                    } // container statistics

                    ///nokia-state/state/log/event-trigger/ip/summary-entry-statistics
                    container summary-entry-statistics {
                        description "Enter the summary-entry-statistics context";

                        ///nokia-state/state/log/event-trigger/ip/summary-entry-statistics/filter-match
                        leaf filter-match {
                            type yang:counter32;
                            description "Indicates the number of times a filter matches an logger event.";
                        }

                        ///nokia-state/state/log/event-trigger/ip/summary-entry-statistics/filter-fail
                        leaf filter-fail {
                            type yang:counter32;
                            description "Indicates the number of times a filter does not match an logger event.";
                        }

                        ///nokia-state/state/log/event-trigger/ip/summary-entry-statistics/error-admin-state
                        leaf error-admin-state {
                            type yang:counter32;
                            description
                                "Indicates the number of times the logger event will be ignored due to
                                 admin state of EHS trigger entries is out-of-service.";
                        }

                        ///nokia-state/state/log/event-trigger/ip/summary-entry-statistics/error-filter
                        leaf error-filter {
                            type yang:counter32;
                            description
                                "Indicates the number of times the logger event will be ignored due to filter
                                 is not operational or is not configured in EHS trigger entries.";
                        }

                        ///nokia-state/state/log/event-trigger/ip/summary-entry-statistics/error-handler
                        leaf error-handler {
                            type yang:counter32;
                            description
                                "Indicates the number of times the logger event will be ignored due to handler
                                 is not operational or is not configured in EHS trigger entries.";
                        }

                        ///nokia-state/state/log/event-trigger/ip/summary-entry-statistics/trigger-count
                        leaf trigger-count {
                            type yang:counter32;
                            description "Indicates the number of times script execution is triggered after filter match.";
                        }

                        ///nokia-state/state/log/event-trigger/ip/summary-entry-statistics/debounce-count
                        leaf debounce-count {
                            type yang:counter32;
                            description "Indicates the number of times script is not executed due to debounce rule.";
                        }

                    } // container summary-entry-statistics

                    ///nokia-state/state/log/event-trigger/ip/entry
                    list entry {
                        key "id";
                        description "Enter the entry list instance";

                        ///nokia-state/state/log/event-trigger/ip/entry/id
                        leaf id {
                            type uint32 {
                                range "1..1500";
                            }
                            description "ID of the EHS event trigger entry";
                        }

                        ///nokia-state/state/log/event-trigger/ip/entry/oper-state
                        leaf oper-state {
                            type types-sros:oper-state;
                            description "Indicates the operational state of the EHS Event Trigger Entry.";
                        }

                        ///nokia-state/state/log/event-trigger/ip/entry/statistics
                        container statistics {
                            description "Enter the statistics context";

                            ///nokia-state/state/log/event-trigger/ip/entry/statistics/filter-match
                            leaf filter-match {
                                type yang:counter32;
                                description
                                    "Indicates the number of times a filter, for the specified trigger entry,
                                     matches an logger event.";
                            }

                            ///nokia-state/state/log/event-trigger/ip/entry/statistics/filter-fail
                            leaf filter-fail {
                                type yang:counter32;
                                description
                                    "Indicates the number of times a filter, for the specified trigger entry,
                                     does not match an logger event.";
                            }

                            ///nokia-state/state/log/event-trigger/ip/entry/statistics/error-admin-state
                            leaf error-admin-state {
                                type yang:counter32;
                                description
                                    "Indicates the number of times the logger event will be ignored due to
                                     admin state of EHS trigger entry is out-of-service.";
                            }

                            ///nokia-state/state/log/event-trigger/ip/entry/statistics/error-filter
                            leaf error-filter {
                                type yang:counter32;
                                description
                                    "Indicates the number of times the logger event will be ignored due to filter
                                     is not operational or is not configured in EHS trigger entry.";
                            }

                            ///nokia-state/state/log/event-trigger/ip/entry/statistics/error-handler
                            leaf error-handler {
                                type yang:counter32;
                                description
                                    "Indicates the number of times the logger event will be ignored due to handler
                                     is not operational or is not configured in EHS trigger entry.";
                            }

                            ///nokia-state/state/log/event-trigger/ip/entry/statistics/trigger-count
                            leaf trigger-count {
                                type yang:counter32;
                                description
                                    "Indicates the number of times script execution is triggered after filter match
                                     for the specified trigger entry.";
                            }

                            ///nokia-state/state/log/event-trigger/ip/entry/statistics/debounce-count
                            leaf debounce-count {
                                type yang:counter32;
                                description
                                    "Indicates the number of times script is not executed due to debounce rule
                                     for the specified trigger entry.";
                            }

                        } // container statistics

                    } // list entry

                } // list ip

                ///nokia-state/state/log/event-trigger/ipsec
                list ipsec {
                    key "event";
                    description "Enter the ipsec list instance";

                    ///nokia-state/state/log/event-trigger/ipsec/event
                    leaf event {
                        type types-log:ipsec-events;
                        description "Log event as a trigger for one or more EHS handlers";
                    }

                    ///nokia-state/state/log/event-trigger/ipsec/oper-state
                    leaf oper-state {
                        type types-sros:oper-state;
                        description "Indicates the operational state of the EHS Event Trigger.";
                    }

                    ///nokia-state/state/log/event-trigger/ipsec/statistics
                    container statistics {
                        description "Enter the statistics context";

                        ///nokia-state/state/log/event-trigger/ipsec/statistics/success
                        leaf success {
                            type yang:counter32;
                            description
                                "Indicates the number of not ignored logger event occurrences
                                 associated with EHS trigger.";
                        }

                        ///nokia-state/state/log/event-trigger/ipsec/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ipsec/statistics/error-admin-state
                        leaf error-admin-state {
                            type yang:counter32;
                            description
                                "Indicates the number of ignored logger event occurrences associated
                                 with EHS trigger.

                                 Event is ignored due to trigger may be out-of-service.";
                        }

                        ///nokia-state/state/log/event-trigger/ipsec/statistics/total
                        leaf total {
                            type yang:counter32;
                            description "Sum of success + error-no-entry + error-admin-state.";
                        }

                    } // container statistics

                    ///nokia-state/state/log/event-trigger/ipsec/summary-entry-statistics
                    container summary-entry-statistics {
                        description "Enter the summary-entry-statistics context";

                        ///nokia-state/state/log/event-trigger/ipsec/summary-entry-statistics/filter-match
                        leaf filter-match {
                            type yang:counter32;
                            description "Indicates the number of times a filter matches an logger event.";
                        }

                        ///nokia-state/state/log/event-trigger/ipsec/summary-entry-statistics/filter-fail
                        leaf filter-fail {
                            type yang:counter32;
                            description "Indicates the number of times a filter does not match an logger event.";
                        }

                        ///nokia-state/state/log/event-trigger/ipsec/summary-entry-statistics/error-admin-state
                        leaf error-admin-state {
                            type yang:counter32;
                            description
                                "Indicates the number of times the logger event will be ignored due to
                                 admin state of EHS trigger entries is out-of-service.";
                        }

                        ///nokia-state/state/log/event-trigger/ipsec/summary-entry-statistics/error-filter
                        leaf error-filter {
                            type yang:counter32;
                            description
                                "Indicates the number of times the logger event will be ignored due to filter
                                 is not operational or is not configured in EHS trigger entries.";
                        }

                        ///nokia-state/state/log/event-trigger/ipsec/summary-entry-statistics/error-handler
                        leaf error-handler {
                            type yang:counter32;
                            description
                                "Indicates the number of times the logger event will be ignored due to handler
                                 is not operational or is not configured in EHS trigger entries.";
                        }

                        ///nokia-state/state/log/event-trigger/ipsec/summary-entry-statistics/trigger-count
                        leaf trigger-count {
                            type yang:counter32;
                            description "Indicates the number of times script execution is triggered after filter match.";
                        }

                        ///nokia-state/state/log/event-trigger/ipsec/summary-entry-statistics/debounce-count
                        leaf debounce-count {
                            type yang:counter32;
                            description "Indicates the number of times script is not executed due to debounce rule.";
                        }

                    } // container summary-entry-statistics

                    ///nokia-state/state/log/event-trigger/ipsec/entry
                    list entry {
                        key "id";
                        description "Enter the entry list instance";

                        ///nokia-state/state/log/event-trigger/ipsec/entry/id
                        leaf id {
                            type uint32 {
                                range "1..1500";
                            }
                            description "ID of the EHS event trigger entry";
                        }

                        ///nokia-state/state/log/event-trigger/ipsec/entry/oper-state
                        leaf oper-state {
                            type types-sros:oper-state;
                            description "Indicates the operational state of the EHS Event Trigger Entry.";
                        }

                        ///nokia-state/state/log/event-trigger/ipsec/entry/statistics
                        container statistics {
                            description "Enter the statistics context";

                            ///nokia-state/state/log/event-trigger/ipsec/entry/statistics/filter-match
                            leaf filter-match {
                                type yang:counter32;
                                description
                                    "Indicates the number of times a filter, for the specified trigger entry,
                                     matches an logger event.";
                            }

                            ///nokia-state/state/log/event-trigger/ipsec/entry/statistics/filter-fail
                            leaf filter-fail {
                                type yang:counter32;
                                description
                                    "Indicates the number of times a filter, for the specified trigger entry,
                                     does not match an logger event.";
                            }

                            ///nokia-state/state/log/event-trigger/ipsec/entry/statistics/error-admin-state
                            leaf error-admin-state {
                                type yang:counter32;
                                description
                                    "Indicates the number of times the logger event will be ignored due to
                                     admin state of EHS trigger entry is out-of-service.";
                            }

                            ///nokia-state/state/log/event-trigger/ipsec/entry/statistics/error-filter
                            leaf error-filter {
                                type yang:counter32;
                                description
                                    "Indicates the number of times the logger event will be ignored due to filter
                                     is not operational or is not configured in EHS trigger entry.";
                            }

                            ///nokia-state/state/log/event-trigger/ipsec/entry/statistics/error-handler
                            leaf error-handler {
                                type yang:counter32;
                                description
                                    "Indicates the number of times the logger event will be ignored due to handler
                                     is not operational or is not configured in EHS trigger entry.";
                            }

                            ///nokia-state/state/log/event-trigger/ipsec/entry/statistics/trigger-count
                            leaf trigger-count {
                                type yang:counter32;
                                description
                                    "Indicates the number of times script execution is triggered after filter match
                                     for the specified trigger entry.";
                            }

                            ///nokia-state/state/log/event-trigger/ipsec/entry/statistics/debounce-count
                            leaf debounce-count {
                                type yang:counter32;
                                description
                                    "Indicates the number of times script is not executed due to debounce rule
                                     for the specified trigger entry.";
                            }

                        } // container statistics

                    } // list entry

                } // list ipsec

                ///nokia-state/state/log/event-trigger/isis
                list isis {
                    key "event";
                    description "Enter the isis list instance";

                    ///nokia-state/state/log/event-trigger/isis/event
                    leaf event {
                        type types-log:isis-events;
                        description "Log event as a trigger for one or more EHS handlers";
                    }

                    ///nokia-state/state/log/event-trigger/isis/oper-state
                    leaf oper-state {
                        type types-sros:oper-state;
                        description "Indicates the operational state of the EHS Event Trigger.";
                    }

                    ///nokia-state/state/log/event-trigger/isis/statistics
                    container statistics {
                        description "Enter the statistics context";

                        ///nokia-state/state/log/event-trigger/isis/statistics/success
                        leaf success {
                            type yang:counter32;
                            description
                                "Indicates the number of not ignored logger event occurrences
                                 associated with EHS trigger.";
                        }

                        ///nokia-state/state/log/event-trigger/isis/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/isis/statistics/error-admin-state
                        leaf error-admin-state {
                            type yang:counter32;
                            description
                                "Indicates the number of ignored logger event occurrences associated
                                 with EHS trigger.

                                 Event is ignored due to trigger may be out-of-service.";
                        }

                        ///nokia-state/state/log/event-trigger/isis/statistics/total
                        leaf total {
                            type yang:counter32;
                            description "Sum of success + error-no-entry + error-admin-state.";
                        }

                    } // container statistics

                    ///nokia-state/state/log/event-trigger/isis/summary-entry-statistics
                    container summary-entry-statistics {
                        description "Enter the summary-entry-statistics context";

                        ///nokia-state/state/log/event-trigger/isis/summary-entry-statistics/filter-match
                        leaf filter-match {
                            type yang:counter32;
                            description "Indicates the number of times a filter matches an logger event.";
                        }

                        ///nokia-state/state/log/event-trigger/isis/summary-entry-statistics/filter-fail
                        leaf filter-fail {
                            type yang:counter32;
                            description "Indicates the number of times a filter does not match an logger event.";
                        }

                        ///nokia-state/state/log/event-trigger/isis/summary-entry-statistics/error-admin-state
                        leaf error-admin-state {
                            type yang:counter32;
                            description
                                "Indicates the number of times the logger event will be ignored due to
                                 admin state of EHS trigger entries is out-of-service.";
                        }

                        ///nokia-state/state/log/event-trigger/isis/summary-entry-statistics/error-filter
                        leaf error-filter {
                            type yang:counter32;
                            description
                                "Indicates the number of times the logger event will be ignored due to filter
                                 is not operational or is not configured in EHS trigger entries.";
                        }

                        ///nokia-state/state/log/event-trigger/isis/summary-entry-statistics/error-handler
                        leaf error-handler {
                            type yang:counter32;
                            description
                                "Indicates the number of times the logger event will be ignored due to handler
                                 is not operational or is not configured in EHS trigger entries.";
                        }

                        ///nokia-state/state/log/event-trigger/isis/summary-entry-statistics/trigger-count
                        leaf trigger-count {
                            type yang:counter32;
                            description "Indicates the number of times script execution is triggered after filter match.";
                        }

                        ///nokia-state/state/log/event-trigger/isis/summary-entry-statistics/debounce-count
                        leaf debounce-count {
                            type yang:counter32;
                            description "Indicates the number of times script is not executed due to debounce rule.";
                        }

                    } // container summary-entry-statistics

                    ///nokia-state/state/log/event-trigger/isis/entry
                    list entry {
                        key "id";
                        description "Enter the entry list instance";

                        ///nokia-state/state/log/event-trigger/isis/entry/id
                        leaf id {
                            type uint32 {
                                range "1..1500";
                            }
                            description "ID of the EHS event trigger entry";
                        }

                        ///nokia-state/state/log/event-trigger/isis/entry/oper-state
                        leaf oper-state {
                            type types-sros:oper-state;
                            description "Indicates the operational state of the EHS Event Trigger Entry.";
                        }

                        ///nokia-state/state/log/event-trigger/isis/entry/statistics
                        container statistics {
                            description "Enter the statistics context";

                            ///nokia-state/state/log/event-trigger/isis/entry/statistics/filter-match
                            leaf filter-match {
                                type yang:counter32;
                                description
                                    "Indicates the number of times a filter, for the specified trigger entry,
                                     matches an logger event.";
                            }

                            ///nokia-state/state/log/event-trigger/isis/entry/statistics/filter-fail
                            leaf filter-fail {
                                type yang:counter32;
                                description
                                    "Indicates the number of times a filter, for the specified trigger entry,
                                     does not match an logger event.";
                            }

                            ///nokia-state/state/log/event-trigger/isis/entry/statistics/error-admin-state
                            leaf error-admin-state {
                                type yang:counter32;
                                description
                                    "Indicates the number of times the logger event will be ignored due to
                                     admin state of EHS trigger entry is out-of-service.";
                            }

                            ///nokia-state/state/log/event-trigger/isis/entry/statistics/error-filter
                            leaf error-filter {
                                type yang:counter32;
                                description
                                    "Indicates the number of times the logger event will be ignored due to filter
                                     is not operational or is not configured in EHS trigger entry.";
                            }

                            ///nokia-state/state/log/event-trigger/isis/entry/statistics/error-handler
                            leaf error-handler {
                                type yang:counter32;
                                description
                                    "Indicates the number of times the logger event will be ignored due to handler
                                     is not operational or is not configured in EHS trigger entry.";
                            }

                            ///nokia-state/state/log/event-trigger/isis/entry/statistics/trigger-count
                            leaf trigger-count {
                                type yang:counter32;
                                description
                                    "Indicates the number of times script execution is triggered after filter match
                                     for the specified trigger entry.";
                            }

                            ///nokia-state/state/log/event-trigger/isis/entry/statistics/debounce-count
                            leaf debounce-count {
                                type yang:counter32;
                                description
                                    "Indicates the number of times script is not executed due to debounce rule
                                     for the specified trigger entry.";
                            }

                        } // container statistics

                    } // list entry

                } // list isis

                ///nokia-state/state/log/event-trigger/l2tp
                list l2tp {
                    key "event";
                    description "Enter the l2tp list instance";

                    ///nokia-state/state/log/event-trigger/l2tp/event
                    leaf event {
                        type types-log:l2tp-events;
                        description "Log event as a trigger for one or more EHS handlers";
                    }

                    ///nokia-state/state/log/event-trigger/l2tp/oper-state
                    leaf oper-state {
                        type types-sros:oper-state;
                        description "Indicates the operational state of the EHS Event Trigger.";
                    }

                    ///nokia-state/state/log/event-trigger/l2tp/statistics
                    container statistics {
                        description "Enter the statistics context";

                        ///nokia-state/state/log/event-trigger/l2tp/statistics/success
                        leaf success {
                            type yang:counter32;
                            description
                                "Indicates the number of not ignored logger event occurrences
                                 associated with EHS trigger.";
                        }

                        ///nokia-state/state/log/event-trigger/l2tp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/l2tp/statistics/error-admin-state
                        leaf error-admin-state {
                            type yang:counter32;
                            description
                                "Indicates the number of ignored logger event occurrences associated
                                 with EHS trigger.

                                 Event is ignored due to trigger may be out-of-service.";
                        }

                        ///nokia-state/state/log/event-trigger/l2tp/statistics/total
                        leaf total {
                            type yang:counter32;
                            description "Sum of success + error-no-entry + error-admin-state.";
                        }

                    } // container statistics

                    ///nokia-state/state/log/event-trigger/l2tp/summary-entry-statistics
                    container summary-entry-statistics {
                        description "Enter the summary-entry-statistics context";

                        ///nokia-state/state/log/event-trigger/l2tp/summary-entry-statistics/filter-match
                        leaf filter-match {
                            type yang:counter32;
                            description "Indicates the number of times a filter matches an logger event.";
                        }

                        ///nokia-state/state/log/event-trigger/l2tp/summary-entry-statistics/filter-fail
                        leaf filter-fail {
                            type yang:counter32;
                            description "Indicates the number of times a filter does not match an logger event.";
                        }

                        ///nokia-state/state/log/event-trigger/l2tp/summary-entry-statistics/error-admin-state
                        leaf error-admin-state {
                            type yang:counter32;
                            description
                                "Indicates the number of times the logger event will be ignored due to
                                 admin state of EHS trigger entries is out-of-service.";
                        }

                        ///nokia-state/state/log/event-trigger/l2tp/summary-entry-statistics/error-filter
                        leaf error-filter {
                            type yang:counter32;
                            description
                                "Indicates the number of times the logger event will be ignored due to filter
                                 is not operational or is not configured in EHS trigger entries.";
                        }

                        ///nokia-state/state/log/event-trigger/l2tp/summary-entry-statistics/error-handler
                        leaf error-handler {
                            type yang:counter32;
                            description
                                "Indicates the number of times the logger event will be ignored due to handler
                                 is not operational or is not configured in EHS trigger entries.";
                        }

                        ///nokia-state/state/log/event-trigger/l2tp/summary-entry-statistics/trigger-count
                        leaf trigger-count {
                            type yang:counter32;
                            description "Indicates the number of times script execution is triggered after filter match.";
                        }

                        ///nokia-state/state/log/event-trigger/l2tp/summary-entry-statistics/debounce-count
                        leaf debounce-count {
                            type yang:counter32;
                            description "Indicates the number of times script is not executed due to debounce rule.";
                        }

                    } // container summary-entry-statistics

                    ///nokia-state/state/log/event-trigger/l2tp/entry
                    list entry {
                        key "id";
                        description "Enter the entry list instance";

                        ///nokia-state/state/log/event-trigger/l2tp/entry/id
                        leaf id {
                            type uint32 {
                                range "1..1500";
                            }
                            description "ID of the EHS event trigger entry";
                        }

                        ///nokia-state/state/log/event-trigger/l2tp/entry/oper-state
                        leaf oper-state {
                            type types-sros:oper-state;
                            description "Indicates the operational state of the EHS Event Trigger Entry.";
                        }

                        ///nokia-state/state/log/event-trigger/l2tp/entry/statistics
                        container statistics {
                            description "Enter the statistics context";

                            ///nokia-state/state/log/event-trigger/l2tp/entry/statistics/filter-match
                            leaf filter-match {
                                type yang:counter32;
                                description
                                    "Indicates the number of times a filter, for the specified trigger entry,
                                     matches an logger event.";
                            }

                            ///nokia-state/state/log/event-trigger/l2tp/entry/statistics/filter-fail
                            leaf filter-fail {
                                type yang:counter32;
                                description
                                    "Indicates the number of times a filter, for the specified trigger entry,
                                     does not match an logger event.";
                            }

                            ///nokia-state/state/log/event-trigger/l2tp/entry/statistics/error-admin-state
                            leaf error-admin-state {
                                type yang:counter32;
                                description
                                    "Indicates the number of times the logger event will be ignored due to
                                     admin state of EHS trigger entry is out-of-service.";
                            }

                            ///nokia-state/state/log/event-trigger/l2tp/entry/statistics/error-filter
                            leaf error-filter {
                                type yang:counter32;
                                description
                                    "Indicates the number of times the logger event will be ignored due to filter
                                     is not operational or is not configured in EHS trigger entry.";
                            }

                            ///nokia-state/state/log/event-trigger/l2tp/entry/statistics/error-handler
                            leaf error-handler {
                                type yang:counter32;
                                description
                                    "Indicates the number of times the logger event will be ignored due to handler
                                     is not operational or is not configured in EHS trigger entry.";
                            }

                            ///nokia-state/state/log/event-trigger/l2tp/entry/statistics/trigger-count
                            leaf trigger-count {
                                type yang:counter32;
                                description
                                    "Indicates the number of times script execution is triggered after filter match
                                     for the specified trigger entry.";
                            }

                            ///nokia-state/state/log/event-trigger/l2tp/entry/statistics/debounce-count
                            leaf debounce-count {
                                type yang:counter32;
                                description
                                    "Indicates the number of times script is not executed due to debounce rule
                                     for the specified trigger entry.";
                            }

                        } // container statistics

                    } // list entry

                } // list l2tp

                ///nokia-state/state/log/event-trigger/lag
                list lag {
                    key "event";
                    description "Enter the lag list instance";

                    ///nokia-state/state/log/event-trigger/lag/event
                    leaf event {
                        type types-log:lag-events;
                        description "Log event as a trigger for one or more EHS handlers";
                    }

                    ///nokia-state/state/log/event-trigger/lag/oper-state
                    leaf oper-state {
                        type types-sros:oper-state;
                        description "Indicates the operational state of the EHS Event Trigger.";
                    }

                    ///nokia-state/state/log/event-trigger/lag/statistics
                    container statistics {
                        description "Enter the statistics context";

                        ///nokia-state/state/log/event-trigger/lag/statistics/success
                        leaf success {
                            type yang:counter32;
                            description
                                "Indicates the number of not ignored logger event occurrences
                                 associated with EHS trigger.";
                        }

                        ///nokia-state/state/log/event-trigger/lag/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/lag/statistics/error-admin-state
                        leaf error-admin-state {
                            type yang:counter32;
                            description
                                "Indicates the number of ignored logger event occurrences associated
                                 with EHS trigger.

                                 Event is ignored due to trigger may be out-of-service.";
                        }

                        ///nokia-state/state/log/event-trigger/lag/statistics/total
                        leaf total {
                            type yang:counter32;
                            description "Sum of success + error-no-entry + error-admin-state.";
                        }

                    } // container statistics

                    ///nokia-state/state/log/event-trigger/lag/summary-entry-statistics
                    container summary-entry-statistics {
                        description "Enter the summary-entry-statistics context";

                        ///nokia-state/state/log/event-trigger/lag/summary-entry-statistics/filter-match
                        leaf filter-match {
                            type yang:counter32;
                            description "Indicates the number of times a filter matches an logger event.";
                        }

                        ///nokia-state/state/log/event-trigger/lag/summary-entry-statistics/filter-fail
                        leaf filter-fail {
                            type yang:counter32;
                            description "Indicates the number of times a filter does not match an logger event.";
                        }

                        ///nokia-state/state/log/event-trigger/lag/summary-entry-statistics/error-admin-state
                        leaf error-admin-state {
                            type yang:counter32;
                            description
                                "Indicates the number of times the logger event will be ignored due to
                                 admin state of EHS trigger entries is out-of-service.";
                        }

                        ///nokia-state/state/log/event-trigger/lag/summary-entry-statistics/error-filter
                        leaf error-filter {
                            type yang:counter32;
                            description
                                "Indicates the number of times the logger event will be ignored due to filter
                                 is not operational or is not configured in EHS trigger entries.";
                        }

                        ///nokia-state/state/log/event-trigger/lag/summary-entry-statistics/error-handler
                        leaf error-handler {
                            type yang:counter32;
                            description
                                "Indicates the number of times the logger event will be ignored due to handler
                                 is not operational or is not configured in EHS trigger entries.";
                        }

                        ///nokia-state/state/log/event-trigger/lag/summary-entry-statistics/trigger-count
                        leaf trigger-count {
                            type yang:counter32;
                            description "Indicates the number of times script execution is triggered after filter match.";
                        }

                        ///nokia-state/state/log/event-trigger/lag/summary-entry-statistics/debounce-count
                        leaf debounce-count {
                            type yang:counter32;
                            description "Indicates the number of times script is not executed due to debounce rule.";
                        }

                    } // container summary-entry-statistics

                    ///nokia-state/state/log/event-trigger/lag/entry
                    list entry {
                        key "id";
                        description "Enter the entry list instance";

                        ///nokia-state/state/log/event-trigger/lag/entry/id
                        leaf id {
                            type uint32 {
                                range "1..1500";
                            }
                            description "ID of the EHS event trigger entry";
                        }

                        ///nokia-state/state/log/event-trigger/lag/entry/oper-state
                        leaf oper-state {
                            type types-sros:oper-state;
                            description "Indicates the operational state of the EHS Event Trigger Entry.";
                        }

                        ///nokia-state/state/log/event-trigger/lag/entry/statistics
                        container statistics {
                            description "Enter the statistics context";

                            ///nokia-state/state/log/event-trigger/lag/entry/statistics/filter-match
                            leaf filter-match {
                                type yang:counter32;
                                description
                                    "Indicates the number of times a filter, for the specified trigger entry,
                                     matches an logger event.";
                            }

                            ///nokia-state/state/log/event-trigger/lag/entry/statistics/filter-fail
                            leaf filter-fail {
                                type yang:counter32;
                                description
                                    "Indicates the number of times a filter, for the specified trigger entry,
                                     does not match an logger event.";
                            }

                            ///nokia-state/state/log/event-trigger/lag/entry/statistics/error-admin-state
                            leaf error-admin-state {
                                type yang:counter32;
                                description
                                    "Indicates the number of times the logger event will be ignored due to
                                     admin state of EHS trigger entry is out-of-service.";
                            }

                            ///nokia-state/state/log/event-trigger/lag/entry/statistics/error-filter
                            leaf error-filter {
                                type yang:counter32;
                                description
                                    "Indicates the number of times the logger event will be ignored due to filter
                                     is not operational or is not configured in EHS trigger entry.";
                            }

                            ///nokia-state/state/log/event-trigger/lag/entry/statistics/error-handler
                            leaf error-handler {
                                type yang:counter32;
                                description
                                    "Indicates the number of times the logger event will be ignored due to handler
                                     is not operational or is not configured in EHS trigger entry.";
                            }

                            ///nokia-state/state/log/event-trigger/lag/entry/statistics/trigger-count
                            leaf trigger-count {
                                type yang:counter32;
                                description
                                    "Indicates the number of times script execution is triggered after filter match
                                     for the specified trigger entry.";
                            }

                            ///nokia-state/state/log/event-trigger/lag/entry/statistics/debounce-count
                            leaf debounce-count {
                                type yang:counter32;
                                description
                                    "Indicates the number of times script is not executed due to debounce rule
                                     for the specified trigger entry.";
                            }

                        } // container statistics

                    } // list entry

                } // list lag

                ///nokia-state/state/log/event-trigger/ldap
                list ldap {
                    key "event";
                    description "Enter the ldap list instance";

                    ///nokia-state/state/log/event-trigger/ldap/event
                    leaf event {
                        type types-log:ldap-events;
                        description "Log event as a trigger for one or more EHS handlers";
                    }

                    ///nokia-state/state/log/event-trigger/ldap/oper-state
                    leaf oper-state {
                        type types-sros:oper-state;
                        description "Indicates the operational state of the EHS Event Trigger.";
                    }

                    ///nokia-state/state/log/event-trigger/ldap/statistics
                    container statistics {
                        description "Enter the statistics context";

                        ///nokia-state/state/log/event-trigger/ldap/statistics/success
                        leaf success {
                            type yang:counter32;
                            description
                                "Indicates the number of not ignored logger event occurrences
                                 associated with EHS trigger.";
                        }

                        ///nokia-state/state/log/event-trigger/ldap/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ldap/statistics/error-admin-state
                        leaf error-admin-state {
                            type yang:counter32;
                            description
                                "Indicates the number of ignored logger event occurrences associated
                                 with EHS trigger.

                                 Event is ignored due to trigger may be out-of-service.";
                        }

                        ///nokia-state/state/log/event-trigger/ldap/statistics/total
                        leaf total {
                            type yang:counter32;
                            description "Sum of success + error-no-entry + error-admin-state.";
                        }

                    } // container statistics

                    ///nokia-state/state/log/event-trigger/ldap/summary-entry-statistics
                    container summary-entry-statistics {
                        description "Enter the summary-entry-statistics context";

                        ///nokia-state/state/log/event-trigger/ldap/summary-entry-statistics/filter-match
                        leaf filter-match {
                            type yang:counter32;
                            description "Indicates the number of times a filter matches an logger event.";
                        }

                        ///nokia-state/state/log/event-trigger/ldap/summary-entry-statistics/filter-fail
                        leaf filter-fail {
                            type yang:counter32;
                            description "Indicates the number of times a filter does not match an logger event.";
                        }

                        ///nokia-state/state/log/event-trigger/ldap/summary-entry-statistics/error-admin-state
                        leaf error-admin-state {
                            type yang:counter32;
                            description
                                "Indicates the number of times the logger event will be ignored due to
                                 admin state of EHS trigger entries is out-of-service.";
                        }

                        ///nokia-state/state/log/event-trigger/ldap/summary-entry-statistics/error-filter
                        leaf error-filter {
                            type yang:counter32;
                            description
                                "Indicates the number of times the logger event will be ignored due to filter
                                 is not operational or is not configured in EHS trigger entries.";
                        }

                        ///nokia-state/state/log/event-trigger/ldap/summary-entry-statistics/error-handler
                        leaf error-handler {
                            type yang:counter32;
                            description
                                "Indicates the number of times the logger event will be ignored due to handler
                                 is not operational or is not configured in EHS trigger entries.";
                        }

                        ///nokia-state/state/log/event-trigger/ldap/summary-entry-statistics/trigger-count
                        leaf trigger-count {
                            type yang:counter32;
                            description "Indicates the number of times script execution is triggered after filter match.";
                        }

                        ///nokia-state/state/log/event-trigger/ldap/summary-entry-statistics/debounce-count
                        leaf debounce-count {
                            type yang:counter32;
                            description "Indicates the number of times script is not executed due to debounce rule.";
                        }

                    } // container summary-entry-statistics

                    ///nokia-state/state/log/event-trigger/ldap/entry
                    list entry {
                        key "id";
                        description "Enter the entry list instance";

                        ///nokia-state/state/log/event-trigger/ldap/entry/id
                        leaf id {
                            type uint32 {
                                range "1..1500";
                            }
                            description "ID of the EHS event trigger entry";
                        }

                        ///nokia-state/state/log/event-trigger/ldap/entry/oper-state
                        leaf oper-state {
                            type types-sros:oper-state;
                            description "Indicates the operational state of the EHS Event Trigger Entry.";
                        }

                        ///nokia-state/state/log/event-trigger/ldap/entry/statistics
                        container statistics {
                            description "Enter the statistics context";

                            ///nokia-state/state/log/event-trigger/ldap/entry/statistics/filter-match
                            leaf filter-match {
                                type yang:counter32;
                                description
                                    "Indicates the number of times a filter, for the specified trigger entry,
                                     matches an logger event.";
                            }

                            ///nokia-state/state/log/event-trigger/ldap/entry/statistics/filter-fail
                            leaf filter-fail {
                                type yang:counter32;
                                description
                                    "Indicates the number of times a filter, for the specified trigger entry,
                                     does not match an logger event.";
                            }

                            ///nokia-state/state/log/event-trigger/ldap/entry/statistics/error-admin-state
                            leaf error-admin-state {
                                type yang:counter32;
                                description
                                    "Indicates the number of times the logger event will be ignored due to
                                     admin state of EHS trigger entry is out-of-service.";
                            }

                            ///nokia-state/state/log/event-trigger/ldap/entry/statistics/error-filter
                            leaf error-filter {
                                type yang:counter32;
                                description
                                    "Indicates the number of times the logger event will be ignored due to filter
                                     is not operational or is not configured in EHS trigger entry.";
                            }

                            ///nokia-state/state/log/event-trigger/ldap/entry/statistics/error-handler
                            leaf error-handler {
                                type yang:counter32;
                                description
                                    "Indicates the number of times the logger event will be ignored due to handler
                                     is not operational or is not configured in EHS trigger entry.";
                            }

                            ///nokia-state/state/log/event-trigger/ldap/entry/statistics/trigger-count
                            leaf trigger-count {
                                type yang:counter32;
                                description
                                    "Indicates the number of times script execution is triggered after filter match
                                     for the specified trigger entry.";
                            }

                            ///nokia-state/state/log/event-trigger/ldap/entry/statistics/debounce-count
                            leaf debounce-count {
                                type yang:counter32;
                                description
                                    "Indicates the number of times script is not executed due to debounce rule
                                     for the specified trigger entry.";
                            }

                        } // container statistics

                    } // list entry

                } // list ldap

                ///nokia-state/state/log/event-trigger/ldp
                list ldp {
                    key "event";
                    description "Enter the ldp list instance";

                    ///nokia-state/state/log/event-trigger/ldp/event
                    leaf event {
                        type types-log:ldp-events;
                        description "Log event as a trigger for one or more EHS handlers";
                    }

                    ///nokia-state/state/log/event-trigger/ldp/oper-state
                    leaf oper-state {
                        type types-sros:oper-state;
                        description "Indicates the operational state of the EHS Event Trigger.";
                    }

                    ///nokia-state/state/log/event-trigger/ldp/statistics
                    container statistics {
                        description "Enter the statistics context";

                        ///nokia-state/state/log/event-trigger/ldp/statistics/success
                        leaf success {
                            type yang:counter32;
                            description
                                "Indicates the number of not ignored logger event occurrences
                                 associated with EHS trigger.";
                        }

                        ///nokia-state/state/log/event-trigger/ldp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ldp/statistics/error-admin-state
                        leaf error-admin-state {
                            type yang:counter32;
                            description
                                "Indicates the number of ignored logger event occurrences associated
                                 with EHS trigger.

                                 Event is ignored due to trigger may be out-of-service.";
                        }

                        ///nokia-state/state/log/event-trigger/ldp/statistics/total
                        leaf total {
                            type yang:counter32;
                            description "Sum of success + error-no-entry + error-admin-state.";
                        }

                    } // container statistics

                    ///nokia-state/state/log/event-trigger/ldp/summary-entry-statistics
                    container summary-entry-statistics {
                        description "Enter the summary-entry-statistics context";

                        ///nokia-state/state/log/event-trigger/ldp/summary-entry-statistics/filter-match
                        leaf filter-match {
                            type yang:counter32;
                            description "Indicates the number of times a filter matches an logger event.";
                        }

                        ///nokia-state/state/log/event-trigger/ldp/summary-entry-statistics/filter-fail
                        leaf filter-fail {
                            type yang:counter32;
                            description "Indicates the number of times a filter does not match an logger event.";
                        }

                        ///nokia-state/state/log/event-trigger/ldp/summary-entry-statistics/error-admin-state
                        leaf error-admin-state {
                            type yang:counter32;
                            description
                                "Indicates the number of times the logger event will be ignored due to
                                 admin state of EHS trigger entries is out-of-service.";
                        }

                        ///nokia-state/state/log/event-trigger/ldp/summary-entry-statistics/error-filter
                        leaf error-filter {
                            type yang:counter32;
                            description
                                "Indicates the number of times the logger event will be ignored due to filter
                                 is not operational or is not configured in EHS trigger entries.";
                        }

                        ///nokia-state/state/log/event-trigger/ldp/summary-entry-statistics/error-handler
                        leaf error-handler {
                            type yang:counter32;
                            description
                                "Indicates the number of times the logger event will be ignored due to handler
                                 is not operational or is not configured in EHS trigger entries.";
                        }

                        ///nokia-state/state/log/event-trigger/ldp/summary-entry-statistics/trigger-count
                        leaf trigger-count {
                            type yang:counter32;
                            description "Indicates the number of times script execution is triggered after filter match.";
                        }

                        ///nokia-state/state/log/event-trigger/ldp/summary-entry-statistics/debounce-count
                        leaf debounce-count {
                            type yang:counter32;
                            description "Indicates the number of times script is not executed due to debounce rule.";
                        }

                    } // container summary-entry-statistics

                    ///nokia-state/state/log/event-trigger/ldp/entry
                    list entry {
                        key "id";
                        description "Enter the entry list instance";

                        ///nokia-state/state/log/event-trigger/ldp/entry/id
                        leaf id {
                            type uint32 {
                                range "1..1500";
                            }
                            description "ID of the EHS event trigger entry";
                        }

                        ///nokia-state/state/log/event-trigger/ldp/entry/oper-state
                        leaf oper-state {
                            type types-sros:oper-state;
                            description "Indicates the operational state of the EHS Event Trigger Entry.";
                        }

                        ///nokia-state/state/log/event-trigger/ldp/entry/statistics
                        container statistics {
                            description "Enter the statistics context";

                            ///nokia-state/state/log/event-trigger/ldp/entry/statistics/filter-match
                            leaf filter-match {
                                type yang:counter32;
                                description
                                    "Indicates the number of times a filter, for the specified trigger entry,
                                     matches an logger event.";
                            }

                            ///nokia-state/state/log/event-trigger/ldp/entry/statistics/filter-fail
                            leaf filter-fail {
                                type yang:counter32;
                                description
                                    "Indicates the number of times a filter, for the specified trigger entry,
                                     does not match an logger event.";
                            }

                            ///nokia-state/state/log/event-trigger/ldp/entry/statistics/error-admin-state
                            leaf error-admin-state {
                                type yang:counter32;
                                description
                                    "Indicates the number of times the logger event will be ignored due to
                                     admin state of EHS trigger entry is out-of-service.";
                            }

                            ///nokia-state/state/log/event-trigger/ldp/entry/statistics/error-filter
                            leaf error-filter {
                                type yang:counter32;
                                description
                                    "Indicates the number of times the logger event will be ignored due to filter
                                     is not operational or is not configured in EHS trigger entry.";
                            }

                            ///nokia-state/state/log/event-trigger/ldp/entry/statistics/error-handler
                            leaf error-handler {
                                type yang:counter32;
                                description
                                    "Indicates the number of times the logger event will be ignored due to handler
                                     is not operational or is not configured in EHS trigger entry.";
                            }

                            ///nokia-state/state/log/event-trigger/ldp/entry/statistics/trigger-count
                            leaf trigger-count {
                                type yang:counter32;
                                description
                                    "Indicates the number of times script execution is triggered after filter match
                                     for the specified trigger entry.";
                            }

                            ///nokia-state/state/log/event-trigger/ldp/entry/statistics/debounce-count
                            leaf debounce-count {
                                type yang:counter32;
                                description
                                    "Indicates the number of times script is not executed due to debounce rule
                                     for the specified trigger entry.";
                            }

                        } // container statistics

                    } // list entry

                } // list ldp

                ///nokia-state/state/log/event-trigger/li
                list li {
                    key "event";
                    description "Enter the li list instance";

                    ///nokia-state/state/log/event-trigger/li/event
                    leaf event {
                        type types-log:li-events;
                        description "Log event as a trigger for one or more EHS handlers";
                    }

                    ///nokia-state/state/log/event-trigger/li/oper-state
                    leaf oper-state {
                        type types-sros:oper-state;
                        description "Indicates the operational state of the EHS Event Trigger.";
                    }

                    ///nokia-state/state/log/event-trigger/li/statistics
                    container statistics {
                        description "Enter the statistics context";

                        ///nokia-state/state/log/event-trigger/li/statistics/success
                        leaf success {
                            type yang:counter32;
                            description
                                "Indicates the number of not ignored logger event occurrences
                                 associated with EHS trigger.";
                        }

                        ///nokia-state/state/log/event-trigger/li/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/li/statistics/error-admin-state
                        leaf error-admin-state {
                            type yang:counter32;
                            description
                                "Indicates the number of ignored logger event occurrences associated
                                 with EHS trigger.

                                 Event is ignored due to trigger may be out-of-service.";
                        }

                        ///nokia-state/state/log/event-trigger/li/statistics/total
                        leaf total {
                            type yang:counter32;
                            description "Sum of success + error-no-entry + error-admin-state.";
                        }

                    } // container statistics

                    ///nokia-state/state/log/event-trigger/li/summary-entry-statistics
                    container summary-entry-statistics {
                        description "Enter the summary-entry-statistics context";

                        ///nokia-state/state/log/event-trigger/li/summary-entry-statistics/filter-match
                        leaf filter-match {
                            type yang:counter32;
                            description "Indicates the number of times a filter matches an logger event.";
                        }

                        ///nokia-state/state/log/event-trigger/li/summary-entry-statistics/filter-fail
                        leaf filter-fail {
                            type yang:counter32;
                            description "Indicates the number of times a filter does not match an logger event.";
                        }

                        ///nokia-state/state/log/event-trigger/li/summary-entry-statistics/error-admin-state
                        leaf error-admin-state {
                            type yang:counter32;
                            description
                                "Indicates the number of times the logger event will be ignored due to
                                 admin state of EHS trigger entries is out-of-service.";
                        }

                        ///nokia-state/state/log/event-trigger/li/summary-entry-statistics/error-filter
                        leaf error-filter {
                            type yang:counter32;
                            description
                                "Indicates the number of times the logger event will be ignored due to filter
                                 is not operational or is not configured in EHS trigger entries.";
                        }

                        ///nokia-state/state/log/event-trigger/li/summary-entry-statistics/error-handler
                        leaf error-handler {
                            type yang:counter32;
                            description
                                "Indicates the number of times the logger event will be ignored due to handler
                                 is not operational or is not configured in EHS trigger entries.";
                        }

                        ///nokia-state/state/log/event-trigger/li/summary-entry-statistics/trigger-count
                        leaf trigger-count {
                            type yang:counter32;
                            description "Indicates the number of times script execution is triggered after filter match.";
                        }

                        ///nokia-state/state/log/event-trigger/li/summary-entry-statistics/debounce-count
                        leaf debounce-count {
                            type yang:counter32;
                            description "Indicates the number of times script is not executed due to debounce rule.";
                        }

                    } // container summary-entry-statistics

                    ///nokia-state/state/log/event-trigger/li/entry
                    list entry {
                        key "id";
                        description "Enter the entry list instance";

                        ///nokia-state/state/log/event-trigger/li/entry/id
                        leaf id {
                            type uint32 {
                                range "1..1500";
                            }
                            description "ID of the EHS event trigger entry";
                        }

                        ///nokia-state/state/log/event-trigger/li/entry/oper-state
                        leaf oper-state {
                            type types-sros:oper-state;
                            description "Indicates the operational state of the EHS Event Trigger Entry.";
                        }

                        ///nokia-state/state/log/event-trigger/li/entry/statistics
                        container statistics {
                            description "Enter the statistics context";

                            ///nokia-state/state/log/event-trigger/li/entry/statistics/filter-match
                            leaf filter-match {
                                type yang:counter32;
                                description
                                    "Indicates the number of times a filter, for the specified trigger entry,
                                     matches an logger event.";
                            }

                            ///nokia-state/state/log/event-trigger/li/entry/statistics/filter-fail
                            leaf filter-fail {
                                type yang:counter32;
                                description
                                    "Indicates the number of times a filter, for the specified trigger entry,
                                     does not match an logger event.";
                            }

                            ///nokia-state/state/log/event-trigger/li/entry/statistics/error-admin-state
                            leaf error-admin-state {
                                type yang:counter32;
                                description
                                    "Indicates the number of times the logger event will be ignored due to
                                     admin state of EHS trigger entry is out-of-service.";
                            }

                            ///nokia-state/state/log/event-trigger/li/entry/statistics/error-filter
                            leaf error-filter {
                                type yang:counter32;
                                description
                                    "Indicates the number of times the logger event will be ignored due to filter
                                     is not operational or is not configured in EHS trigger entry.";
                            }

                            ///nokia-state/state/log/event-trigger/li/entry/statistics/error-handler
                            leaf error-handler {
                                type yang:counter32;
                                description
                                    "Indicates the number of times the logger event will be ignored due to handler
                                     is not operational or is not configured in EHS trigger entry.";
                            }

                            ///nokia-state/state/log/event-trigger/li/entry/statistics/trigger-count
                            leaf trigger-count {
                                type yang:counter32;
                                description
                                    "Indicates the number of times script execution is triggered after filter match
                                     for the specified trigger entry.";
                            }

                            ///nokia-state/state/log/event-trigger/li/entry/statistics/debounce-count
                            leaf debounce-count {
                                type yang:counter32;
                                description
                                    "Indicates the number of times script is not executed due to debounce rule
                                     for the specified trigger entry.";
                            }

                        } // container statistics

                    } // list entry

                } // list li

                ///nokia-state/state/log/event-trigger/lldp
                list lldp {
                    key "event";
                    description "Enter the lldp list instance";

                    ///nokia-state/state/log/event-trigger/lldp/event
                    leaf event {
                        type types-log:lldp-events;
                        description "Log event as a trigger for one or more EHS handlers";
                    }

                    ///nokia-state/state/log/event-trigger/lldp/oper-state
                    leaf oper-state {
                        type types-sros:oper-state;
                        description "Indicates the operational state of the EHS Event Trigger.";
                    }

                    ///nokia-state/state/log/event-trigger/lldp/statistics
                    container statistics {
                        description "Enter the statistics context";

                        ///nokia-state/state/log/event-trigger/lldp/statistics/success
                        leaf success {
                            type yang:counter32;
                            description
                                "Indicates the number of not ignored logger event occurrences
                                 associated with EHS trigger.";
                        }

                        ///nokia-state/state/log/event-trigger/lldp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/lldp/statistics/error-admin-state
                        leaf error-admin-state {
                            type yang:counter32;
                            description
                                "Indicates the number of ignored logger event occurrences associated
                                 with EHS trigger.

                                 Event is ignored due to trigger may be out-of-service.";
                        }

                        ///nokia-state/state/log/event-trigger/lldp/statistics/total
                        leaf total {
                            type yang:counter32;
                            description "Sum of success + error-no-entry + error-admin-state.";
                        }

                    } // container statistics

                    ///nokia-state/state/log/event-trigger/lldp/summary-entry-statistics
                    container summary-entry-statistics {
                        description "Enter the summary-entry-statistics context";

                        ///nokia-state/state/log/event-trigger/lldp/summary-entry-statistics/filter-match
                        leaf filter-match {
                            type yang:counter32;
                            description "Indicates the number of times a filter matches an logger event.";
                        }

                        ///nokia-state/state/log/event-trigger/lldp/summary-entry-statistics/filter-fail
                        leaf filter-fail {
                            type yang:counter32;
                            description "Indicates the number of times a filter does not match an logger event.";
                        }

                        ///nokia-state/state/log/event-trigger/lldp/summary-entry-statistics/error-admin-state
                        leaf error-admin-state {
                            type yang:counter32;
                            description
                                "Indicates the number of times the logger event will be ignored due to
                                 admin state of EHS trigger entries is out-of-service.";
                        }

                        ///nokia-state/state/log/event-trigger/lldp/summary-entry-statistics/error-filter
                        leaf error-filter {
                            type yang:counter32;
                            description
                                "Indicates the number of times the logger event will be ignored due to filter
                                 is not operational or is not configured in EHS trigger entries.";
                        }

                        ///nokia-state/state/log/event-trigger/lldp/summary-entry-statistics/error-handler
                        leaf error-handler {
                            type yang:counter32;
                            description
                                "Indicates the number of times the logger event will be ignored due to handler
                                 is not operational or is not configured in EHS trigger entries.";
                        }

                        ///nokia-state/state/log/event-trigger/lldp/summary-entry-statistics/trigger-count
                        leaf trigger-count {
                            type yang:counter32;
                            description "Indicates the number of times script execution is triggered after filter match.";
                        }

                        ///nokia-state/state/log/event-trigger/lldp/summary-entry-statistics/debounce-count
                        leaf debounce-count {
                            type yang:counter32;
                            description "Indicates the number of times script is not executed due to debounce rule.";
                        }

                    } // container summary-entry-statistics

                    ///nokia-state/state/log/event-trigger/lldp/entry
                    list entry {
                        key "id";
                        description "Enter the entry list instance";

                        ///nokia-state/state/log/event-trigger/lldp/entry/id
                        leaf id {
                            type uint32 {
                                range "1..1500";
                            }
                            description "ID of the EHS event trigger entry";
                        }

                        ///nokia-state/state/log/event-trigger/lldp/entry/oper-state
                        leaf oper-state {
                            type types-sros:oper-state;
                            description "Indicates the operational state of the EHS Event Trigger Entry.";
                        }

                        ///nokia-state/state/log/event-trigger/lldp/entry/statistics
                        container statistics {
                            description "Enter the statistics context";

                            ///nokia-state/state/log/event-trigger/lldp/entry/statistics/filter-match
                            leaf filter-match {
                                type yang:counter32;
                                description
                                    "Indicates the number of times a filter, for the specified trigger entry,
                                     matches an logger event.";
                            }

                            ///nokia-state/state/log/event-trigger/lldp/entry/statistics/filter-fail
                            leaf filter-fail {
                                type yang:counter32;
                                description
                                    "Indicates the number of times a filter, for the specified trigger entry,
                                     does not match an logger event.";
                            }

                            ///nokia-state/state/log/event-trigger/lldp/entry/statistics/error-admin-state
                            leaf error-admin-state {
                                type yang:counter32;
                                description
                                    "Indicates the number of times the logger event will be ignored due to
                                     admin state of EHS trigger entry is out-of-service.";
                            }

                            ///nokia-state/state/log/event-trigger/lldp/entry/statistics/error-filter
                            leaf error-filter {
                                type yang:counter32;
                                description
                                    "Indicates the number of times the logger event will be ignored due to filter
                                     is not operational or is not configured in EHS trigger entry.";
                            }

                            ///nokia-state/state/log/event-trigger/lldp/entry/statistics/error-handler
                            leaf error-handler {
                                type yang:counter32;
                                description
                                    "Indicates the number of times the logger event will be ignored due to handler
                                     is not operational or is not configured in EHS trigger entry.";
                            }

                            ///nokia-state/state/log/event-trigger/lldp/entry/statistics/trigger-count
                            leaf trigger-count {
                                type yang:counter32;
                                description
                                    "Indicates the number of times script execution is triggered after filter match
                                     for the specified trigger entry.";
                            }

                            ///nokia-state/state/log/event-trigger/lldp/entry/statistics/debounce-count
                            leaf debounce-count {
                                type yang:counter32;
                                description
                                    "Indicates the number of times script is not executed due to debounce rule
                                     for the specified trigger entry.";
                            }

                        } // container statistics

                    } // list entry

                } // list lldp

                ///nokia-state/state/log/event-trigger/logger
                list logger {
                    key "event";
                    description "Enter the logger list instance";

                    ///nokia-state/state/log/event-trigger/logger/event
                    leaf event {
                        type types-log:logger-events;
                        description "Log event as a trigger for one or more EHS handlers";
                    }

                    ///nokia-state/state/log/event-trigger/logger/oper-state
                    leaf oper-state {
                        type types-sros:oper-state;
                        description "Indicates the operational state of the EHS Event Trigger.";
                    }

                    ///nokia-state/state/log/event-trigger/logger/statistics
                    container statistics {
                        description "Enter the statistics context";

                        ///nokia-state/state/log/event-trigger/logger/statistics/success
                        leaf success {
                            type yang:counter32;
                            description
                                "Indicates the number of not ignored logger event occurrences
                                 associated with EHS trigger.";
                        }

                        ///nokia-state/state/log/event-trigger/logger/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/logger/statistics/error-admin-state
                        leaf error-admin-state {
                            type yang:counter32;
                            description
                                "Indicates the number of ignored logger event occurrences associated
                                 with EHS trigger.

                                 Event is ignored due to trigger may be out-of-service.";
                        }

                        ///nokia-state/state/log/event-trigger/logger/statistics/total
                        leaf total {
                            type yang:counter32;
                            description "Sum of success + error-no-entry + error-admin-state.";
                        }

                    } // container statistics

                    ///nokia-state/state/log/event-trigger/logger/summary-entry-statistics
                    container summary-entry-statistics {
                        description "Enter the summary-entry-statistics context";

                        ///nokia-state/state/log/event-trigger/logger/summary-entry-statistics/filter-match
                        leaf filter-match {
                            type yang:counter32;
                            description "Indicates the number of times a filter matches an logger event.";
                        }

                        ///nokia-state/state/log/event-trigger/logger/summary-entry-statistics/filter-fail
                        leaf filter-fail {
                            type yang:counter32;
                            description "Indicates the number of times a filter does not match an logger event.";
                        }

                        ///nokia-state/state/log/event-trigger/logger/summary-entry-statistics/error-admin-state
                        leaf error-admin-state {
                            type yang:counter32;
                            description
                                "Indicates the number of times the logger event will be ignored due to
                                 admin state of EHS trigger entries is out-of-service.";
                        }

                        ///nokia-state/state/log/event-trigger/logger/summary-entry-statistics/error-filter
                        leaf error-filter {
                            type yang:counter32;
                            description
                                "Indicates the number of times the logger event will be ignored due to filter
                                 is not operational or is not configured in EHS trigger entries.";
                        }

                        ///nokia-state/state/log/event-trigger/logger/summary-entry-statistics/error-handler
                        leaf error-handler {
                            type yang:counter32;
                            description
                                "Indicates the number of times the logger event will be ignored due to handler
                                 is not operational or is not configured in EHS trigger entries.";
                        }

                        ///nokia-state/state/log/event-trigger/logger/summary-entry-statistics/trigger-count
                        leaf trigger-count {
                            type yang:counter32;
                            description "Indicates the number of times script execution is triggered after filter match.";
                        }

                        ///nokia-state/state/log/event-trigger/logger/summary-entry-statistics/debounce-count
                        leaf debounce-count {
                            type yang:counter32;
                            description "Indicates the number of times script is not executed due to debounce rule.";
                        }

                    } // container summary-entry-statistics

                    ///nokia-state/state/log/event-trigger/logger/entry
                    list entry {
                        key "id";
                        description "Enter the entry list instance";

                        ///nokia-state/state/log/event-trigger/logger/entry/id
                        leaf id {
                            type uint32 {
                                range "1..1500";
                            }
                            description "ID of the EHS event trigger entry";
                        }

                        ///nokia-state/state/log/event-trigger/logger/entry/oper-state
                        leaf oper-state {
                            type types-sros:oper-state;
                            description "Indicates the operational state of the EHS Event Trigger Entry.";
                        }

                        ///nokia-state/state/log/event-trigger/logger/entry/statistics
                        container statistics {
                            description "Enter the statistics context";

                            ///nokia-state/state/log/event-trigger/logger/entry/statistics/filter-match
                            leaf filter-match {
                                type yang:counter32;
                                description
                                    "Indicates the number of times a filter, for the specified trigger entry,
                                     matches an logger event.";
                            }

                            ///nokia-state/state/log/event-trigger/logger/entry/statistics/filter-fail
                            leaf filter-fail {
                                type yang:counter32;
                                description
                                    "Indicates the number of times a filter, for the specified trigger entry,
                                     does not match an logger event.";
                            }

                            ///nokia-state/state/log/event-trigger/logger/entry/statistics/error-admin-state
                            leaf error-admin-state {
                                type yang:counter32;
                                description
                                    "Indicates the number of times the logger event will be ignored due to
                                     admin state of EHS trigger entry is out-of-service.";
                            }

                            ///nokia-state/state/log/event-trigger/logger/entry/statistics/error-filter
                            leaf error-filter {
                                type yang:counter32;
                                description
                                    "Indicates the number of times the logger event will be ignored due to filter
                                     is not operational or is not configured in EHS trigger entry.";
                            }

                            ///nokia-state/state/log/event-trigger/logger/entry/statistics/error-handler
                            leaf error-handler {
                                type yang:counter32;
                                description
                                    "Indicates the number of times the logger event will be ignored due to handler
                                     is not operational or is not configured in EHS trigger entry.";
                            }

                            ///nokia-state/state/log/event-trigger/logger/entry/statistics/trigger-count
                            leaf trigger-count {
                                type yang:counter32;
                                description
                                    "Indicates the number of times script execution is triggered after filter match
                                     for the specified trigger entry.";
                            }

                            ///nokia-state/state/log/event-trigger/logger/entry/statistics/debounce-count
                            leaf debounce-count {
                                type yang:counter32;
                                description
                                    "Indicates the number of times script is not executed due to debounce rule
                                     for the specified trigger entry.";
                            }

                        } // container statistics

                    } // list entry

                } // list logger

                ///nokia-state/state/log/event-trigger/macsec
                list macsec {
                    key "event";
                    description "Enter the macsec list instance";

                    ///nokia-state/state/log/event-trigger/macsec/event
                    leaf event {
                        type types-log:macsec-events;
                        description "Log event as a trigger for one or more EHS handlers";
                    }

                    ///nokia-state/state/log/event-trigger/macsec/oper-state
                    leaf oper-state {
                        type types-sros:oper-state;
                        description "Indicates the operational state of the EHS Event Trigger.";
                    }

                    ///nokia-state/state/log/event-trigger/macsec/statistics
                    container statistics {
                        description "Enter the statistics context";

                        ///nokia-state/state/log/event-trigger/macsec/statistics/success
                        leaf success {
                            type yang:counter32;
                            description
                                "Indicates the number of not ignored logger event occurrences
                                 associated with EHS trigger.";
                        }

                        ///nokia-state/state/log/event-trigger/macsec/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/macsec/statistics/error-admin-state
                        leaf error-admin-state {
                            type yang:counter32;
                            description
                                "Indicates the number of ignored logger event occurrences associated
                                 with EHS trigger.

                                 Event is ignored due to trigger may be out-of-service.";
                        }

                        ///nokia-state/state/log/event-trigger/macsec/statistics/total
                        leaf total {
                            type yang:counter32;
                            description "Sum of success + error-no-entry + error-admin-state.";
                        }

                    } // container statistics

                    ///nokia-state/state/log/event-trigger/macsec/summary-entry-statistics
                    container summary-entry-statistics {
                        description "Enter the summary-entry-statistics context";

                        ///nokia-state/state/log/event-trigger/macsec/summary-entry-statistics/filter-match
                        leaf filter-match {
                            type yang:counter32;
                            description "Indicates the number of times a filter matches an logger event.";
                        }

                        ///nokia-state/state/log/event-trigger/macsec/summary-entry-statistics/filter-fail
                        leaf filter-fail {
                            type yang:counter32;
                            description "Indicates the number of times a filter does not match an logger event.";
                        }

                        ///nokia-state/state/log/event-trigger/macsec/summary-entry-statistics/error-admin-state
                        leaf error-admin-state {
                            type yang:counter32;
                            description
                                "Indicates the number of times the logger event will be ignored due to
                                 admin state of EHS trigger entries is out-of-service.";
                        }

                        ///nokia-state/state/log/event-trigger/macsec/summary-entry-statistics/error-filter
                        leaf error-filter {
                            type yang:counter32;
                            description
                                "Indicates the number of times the logger event will be ignored due to filter
                                 is not operational or is not configured in EHS trigger entries.";
                        }

                        ///nokia-state/state/log/event-trigger/macsec/summary-entry-statistics/error-handler
                        leaf error-handler {
                            type yang:counter32;
                            description
                                "Indicates the number of times the logger event will be ignored due to handler
                                 is not operational or is not configured in EHS trigger entries.";
                        }

                        ///nokia-state/state/log/event-trigger/macsec/summary-entry-statistics/trigger-count
                        leaf trigger-count {
                            type yang:counter32;
                            description "Indicates the number of times script execution is triggered after filter match.";
                        }

                        ///nokia-state/state/log/event-trigger/macsec/summary-entry-statistics/debounce-count
                        leaf debounce-count {
                            type yang:counter32;
                            description "Indicates the number of times script is not executed due to debounce rule.";
                        }

                    } // container summary-entry-statistics

                    ///nokia-state/state/log/event-trigger/macsec/entry
                    list entry {
                        key "id";
                        description "Enter the entry list instance";

                        ///nokia-state/state/log/event-trigger/macsec/entry/id
                        leaf id {
                            type uint32 {
                                range "1..1500";
                            }
                            description "ID of the EHS event trigger entry";
                        }

                        ///nokia-state/state/log/event-trigger/macsec/entry/oper-state
                        leaf oper-state {
                            type types-sros:oper-state;
                            description "Indicates the operational state of the EHS Event Trigger Entry.";
                        }

                        ///nokia-state/state/log/event-trigger/macsec/entry/statistics
                        container statistics {
                            description "Enter the statistics context";

                            ///nokia-state/state/log/event-trigger/macsec/entry/statistics/filter-match
                            leaf filter-match {
                                type yang:counter32;
                                description
                                    "Indicates the number of times a filter, for the specified trigger entry,
                                     matches an logger event.";
                            }

                            ///nokia-state/state/log/event-trigger/macsec/entry/statistics/filter-fail
                            leaf filter-fail {
                                type yang:counter32;
                                description
                                    "Indicates the number of times a filter, for the specified trigger entry,
                                     does not match an logger event.";
                            }

                            ///nokia-state/state/log/event-trigger/macsec/entry/statistics/error-admin-state
                            leaf error-admin-state {
                                type yang:counter32;
                                description
                                    "Indicates the number of times the logger event will be ignored due to
                                     admin state of EHS trigger entry is out-of-service.";
                            }

                            ///nokia-state/state/log/event-trigger/macsec/entry/statistics/error-filter
                            leaf error-filter {
                                type yang:counter32;
                                description
                                    "Indicates the number of times the logger event will be ignored due to filter
                                     is not operational or is not configured in EHS trigger entry.";
                            }

                            ///nokia-state/state/log/event-trigger/macsec/entry/statistics/error-handler
                            leaf error-handler {
                                type yang:counter32;
                                description
                                    "Indicates the number of times the logger event will be ignored due to handler
                                     is not operational or is not configured in EHS trigger entry.";
                            }

                            ///nokia-state/state/log/event-trigger/macsec/entry/statistics/trigger-count
                            leaf trigger-count {
                                type yang:counter32;
                                description
                                    "Indicates the number of times script execution is triggered after filter match
                                     for the specified trigger entry.";
                            }

                            ///nokia-state/state/log/event-trigger/macsec/entry/statistics/debounce-count
                            leaf debounce-count {
                                type yang:counter32;
                                description
                                    "Indicates the number of times script is not executed due to debounce rule
                                     for the specified trigger entry.";
                            }

                        } // container statistics

                    } // list entry

                } // list macsec

                ///nokia-state/state/log/event-trigger/mcpath
                list mcpath {
                    key "event";
                    description "Enter the mcpath list instance";

                    ///nokia-state/state/log/event-trigger/mcpath/event
                    leaf event {
                        type types-log:mcpath-events;
                        description "Log event as a trigger for one or more EHS handlers";
                    }

                    ///nokia-state/state/log/event-trigger/mcpath/oper-state
                    leaf oper-state {
                        type types-sros:oper-state;
                        description "Indicates the operational state of the EHS Event Trigger.";
                    }

                    ///nokia-state/state/log/event-trigger/mcpath/statistics
                    container statistics {
                        description "Enter the statistics context";

                        ///nokia-state/state/log/event-trigger/mcpath/statistics/success
                        leaf success {
                            type yang:counter32;
                            description
                                "Indicates the number of not ignored logger event occurrences
                                 associated with EHS trigger.";
                        }

                        ///nokia-state/state/log/event-trigger/mcpath/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mcpath/statistics/error-admin-state
                        leaf error-admin-state {
                            type yang:counter32;
                            description
                                "Indicates the number of ignored logger event occurrences associated
                                 with EHS trigger.

                                 Event is ignored due to trigger may be out-of-service.";
                        }

                        ///nokia-state/state/log/event-trigger/mcpath/statistics/total
                        leaf total {
                            type yang:counter32;
                            description "Sum of success + error-no-entry + error-admin-state.";
                        }

                    } // container statistics

                    ///nokia-state/state/log/event-trigger/mcpath/summary-entry-statistics
                    container summary-entry-statistics {
                        description "Enter the summary-entry-statistics context";

                        ///nokia-state/state/log/event-trigger/mcpath/summary-entry-statistics/filter-match
                        leaf filter-match {
                            type yang:counter32;
                            description "Indicates the number of times a filter matches an logger event.";
                        }

                        ///nokia-state/state/log/event-trigger/mcpath/summary-entry-statistics/filter-fail
                        leaf filter-fail {
                            type yang:counter32;
                            description "Indicates the number of times a filter does not match an logger event.";
                        }

                        ///nokia-state/state/log/event-trigger/mcpath/summary-entry-statistics/error-admin-state
                        leaf error-admin-state {
                            type yang:counter32;
                            description
                                "Indicates the number of times the logger event will be ignored due to
                                 admin state of EHS trigger entries is out-of-service.";
                        }

                        ///nokia-state/state/log/event-trigger/mcpath/summary-entry-statistics/error-filter
                        leaf error-filter {
                            type yang:counter32;
                            description
                                "Indicates the number of times the logger event will be ignored due to filter
                                 is not operational or is not configured in EHS trigger entries.";
                        }

                        ///nokia-state/state/log/event-trigger/mcpath/summary-entry-statistics/error-handler
                        leaf error-handler {
                            type yang:counter32;
                            description
                                "Indicates the number of times the logger event will be ignored due to handler
                                 is not operational or is not configured in EHS trigger entries.";
                        }

                        ///nokia-state/state/log/event-trigger/mcpath/summary-entry-statistics/trigger-count
                        leaf trigger-count {
                            type yang:counter32;
                            description "Indicates the number of times script execution is triggered after filter match.";
                        }

                        ///nokia-state/state/log/event-trigger/mcpath/summary-entry-statistics/debounce-count
                        leaf debounce-count {
                            type yang:counter32;
                            description "Indicates the number of times script is not executed due to debounce rule.";
                        }

                    } // container summary-entry-statistics

                    ///nokia-state/state/log/event-trigger/mcpath/entry
                    list entry {
                        key "id";
                        description "Enter the entry list instance";

                        ///nokia-state/state/log/event-trigger/mcpath/entry/id
                        leaf id {
                            type uint32 {
                                range "1..1500";
                            }
                            description "ID of the EHS event trigger entry";
                        }

                        ///nokia-state/state/log/event-trigger/mcpath/entry/oper-state
                        leaf oper-state {
                            type types-sros:oper-state;
                            description "Indicates the operational state of the EHS Event Trigger Entry.";
                        }

                        ///nokia-state/state/log/event-trigger/mcpath/entry/statistics
                        container statistics {
                            description "Enter the statistics context";

                            ///nokia-state/state/log/event-trigger/mcpath/entry/statistics/filter-match
                            leaf filter-match {
                                type yang:counter32;
                                description
                                    "Indicates the number of times a filter, for the specified trigger entry,
                                     matches an logger event.";
                            }

                            ///nokia-state/state/log/event-trigger/mcpath/entry/statistics/filter-fail
                            leaf filter-fail {
                                type yang:counter32;
                                description
                                    "Indicates the number of times a filter, for the specified trigger entry,
                                     does not match an logger event.";
                            }

                            ///nokia-state/state/log/event-trigger/mcpath/entry/statistics/error-admin-state
                            leaf error-admin-state {
                                type yang:counter32;
                                description
                                    "Indicates the number of times the logger event will be ignored due to
                                     admin state of EHS trigger entry is out-of-service.";
                            }

                            ///nokia-state/state/log/event-trigger/mcpath/entry/statistics/error-filter
                            leaf error-filter {
                                type yang:counter32;
                                description
                                    "Indicates the number of times the logger event will be ignored due to filter
                                     is not operational or is not configured in EHS trigger entry.";
                            }

                            ///nokia-state/state/log/event-trigger/mcpath/entry/statistics/error-handler
                            leaf error-handler {
                                type yang:counter32;
                                description
                                    "Indicates the number of times the logger event will be ignored due to handler
                                     is not operational or is not configured in EHS trigger entry.";
                            }

                            ///nokia-state/state/log/event-trigger/mcpath/entry/statistics/trigger-count
                            leaf trigger-count {
                                type yang:counter32;
                                description
                                    "Indicates the number of times script execution is triggered after filter match
                                     for the specified trigger entry.";
                            }

                            ///nokia-state/state/log/event-trigger/mcpath/entry/statistics/debounce-count
                            leaf debounce-count {
                                type yang:counter32;
                                description
                                    "Indicates the number of times script is not executed due to debounce rule
                                     for the specified trigger entry.";
                            }

                        } // container statistics

                    } // list entry

                } // list mcpath

                ///nokia-state/state/log/event-trigger/mc-redundancy
                list mc-redundancy {
                    key "event";
                    description "Enter the mc-redundancy list instance";

                    ///nokia-state/state/log/event-trigger/mc-redundancy/event
                    leaf event {
                        type types-log:mc-redundancy-events;
                        description "Log event as a trigger for one or more EHS handlers";
                    }

                    ///nokia-state/state/log/event-trigger/mc-redundancy/oper-state
                    leaf oper-state {
                        type types-sros:oper-state;
                        description "Indicates the operational state of the EHS Event Trigger.";
                    }

                    ///nokia-state/state/log/event-trigger/mc-redundancy/statistics
                    container statistics {
                        description "Enter the statistics context";

                        ///nokia-state/state/log/event-trigger/mc-redundancy/statistics/success
                        leaf success {
                            type yang:counter32;
                            description
                                "Indicates the number of not ignored logger event occurrences
                                 associated with EHS trigger.";
                        }

                        ///nokia-state/state/log/event-trigger/mc-redundancy/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mc-redundancy/statistics/error-admin-state
                        leaf error-admin-state {
                            type yang:counter32;
                            description
                                "Indicates the number of ignored logger event occurrences associated
                                 with EHS trigger.

                                 Event is ignored due to trigger may be out-of-service.";
                        }

                        ///nokia-state/state/log/event-trigger/mc-redundancy/statistics/total
                        leaf total {
                            type yang:counter32;
                            description "Sum of success + error-no-entry + error-admin-state.";
                        }

                    } // container statistics

                    ///nokia-state/state/log/event-trigger/mc-redundancy/summary-entry-statistics
                    container summary-entry-statistics {
                        description "Enter the summary-entry-statistics context";

                        ///nokia-state/state/log/event-trigger/mc-redundancy/summary-entry-statistics/filter-match
                        leaf filter-match {
                            type yang:counter32;
                            description "Indicates the number of times a filter matches an logger event.";
                        }

                        ///nokia-state/state/log/event-trigger/mc-redundancy/summary-entry-statistics/filter-fail
                        leaf filter-fail {
                            type yang:counter32;
                            description "Indicates the number of times a filter does not match an logger event.";
                        }

                        ///nokia-state/state/log/event-trigger/mc-redundancy/summary-entry-statistics/error-admin-state
                        leaf error-admin-state {
                            type yang:counter32;
                            description
                                "Indicates the number of times the logger event will be ignored due to
                                 admin state of EHS trigger entries is out-of-service.";
                        }

                        ///nokia-state/state/log/event-trigger/mc-redundancy/summary-entry-statistics/error-filter
                        leaf error-filter {
                            type yang:counter32;
                            description
                                "Indicates the number of times the logger event will be ignored due to filter
                                 is not operational or is not configured in EHS trigger entries.";
                        }

                        ///nokia-state/state/log/event-trigger/mc-redundancy/summary-entry-statistics/error-handler
                        leaf error-handler {
                            type yang:counter32;
                            description
                                "Indicates the number of times the logger event will be ignored due to handler
                                 is not operational or is not configured in EHS trigger entries.";
                        }

                        ///nokia-state/state/log/event-trigger/mc-redundancy/summary-entry-statistics/trigger-count
                        leaf trigger-count {
                            type yang:counter32;
                            description "Indicates the number of times script execution is triggered after filter match.";
                        }

                        ///nokia-state/state/log/event-trigger/mc-redundancy/summary-entry-statistics/debounce-count
                        leaf debounce-count {
                            type yang:counter32;
                            description "Indicates the number of times script is not executed due to debounce rule.";
                        }

                    } // container summary-entry-statistics

                    ///nokia-state/state/log/event-trigger/mc-redundancy/entry
                    list entry {
                        key "id";
                        description "Enter the entry list instance";

                        ///nokia-state/state/log/event-trigger/mc-redundancy/entry/id
                        leaf id {
                            type uint32 {
                                range "1..1500";
                            }
                            description "ID of the EHS event trigger entry";
                        }

                        ///nokia-state/state/log/event-trigger/mc-redundancy/entry/oper-state
                        leaf oper-state {
                            type types-sros:oper-state;
                            description "Indicates the operational state of the EHS Event Trigger Entry.";
                        }

                        ///nokia-state/state/log/event-trigger/mc-redundancy/entry/statistics
                        container statistics {
                            description "Enter the statistics context";

                            ///nokia-state/state/log/event-trigger/mc-redundancy/entry/statistics/filter-match
                            leaf filter-match {
                                type yang:counter32;
                                description
                                    "Indicates the number of times a filter, for the specified trigger entry,
                                     matches an logger event.";
                            }

                            ///nokia-state/state/log/event-trigger/mc-redundancy/entry/statistics/filter-fail
                            leaf filter-fail {
                                type yang:counter32;
                                description
                                    "Indicates the number of times a filter, for the specified trigger entry,
                                     does not match an logger event.";
                            }

                            ///nokia-state/state/log/event-trigger/mc-redundancy/entry/statistics/error-admin-state
                            leaf error-admin-state {
                                type yang:counter32;
                                description
                                    "Indicates the number of times the logger event will be ignored due to
                                     admin state of EHS trigger entry is out-of-service.";
                            }

                            ///nokia-state/state/log/event-trigger/mc-redundancy/entry/statistics/error-filter
                            leaf error-filter {
                                type yang:counter32;
                                description
                                    "Indicates the number of times the logger event will be ignored due to filter
                                     is not operational or is not configured in EHS trigger entry.";
                            }

                            ///nokia-state/state/log/event-trigger/mc-redundancy/entry/statistics/error-handler
                            leaf error-handler {
                                type yang:counter32;
                                description
                                    "Indicates the number of times the logger event will be ignored due to handler
                                     is not operational or is not configured in EHS trigger entry.";
                            }

                            ///nokia-state/state/log/event-trigger/mc-redundancy/entry/statistics/trigger-count
                            leaf trigger-count {
                                type yang:counter32;
                                description
                                    "Indicates the number of times script execution is triggered after filter match
                                     for the specified trigger entry.";
                            }

                            ///nokia-state/state/log/event-trigger/mc-redundancy/entry/statistics/debounce-count
                            leaf debounce-count {
                                type yang:counter32;
                                description
                                    "Indicates the number of times script is not executed due to debounce rule
                                     for the specified trigger entry.";
                            }

                        } // container statistics

                    } // list entry

                } // list mc-redundancy

                ///nokia-state/state/log/event-trigger/mgmt-core
                list mgmt-core {
                    key "event";
                    description "Enter the mgmt-core list instance";

                    ///nokia-state/state/log/event-trigger/mgmt-core/event
                    leaf event {
                        type types-log:mgmt-core-events;
                        description "Log event as a trigger for one or more EHS handlers";
                    }

                    ///nokia-state/state/log/event-trigger/mgmt-core/oper-state
                    leaf oper-state {
                        type types-sros:oper-state;
                        description "Indicates the operational state of the EHS Event Trigger.";
                    }

                    ///nokia-state/state/log/event-trigger/mgmt-core/statistics
                    container statistics {
                        description "Enter the statistics context";

                        ///nokia-state/state/log/event-trigger/mgmt-core/statistics/success
                        leaf success {
                            type yang:counter32;
                            description
                                "Indicates the number of not ignored logger event occurrences
                                 associated with EHS trigger.";
                        }

                        ///nokia-state/state/log/event-trigger/mgmt-core/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mgmt-core/statistics/error-admin-state
                        leaf error-admin-state {
                            type yang:counter32;
                            description
                                "Indicates the number of ignored logger event occurrences associated
                                 with EHS trigger.

                                 Event is ignored due to trigger may be out-of-service.";
                        }

                        ///nokia-state/state/log/event-trigger/mgmt-core/statistics/total
                        leaf total {
                            type yang:counter32;
                            description "Sum of success + error-no-entry + error-admin-state.";
                        }

                    } // container statistics

                    ///nokia-state/state/log/event-trigger/mgmt-core/summary-entry-statistics
                    container summary-entry-statistics {
                        description "Enter the summary-entry-statistics context";

                        ///nokia-state/state/log/event-trigger/mgmt-core/summary-entry-statistics/filter-match
                        leaf filter-match {
                            type yang:counter32;
                            description "Indicates the number of times a filter matches an logger event.";
                        }

                        ///nokia-state/state/log/event-trigger/mgmt-core/summary-entry-statistics/filter-fail
                        leaf filter-fail {
                            type yang:counter32;
                            description "Indicates the number of times a filter does not match an logger event.";
                        }

                        ///nokia-state/state/log/event-trigger/mgmt-core/summary-entry-statistics/error-admin-state
                        leaf error-admin-state {
                            type yang:counter32;
                            description
                                "Indicates the number of times the logger event will be ignored due to
                                 admin state of EHS trigger entries is out-of-service.";
                        }

                        ///nokia-state/state/log/event-trigger/mgmt-core/summary-entry-statistics/error-filter
                        leaf error-filter {
                            type yang:counter32;
                            description
                                "Indicates the number of times the logger event will be ignored due to filter
                                 is not operational or is not configured in EHS trigger entries.";
                        }

                        ///nokia-state/state/log/event-trigger/mgmt-core/summary-entry-statistics/error-handler
                        leaf error-handler {
                            type yang:counter32;
                            description
                                "Indicates the number of times the logger event will be ignored due to handler
                                 is not operational or is not configured in EHS trigger entries.";
                        }

                        ///nokia-state/state/log/event-trigger/mgmt-core/summary-entry-statistics/trigger-count
                        leaf trigger-count {
                            type yang:counter32;
                            description "Indicates the number of times script execution is triggered after filter match.";
                        }

                        ///nokia-state/state/log/event-trigger/mgmt-core/summary-entry-statistics/debounce-count
                        leaf debounce-count {
                            type yang:counter32;
                            description "Indicates the number of times script is not executed due to debounce rule.";
                        }

                    } // container summary-entry-statistics

                    ///nokia-state/state/log/event-trigger/mgmt-core/entry
                    list entry {
                        key "id";
                        description "Enter the entry list instance";

                        ///nokia-state/state/log/event-trigger/mgmt-core/entry/id
                        leaf id {
                            type uint32 {
                                range "1..1500";
                            }
                            description "ID of the EHS event trigger entry";
                        }

                        ///nokia-state/state/log/event-trigger/mgmt-core/entry/oper-state
                        leaf oper-state {
                            type types-sros:oper-state;
                            description "Indicates the operational state of the EHS Event Trigger Entry.";
                        }

                        ///nokia-state/state/log/event-trigger/mgmt-core/entry/statistics
                        container statistics {
                            description "Enter the statistics context";

                            ///nokia-state/state/log/event-trigger/mgmt-core/entry/statistics/filter-match
                            leaf filter-match {
                                type yang:counter32;
                                description
                                    "Indicates the number of times a filter, for the specified trigger entry,
                                     matches an logger event.";
                            }

                            ///nokia-state/state/log/event-trigger/mgmt-core/entry/statistics/filter-fail
                            leaf filter-fail {
                                type yang:counter32;
                                description
                                    "Indicates the number of times a filter, for the specified trigger entry,
                                     does not match an logger event.";
                            }

                            ///nokia-state/state/log/event-trigger/mgmt-core/entry/statistics/error-admin-state
                            leaf error-admin-state {
                                type yang:counter32;
                                description
                                    "Indicates the number of times the logger event will be ignored due to
                                     admin state of EHS trigger entry is out-of-service.";
                            }

                            ///nokia-state/state/log/event-trigger/mgmt-core/entry/statistics/error-filter
                            leaf error-filter {
                                type yang:counter32;
                                description
                                    "Indicates the number of times the logger event will be ignored due to filter
                                     is not operational or is not configured in EHS trigger entry.";
                            }

                            ///nokia-state/state/log/event-trigger/mgmt-core/entry/statistics/error-handler
                            leaf error-handler {
                                type yang:counter32;
                                description
                                    "Indicates the number of times the logger event will be ignored due to handler
                                     is not operational or is not configured in EHS trigger entry.";
                            }

                            ///nokia-state/state/log/event-trigger/mgmt-core/entry/statistics/trigger-count
                            leaf trigger-count {
                                type yang:counter32;
                                description
                                    "Indicates the number of times script execution is triggered after filter match
                                     for the specified trigger entry.";
                            }

                            ///nokia-state/state/log/event-trigger/mgmt-core/entry/statistics/debounce-count
                            leaf debounce-count {
                                type yang:counter32;
                                description
                                    "Indicates the number of times script is not executed due to debounce rule
                                     for the specified trigger entry.";
                            }

                        } // container statistics

                    } // list entry

                } // list mgmt-core

                ///nokia-state/state/log/event-trigger/mirror
                list mirror {
                    key "event";
                    description "Enter the mirror list instance";

                    ///nokia-state/state/log/event-trigger/mirror/event
                    leaf event {
                        type types-log:mirror-events;
                        description "Log event as a trigger for one or more EHS handlers";
                    }

                    ///nokia-state/state/log/event-trigger/mirror/oper-state
                    leaf oper-state {
                        type types-sros:oper-state;
                        description "Indicates the operational state of the EHS Event Trigger.";
                    }

                    ///nokia-state/state/log/event-trigger/mirror/statistics
                    container statistics {
                        description "Enter the statistics context";

                        ///nokia-state/state/log/event-trigger/mirror/statistics/success
                        leaf success {
                            type yang:counter32;
                            description
                                "Indicates the number of not ignored logger event occurrences
                                 associated with EHS trigger.";
                        }

                        ///nokia-state/state/log/event-trigger/mirror/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mirror/statistics/error-admin-state
                        leaf error-admin-state {
                            type yang:counter32;
                            description
                                "Indicates the number of ignored logger event occurrences associated
                                 with EHS trigger.

                                 Event is ignored due to trigger may be out-of-service.";
                        }

                        ///nokia-state/state/log/event-trigger/mirror/statistics/total
                        leaf total {
                            type yang:counter32;
                            description "Sum of success + error-no-entry + error-admin-state.";
                        }

                    } // container statistics

                    ///nokia-state/state/log/event-trigger/mirror/summary-entry-statistics
                    container summary-entry-statistics {
                        description "Enter the summary-entry-statistics context";

                        ///nokia-state/state/log/event-trigger/mirror/summary-entry-statistics/filter-match
                        leaf filter-match {
                            type yang:counter32;
                            description "Indicates the number of times a filter matches an logger event.";
                        }

                        ///nokia-state/state/log/event-trigger/mirror/summary-entry-statistics/filter-fail
                        leaf filter-fail {
                            type yang:counter32;
                            description "Indicates the number of times a filter does not match an logger event.";
                        }

                        ///nokia-state/state/log/event-trigger/mirror/summary-entry-statistics/error-admin-state
                        leaf error-admin-state {
                            type yang:counter32;
                            description
                                "Indicates the number of times the logger event will be ignored due to
                                 admin state of EHS trigger entries is out-of-service.";
                        }

                        ///nokia-state/state/log/event-trigger/mirror/summary-entry-statistics/error-filter
                        leaf error-filter {
                            type yang:counter32;
                            description
                                "Indicates the number of times the logger event will be ignored due to filter
                                 is not operational or is not configured in EHS trigger entries.";
                        }

                        ///nokia-state/state/log/event-trigger/mirror/summary-entry-statistics/error-handler
                        leaf error-handler {
                            type yang:counter32;
                            description
                                "Indicates the number of times the logger event will be ignored due to handler
                                 is not operational or is not configured in EHS trigger entries.";
                        }

                        ///nokia-state/state/log/event-trigger/mirror/summary-entry-statistics/trigger-count
                        leaf trigger-count {
                            type yang:counter32;
                            description "Indicates the number of times script execution is triggered after filter match.";
                        }

                        ///nokia-state/state/log/event-trigger/mirror/summary-entry-statistics/debounce-count
                        leaf debounce-count {
                            type yang:counter32;
                            description "Indicates the number of times script is not executed due to debounce rule.";
                        }

                    } // container summary-entry-statistics

                    ///nokia-state/state/log/event-trigger/mirror/entry
                    list entry {
                        key "id";
                        description "Enter the entry list instance";

                        ///nokia-state/state/log/event-trigger/mirror/entry/id
                        leaf id {
                            type uint32 {
                                range "1..1500";
                            }
                            description "ID of the EHS event trigger entry";
                        }

                        ///nokia-state/state/log/event-trigger/mirror/entry/oper-state
                        leaf oper-state {
                            type types-sros:oper-state;
                            description "Indicates the operational state of the EHS Event Trigger Entry.";
                        }

                        ///nokia-state/state/log/event-trigger/mirror/entry/statistics
                        container statistics {
                            description "Enter the statistics context";

                            ///nokia-state/state/log/event-trigger/mirror/entry/statistics/filter-match
                            leaf filter-match {
                                type yang:counter32;
                                description
                                    "Indicates the number of times a filter, for the specified trigger entry,
                                     matches an logger event.";
                            }

                            ///nokia-state/state/log/event-trigger/mirror/entry/statistics/filter-fail
                            leaf filter-fail {
                                type yang:counter32;
                                description
                                    "Indicates the number of times a filter, for the specified trigger entry,
                                     does not match an logger event.";
                            }

                            ///nokia-state/state/log/event-trigger/mirror/entry/statistics/error-admin-state
                            leaf error-admin-state {
                                type yang:counter32;
                                description
                                    "Indicates the number of times the logger event will be ignored due to
                                     admin state of EHS trigger entry is out-of-service.";
                            }

                            ///nokia-state/state/log/event-trigger/mirror/entry/statistics/error-filter
                            leaf error-filter {
                                type yang:counter32;
                                description
                                    "Indicates the number of times the logger event will be ignored due to filter
                                     is not operational or is not configured in EHS trigger entry.";
                            }

                            ///nokia-state/state/log/event-trigger/mirror/entry/statistics/error-handler
                            leaf error-handler {
                                type yang:counter32;
                                description
                                    "Indicates the number of times the logger event will be ignored due to handler
                                     is not operational or is not configured in EHS trigger entry.";
                            }

                            ///nokia-state/state/log/event-trigger/mirror/entry/statistics/trigger-count
                            leaf trigger-count {
                                type yang:counter32;
                                description
                                    "Indicates the number of times script execution is triggered after filter match
                                     for the specified trigger entry.";
                            }

                            ///nokia-state/state/log/event-trigger/mirror/entry/statistics/debounce-count
                            leaf debounce-count {
                                type yang:counter32;
                                description
                                    "Indicates the number of times script is not executed due to debounce rule
                                     for the specified trigger entry.";
                            }

                        } // container statistics

                    } // list entry

                } // list mirror

                ///nokia-state/state/log/event-trigger/mld
                list mld {
                    key "event";
                    description "Enter the mld list instance";

                    ///nokia-state/state/log/event-trigger/mld/event
                    leaf event {
                        type types-log:mld-events;
                        description "Log event as a trigger for one or more EHS handlers";
                    }

                    ///nokia-state/state/log/event-trigger/mld/oper-state
                    leaf oper-state {
                        type types-sros:oper-state;
                        description "Indicates the operational state of the EHS Event Trigger.";
                    }

                    ///nokia-state/state/log/event-trigger/mld/statistics
                    container statistics {
                        description "Enter the statistics context";

                        ///nokia-state/state/log/event-trigger/mld/statistics/success
                        leaf success {
                            type yang:counter32;
                            description
                                "Indicates the number of not ignored logger event occurrences
                                 associated with EHS trigger.";
                        }

                        ///nokia-state/state/log/event-trigger/mld/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mld/statistics/error-admin-state
                        leaf error-admin-state {
                            type yang:counter32;
                            description
                                "Indicates the number of ignored logger event occurrences associated
                                 with EHS trigger.

                                 Event is ignored due to trigger may be out-of-service.";
                        }

                        ///nokia-state/state/log/event-trigger/mld/statistics/total
                        leaf total {
                            type yang:counter32;
                            description "Sum of success + error-no-entry + error-admin-state.";
                        }

                    } // container statistics

                    ///nokia-state/state/log/event-trigger/mld/summary-entry-statistics
                    container summary-entry-statistics {
                        description "Enter the summary-entry-statistics context";

                        ///nokia-state/state/log/event-trigger/mld/summary-entry-statistics/filter-match
                        leaf filter-match {
                            type yang:counter32;
                            description "Indicates the number of times a filter matches an logger event.";
                        }

                        ///nokia-state/state/log/event-trigger/mld/summary-entry-statistics/filter-fail
                        leaf filter-fail {
                            type yang:counter32;
                            description "Indicates the number of times a filter does not match an logger event.";
                        }

                        ///nokia-state/state/log/event-trigger/mld/summary-entry-statistics/error-admin-state
                        leaf error-admin-state {
                            type yang:counter32;
                            description
                                "Indicates the number of times the logger event will be ignored due to
                                 admin state of EHS trigger entries is out-of-service.";
                        }

                        ///nokia-state/state/log/event-trigger/mld/summary-entry-statistics/error-filter
                        leaf error-filter {
                            type yang:counter32;
                            description
                                "Indicates the number of times the logger event will be ignored due to filter
                                 is not operational or is not configured in EHS trigger entries.";
                        }

                        ///nokia-state/state/log/event-trigger/mld/summary-entry-statistics/error-handler
                        leaf error-handler {
                            type yang:counter32;
                            description
                                "Indicates the number of times the logger event will be ignored due to handler
                                 is not operational or is not configured in EHS trigger entries.";
                        }

                        ///nokia-state/state/log/event-trigger/mld/summary-entry-statistics/trigger-count
                        leaf trigger-count {
                            type yang:counter32;
                            description "Indicates the number of times script execution is triggered after filter match.";
                        }

                        ///nokia-state/state/log/event-trigger/mld/summary-entry-statistics/debounce-count
                        leaf debounce-count {
                            type yang:counter32;
                            description "Indicates the number of times script is not executed due to debounce rule.";
                        }

                    } // container summary-entry-statistics

                    ///nokia-state/state/log/event-trigger/mld/entry
                    list entry {
                        key "id";
                        description "Enter the entry list instance";

                        ///nokia-state/state/log/event-trigger/mld/entry/id
                        leaf id {
                            type uint32 {
                                range "1..1500";
                            }
                            description "ID of the EHS event trigger entry";
                        }

                        ///nokia-state/state/log/event-trigger/mld/entry/oper-state
                        leaf oper-state {
                            type types-sros:oper-state;
                            description "Indicates the operational state of the EHS Event Trigger Entry.";
                        }

                        ///nokia-state/state/log/event-trigger/mld/entry/statistics
                        container statistics {
                            description "Enter the statistics context";

                            ///nokia-state/state/log/event-trigger/mld/entry/statistics/filter-match
                            leaf filter-match {
                                type yang:counter32;
                                description
                                    "Indicates the number of times a filter, for the specified trigger entry,
                                     matches an logger event.";
                            }

                            ///nokia-state/state/log/event-trigger/mld/entry/statistics/filter-fail
                            leaf filter-fail {
                                type yang:counter32;
                                description
                                    "Indicates the number of times a filter, for the specified trigger entry,
                                     does not match an logger event.";
                            }

                            ///nokia-state/state/log/event-trigger/mld/entry/statistics/error-admin-state
                            leaf error-admin-state {
                                type yang:counter32;
                                description
                                    "Indicates the number of times the logger event will be ignored due to
                                     admin state of EHS trigger entry is out-of-service.";
                            }

                            ///nokia-state/state/log/event-trigger/mld/entry/statistics/error-filter
                            leaf error-filter {
                                type yang:counter32;
                                description
                                    "Indicates the number of times the logger event will be ignored due to filter
                                     is not operational or is not configured in EHS trigger entry.";
                            }

                            ///nokia-state/state/log/event-trigger/mld/entry/statistics/error-handler
                            leaf error-handler {
                                type yang:counter32;
                                description
                                    "Indicates the number of times the logger event will be ignored due to handler
                                     is not operational or is not configured in EHS trigger entry.";
                            }

                            ///nokia-state/state/log/event-trigger/mld/entry/statistics/trigger-count
                            leaf trigger-count {
                                type yang:counter32;
                                description
                                    "Indicates the number of times script execution is triggered after filter match
                                     for the specified trigger entry.";
                            }

                            ///nokia-state/state/log/event-trigger/mld/entry/statistics/debounce-count
                            leaf debounce-count {
                                type yang:counter32;
                                description
                                    "Indicates the number of times script is not executed due to debounce rule
                                     for the specified trigger entry.";
                            }

                        } // container statistics

                    } // list entry

                } // list mld

                ///nokia-state/state/log/event-trigger/mld-snooping
                list mld-snooping {
                    key "event";
                    description "Enter the mld-snooping list instance";

                    ///nokia-state/state/log/event-trigger/mld-snooping/event
                    leaf event {
                        type types-log:mld-snooping-events;
                        description "Log event as a trigger for one or more EHS handlers";
                    }

                    ///nokia-state/state/log/event-trigger/mld-snooping/oper-state
                    leaf oper-state {
                        type types-sros:oper-state;
                        description "Indicates the operational state of the EHS Event Trigger.";
                    }

                    ///nokia-state/state/log/event-trigger/mld-snooping/statistics
                    container statistics {
                        description "Enter the statistics context";

                        ///nokia-state/state/log/event-trigger/mld-snooping/statistics/success
                        leaf success {
                            type yang:counter32;
                            description
                                "Indicates the number of not ignored logger event occurrences
                                 associated with EHS trigger.";
                        }

                        ///nokia-state/state/log/event-trigger/mld-snooping/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mld-snooping/statistics/error-admin-state
                        leaf error-admin-state {
                            type yang:counter32;
                            description
                                "Indicates the number of ignored logger event occurrences associated
                                 with EHS trigger.

                                 Event is ignored due to trigger may be out-of-service.";
                        }

                        ///nokia-state/state/log/event-trigger/mld-snooping/statistics/total
                        leaf total {
                            type yang:counter32;
                            description "Sum of success + error-no-entry + error-admin-state.";
                        }

                    } // container statistics

                    ///nokia-state/state/log/event-trigger/mld-snooping/summary-entry-statistics
                    container summary-entry-statistics {
                        description "Enter the summary-entry-statistics context";

                        ///nokia-state/state/log/event-trigger/mld-snooping/summary-entry-statistics/filter-match
                        leaf filter-match {
                            type yang:counter32;
                            description "Indicates the number of times a filter matches an logger event.";
                        }

                        ///nokia-state/state/log/event-trigger/mld-snooping/summary-entry-statistics/filter-fail
                        leaf filter-fail {
                            type yang:counter32;
                            description "Indicates the number of times a filter does not match an logger event.";
                        }

                        ///nokia-state/state/log/event-trigger/mld-snooping/summary-entry-statistics/error-admin-state
                        leaf error-admin-state {
                            type yang:counter32;
                            description
                                "Indicates the number of times the logger event will be ignored due to
                                 admin state of EHS trigger entries is out-of-service.";
                        }

                        ///nokia-state/state/log/event-trigger/mld-snooping/summary-entry-statistics/error-filter
                        leaf error-filter {
                            type yang:counter32;
                            description
                                "Indicates the number of times the logger event will be ignored due to filter
                                 is not operational or is not configured in EHS trigger entries.";
                        }

                        ///nokia-state/state/log/event-trigger/mld-snooping/summary-entry-statistics/error-handler
                        leaf error-handler {
                            type yang:counter32;
                            description
                                "Indicates the number of times the logger event will be ignored due to handler
                                 is not operational or is not configured in EHS trigger entries.";
                        }

                        ///nokia-state/state/log/event-trigger/mld-snooping/summary-entry-statistics/trigger-count
                        leaf trigger-count {
                            type yang:counter32;
                            description "Indicates the number of times script execution is triggered after filter match.";
                        }

                        ///nokia-state/state/log/event-trigger/mld-snooping/summary-entry-statistics/debounce-count
                        leaf debounce-count {
                            type yang:counter32;
                            description "Indicates the number of times script is not executed due to debounce rule.";
                        }

                    } // container summary-entry-statistics

                    ///nokia-state/state/log/event-trigger/mld-snooping/entry
                    list entry {
                        key "id";
                        description "Enter the entry list instance";

                        ///nokia-state/state/log/event-trigger/mld-snooping/entry/id
                        leaf id {
                            type uint32 {
                                range "1..1500";
                            }
                            description "ID of the EHS event trigger entry";
                        }

                        ///nokia-state/state/log/event-trigger/mld-snooping/entry/oper-state
                        leaf oper-state {
                            type types-sros:oper-state;
                            description "Indicates the operational state of the EHS Event Trigger Entry.";
                        }

                        ///nokia-state/state/log/event-trigger/mld-snooping/entry/statistics
                        container statistics {
                            description "Enter the statistics context";

                            ///nokia-state/state/log/event-trigger/mld-snooping/entry/statistics/filter-match
                            leaf filter-match {
                                type yang:counter32;
                                description
                                    "Indicates the number of times a filter, for the specified trigger entry,
                                     matches an logger event.";
                            }

                            ///nokia-state/state/log/event-trigger/mld-snooping/entry/statistics/filter-fail
                            leaf filter-fail {
                                type yang:counter32;
                                description
                                    "Indicates the number of times a filter, for the specified trigger entry,
                                     does not match an logger event.";
                            }

                            ///nokia-state/state/log/event-trigger/mld-snooping/entry/statistics/error-admin-state
                            leaf error-admin-state {
                                type yang:counter32;
                                description
                                    "Indicates the number of times the logger event will be ignored due to
                                     admin state of EHS trigger entry is out-of-service.";
                            }

                            ///nokia-state/state/log/event-trigger/mld-snooping/entry/statistics/error-filter
                            leaf error-filter {
                                type yang:counter32;
                                description
                                    "Indicates the number of times the logger event will be ignored due to filter
                                     is not operational or is not configured in EHS trigger entry.";
                            }

                            ///nokia-state/state/log/event-trigger/mld-snooping/entry/statistics/error-handler
                            leaf error-handler {
                                type yang:counter32;
                                description
                                    "Indicates the number of times the logger event will be ignored due to handler
                                     is not operational or is not configured in EHS trigger entry.";
                            }

                            ///nokia-state/state/log/event-trigger/mld-snooping/entry/statistics/trigger-count
                            leaf trigger-count {
                                type yang:counter32;
                                description
                                    "Indicates the number of times script execution is triggered after filter match
                                     for the specified trigger entry.";
                            }

                            ///nokia-state/state/log/event-trigger/mld-snooping/entry/statistics/debounce-count
                            leaf debounce-count {
                                type yang:counter32;
                                description
                                    "Indicates the number of times script is not executed due to debounce rule
                                     for the specified trigger entry.";
                            }

                        } // container statistics

                    } // list entry

                } // list mld-snooping

                ///nokia-state/state/log/event-trigger/mpls
                list mpls {
                    key "event";
                    description "Enter the mpls list instance";

                    ///nokia-state/state/log/event-trigger/mpls/event
                    leaf event {
                        type types-log:mpls-events;
                        description "Log event as a trigger for one or more EHS handlers";
                    }

                    ///nokia-state/state/log/event-trigger/mpls/oper-state
                    leaf oper-state {
                        type types-sros:oper-state;
                        description "Indicates the operational state of the EHS Event Trigger.";
                    }

                    ///nokia-state/state/log/event-trigger/mpls/statistics
                    container statistics {
                        description "Enter the statistics context";

                        ///nokia-state/state/log/event-trigger/mpls/statistics/success
                        leaf success {
                            type yang:counter32;
                            description
                                "Indicates the number of not ignored logger event occurrences
                                 associated with EHS trigger.";
                        }

                        ///nokia-state/state/log/event-trigger/mpls/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mpls/statistics/error-admin-state
                        leaf error-admin-state {
                            type yang:counter32;
                            description
                                "Indicates the number of ignored logger event occurrences associated
                                 with EHS trigger.

                                 Event is ignored due to trigger may be out-of-service.";
                        }

                        ///nokia-state/state/log/event-trigger/mpls/statistics/total
                        leaf total {
                            type yang:counter32;
                            description "Sum of success + error-no-entry + error-admin-state.";
                        }

                    } // container statistics

                    ///nokia-state/state/log/event-trigger/mpls/summary-entry-statistics
                    container summary-entry-statistics {
                        description "Enter the summary-entry-statistics context";

                        ///nokia-state/state/log/event-trigger/mpls/summary-entry-statistics/filter-match
                        leaf filter-match {
                            type yang:counter32;
                            description "Indicates the number of times a filter matches an logger event.";
                        }

                        ///nokia-state/state/log/event-trigger/mpls/summary-entry-statistics/filter-fail
                        leaf filter-fail {
                            type yang:counter32;
                            description "Indicates the number of times a filter does not match an logger event.";
                        }

                        ///nokia-state/state/log/event-trigger/mpls/summary-entry-statistics/error-admin-state
                        leaf error-admin-state {
                            type yang:counter32;
                            description
                                "Indicates the number of times the logger event will be ignored due to
                                 admin state of EHS trigger entries is out-of-service.";
                        }

                        ///nokia-state/state/log/event-trigger/mpls/summary-entry-statistics/error-filter
                        leaf error-filter {
                            type yang:counter32;
                            description
                                "Indicates the number of times the logger event will be ignored due to filter
                                 is not operational or is not configured in EHS trigger entries.";
                        }

                        ///nokia-state/state/log/event-trigger/mpls/summary-entry-statistics/error-handler
                        leaf error-handler {
                            type yang:counter32;
                            description
                                "Indicates the number of times the logger event will be ignored due to handler
                                 is not operational or is not configured in EHS trigger entries.";
                        }

                        ///nokia-state/state/log/event-trigger/mpls/summary-entry-statistics/trigger-count
                        leaf trigger-count {
                            type yang:counter32;
                            description "Indicates the number of times script execution is triggered after filter match.";
                        }

                        ///nokia-state/state/log/event-trigger/mpls/summary-entry-statistics/debounce-count
                        leaf debounce-count {
                            type yang:counter32;
                            description "Indicates the number of times script is not executed due to debounce rule.";
                        }

                    } // container summary-entry-statistics

                    ///nokia-state/state/log/event-trigger/mpls/entry
                    list entry {
                        key "id";
                        description "Enter the entry list instance";

                        ///nokia-state/state/log/event-trigger/mpls/entry/id
                        leaf id {
                            type uint32 {
                                range "1..1500";
                            }
                            description "ID of the EHS event trigger entry";
                        }

                        ///nokia-state/state/log/event-trigger/mpls/entry/oper-state
                        leaf oper-state {
                            type types-sros:oper-state;
                            description "Indicates the operational state of the EHS Event Trigger Entry.";
                        }

                        ///nokia-state/state/log/event-trigger/mpls/entry/statistics
                        container statistics {
                            description "Enter the statistics context";

                            ///nokia-state/state/log/event-trigger/mpls/entry/statistics/filter-match
                            leaf filter-match {
                                type yang:counter32;
                                description
                                    "Indicates the number of times a filter, for the specified trigger entry,
                                     matches an logger event.";
                            }

                            ///nokia-state/state/log/event-trigger/mpls/entry/statistics/filter-fail
                            leaf filter-fail {
                                type yang:counter32;
                                description
                                    "Indicates the number of times a filter, for the specified trigger entry,
                                     does not match an logger event.";
                            }

                            ///nokia-state/state/log/event-trigger/mpls/entry/statistics/error-admin-state
                            leaf error-admin-state {
                                type yang:counter32;
                                description
                                    "Indicates the number of times the logger event will be ignored due to
                                     admin state of EHS trigger entry is out-of-service.";
                            }

                            ///nokia-state/state/log/event-trigger/mpls/entry/statistics/error-filter
                            leaf error-filter {
                                type yang:counter32;
                                description
                                    "Indicates the number of times the logger event will be ignored due to filter
                                     is not operational or is not configured in EHS trigger entry.";
                            }

                            ///nokia-state/state/log/event-trigger/mpls/entry/statistics/error-handler
                            leaf error-handler {
                                type yang:counter32;
                                description
                                    "Indicates the number of times the logger event will be ignored due to handler
                                     is not operational or is not configured in EHS trigger entry.";
                            }

                            ///nokia-state/state/log/event-trigger/mpls/entry/statistics/trigger-count
                            leaf trigger-count {
                                type yang:counter32;
                                description
                                    "Indicates the number of times script execution is triggered after filter match
                                     for the specified trigger entry.";
                            }

                            ///nokia-state/state/log/event-trigger/mpls/entry/statistics/debounce-count
                            leaf debounce-count {
                                type yang:counter32;
                                description
                                    "Indicates the number of times script is not executed due to debounce rule
                                     for the specified trigger entry.";
                            }

                        } // container statistics

                    } // list entry

                } // list mpls

                ///nokia-state/state/log/event-trigger/mpls-tp
                list mpls-tp {
                    key "event";
                    description "Enter the mpls-tp list instance";

                    ///nokia-state/state/log/event-trigger/mpls-tp/event
                    leaf event {
                        type types-log:mpls-tp-events;
                        description "Log event as a trigger for one or more EHS handlers";
                    }

                    ///nokia-state/state/log/event-trigger/mpls-tp/oper-state
                    leaf oper-state {
                        type types-sros:oper-state;
                        description "Indicates the operational state of the EHS Event Trigger.";
                    }

                    ///nokia-state/state/log/event-trigger/mpls-tp/statistics
                    container statistics {
                        description "Enter the statistics context";

                        ///nokia-state/state/log/event-trigger/mpls-tp/statistics/success
                        leaf success {
                            type yang:counter32;
                            description
                                "Indicates the number of not ignored logger event occurrences
                                 associated with EHS trigger.";
                        }

                        ///nokia-state/state/log/event-trigger/mpls-tp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/mpls-tp/statistics/error-admin-state
                        leaf error-admin-state {
                            type yang:counter32;
                            description
                                "Indicates the number of ignored logger event occurrences associated
                                 with EHS trigger.

                                 Event is ignored due to trigger may be out-of-service.";
                        }

                        ///nokia-state/state/log/event-trigger/mpls-tp/statistics/total
                        leaf total {
                            type yang:counter32;
                            description "Sum of success + error-no-entry + error-admin-state.";
                        }

                    } // container statistics

                    ///nokia-state/state/log/event-trigger/mpls-tp/summary-entry-statistics
                    container summary-entry-statistics {
                        description "Enter the summary-entry-statistics context";

                        ///nokia-state/state/log/event-trigger/mpls-tp/summary-entry-statistics/filter-match
                        leaf filter-match {
                            type yang:counter32;
                            description "Indicates the number of times a filter matches an logger event.";
                        }

                        ///nokia-state/state/log/event-trigger/mpls-tp/summary-entry-statistics/filter-fail
                        leaf filter-fail {
                            type yang:counter32;
                            description "Indicates the number of times a filter does not match an logger event.";
                        }

                        ///nokia-state/state/log/event-trigger/mpls-tp/summary-entry-statistics/error-admin-state
                        leaf error-admin-state {
                            type yang:counter32;
                            description
                                "Indicates the number of times the logger event will be ignored due to
                                 admin state of EHS trigger entries is out-of-service.";
                        }

                        ///nokia-state/state/log/event-trigger/mpls-tp/summary-entry-statistics/error-filter
                        leaf error-filter {
                            type yang:counter32;
                            description
                                "Indicates the number of times the logger event will be ignored due to filter
                                 is not operational or is not configured in EHS trigger entries.";
                        }

                        ///nokia-state/state/log/event-trigger/mpls-tp/summary-entry-statistics/error-handler
                        leaf error-handler {
                            type yang:counter32;
                            description
                                "Indicates the number of times the logger event will be ignored due to handler
                                 is not operational or is not configured in EHS trigger entries.";
                        }

                        ///nokia-state/state/log/event-trigger/mpls-tp/summary-entry-statistics/trigger-count
                        leaf trigger-count {
                            type yang:counter32;
                            description "Indicates the number of times script execution is triggered after filter match.";
                        }

                        ///nokia-state/state/log/event-trigger/mpls-tp/summary-entry-statistics/debounce-count
                        leaf debounce-count {
                            type yang:counter32;
                            description "Indicates the number of times script is not executed due to debounce rule.";
                        }

                    } // container summary-entry-statistics

                    ///nokia-state/state/log/event-trigger/mpls-tp/entry
                    list entry {
                        key "id";
                        description "Enter the entry list instance";

                        ///nokia-state/state/log/event-trigger/mpls-tp/entry/id
                        leaf id {
                            type uint32 {
                                range "1..1500";
                            }
                            description "ID of the EHS event trigger entry";
                        }

                        ///nokia-state/state/log/event-trigger/mpls-tp/entry/oper-state
                        leaf oper-state {
                            type types-sros:oper-state;
                            description "Indicates the operational state of the EHS Event Trigger Entry.";
                        }

                        ///nokia-state/state/log/event-trigger/mpls-tp/entry/statistics
                        container statistics {
                            description "Enter the statistics context";

                            ///nokia-state/state/log/event-trigger/mpls-tp/entry/statistics/filter-match
                            leaf filter-match {
                                type yang:counter32;
                                description
                                    "Indicates the number of times a filter, for the specified trigger entry,
                                     matches an logger event.";
                            }

                            ///nokia-state/state/log/event-trigger/mpls-tp/entry/statistics/filter-fail
                            leaf filter-fail {
                                type yang:counter32;
                                description
                                    "Indicates the number of times a filter, for the specified trigger entry,
                                     does not match an logger event.";
                            }

                            ///nokia-state/state/log/event-trigger/mpls-tp/entry/statistics/error-admin-state
                            leaf error-admin-state {
                                type yang:counter32;
                                description
                                    "Indicates the number of times the logger event will be ignored due to
                                     admin state of EHS trigger entry is out-of-service.";
                            }

                            ///nokia-state/state/log/event-trigger/mpls-tp/entry/statistics/error-filter
                            leaf error-filter {
                                type yang:counter32;
                                description
                                    "Indicates the number of times the logger event will be ignored due to filter
                                     is not operational or is not configured in EHS trigger entry.";
                            }

                            ///nokia-state/state/log/event-trigger/mpls-tp/entry/statistics/error-handler
                            leaf error-handler {
                                type yang:counter32;
                                description
                                    "Indicates the number of times the logger event will be ignored due to handler
                                     is not operational or is not configured in EHS trigger entry.";
                            }

                            ///nokia-state/state/log/event-trigger/mpls-tp/entry/statistics/trigger-count
                            leaf trigger-count {
                                type yang:counter32;
                                description
                                    "Indicates the number of times script execution is triggered after filter match
                                     for the specified trigger entry.";
                            }

                            ///nokia-state/state/log/event-trigger/mpls-tp/entry/statistics/debounce-count
                            leaf debounce-count {
                                type yang:counter32;
                                description
                                    "Indicates the number of times script is not executed due to debounce rule
                                     for the specified trigger entry.";
                            }

                        } // container statistics

                    } // list entry

                } // list mpls-tp

                ///nokia-state/state/log/event-trigger/msdp
                list msdp {
                    key "event";
                    description "Enter the msdp list instance";

                    ///nokia-state/state/log/event-trigger/msdp/event
                    leaf event {
                        type types-log:msdp-events;
                        description "Log event as a trigger for one or more EHS handlers";
                    }

                    ///nokia-state/state/log/event-trigger/msdp/oper-state
                    leaf oper-state {
                        type types-sros:oper-state;
                        description "Indicates the operational state of the EHS Event Trigger.";
                    }

                    ///nokia-state/state/log/event-trigger/msdp/statistics
                    container statistics {
                        description "Enter the statistics context";

                        ///nokia-state/state/log/event-trigger/msdp/statistics/success
                        leaf success {
                            type yang:counter32;
                            description
                                "Indicates the number of not ignored logger event occurrences
                                 associated with EHS trigger.";
                        }

                        ///nokia-state/state/log/event-trigger/msdp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/msdp/statistics/error-admin-state
                        leaf error-admin-state {
                            type yang:counter32;
                            description
                                "Indicates the number of ignored logger event occurrences associated
                                 with EHS trigger.

                                 Event is ignored due to trigger may be out-of-service.";
                        }

                        ///nokia-state/state/log/event-trigger/msdp/statistics/total
                        leaf total {
                            type yang:counter32;
                            description "Sum of success + error-no-entry + error-admin-state.";
                        }

                    } // container statistics

                    ///nokia-state/state/log/event-trigger/msdp/summary-entry-statistics
                    container summary-entry-statistics {
                        description "Enter the summary-entry-statistics context";

                        ///nokia-state/state/log/event-trigger/msdp/summary-entry-statistics/filter-match
                        leaf filter-match {
                            type yang:counter32;
                            description "Indicates the number of times a filter matches an logger event.";
                        }

                        ///nokia-state/state/log/event-trigger/msdp/summary-entry-statistics/filter-fail
                        leaf filter-fail {
                            type yang:counter32;
                            description "Indicates the number of times a filter does not match an logger event.";
                        }

                        ///nokia-state/state/log/event-trigger/msdp/summary-entry-statistics/error-admin-state
                        leaf error-admin-state {
                            type yang:counter32;
                            description
                                "Indicates the number of times the logger event will be ignored due to
                                 admin state of EHS trigger entries is out-of-service.";
                        }

                        ///nokia-state/state/log/event-trigger/msdp/summary-entry-statistics/error-filter
                        leaf error-filter {
                            type yang:counter32;
                            description
                                "Indicates the number of times the logger event will be ignored due to filter
                                 is not operational or is not configured in EHS trigger entries.";
                        }

                        ///nokia-state/state/log/event-trigger/msdp/summary-entry-statistics/error-handler
                        leaf error-handler {
                            type yang:counter32;
                            description
                                "Indicates the number of times the logger event will be ignored due to handler
                                 is not operational or is not configured in EHS trigger entries.";
                        }

                        ///nokia-state/state/log/event-trigger/msdp/summary-entry-statistics/trigger-count
                        leaf trigger-count {
                            type yang:counter32;
                            description "Indicates the number of times script execution is triggered after filter match.";
                        }

                        ///nokia-state/state/log/event-trigger/msdp/summary-entry-statistics/debounce-count
                        leaf debounce-count {
                            type yang:counter32;
                            description "Indicates the number of times script is not executed due to debounce rule.";
                        }

                    } // container summary-entry-statistics

                    ///nokia-state/state/log/event-trigger/msdp/entry
                    list entry {
                        key "id";
                        description "Enter the entry list instance";

                        ///nokia-state/state/log/event-trigger/msdp/entry/id
                        leaf id {
                            type uint32 {
                                range "1..1500";
                            }
                            description "ID of the EHS event trigger entry";
                        }

                        ///nokia-state/state/log/event-trigger/msdp/entry/oper-state
                        leaf oper-state {
                            type types-sros:oper-state;
                            description "Indicates the operational state of the EHS Event Trigger Entry.";
                        }

                        ///nokia-state/state/log/event-trigger/msdp/entry/statistics
                        container statistics {
                            description "Enter the statistics context";

                            ///nokia-state/state/log/event-trigger/msdp/entry/statistics/filter-match
                            leaf filter-match {
                                type yang:counter32;
                                description
                                    "Indicates the number of times a filter, for the specified trigger entry,
                                     matches an logger event.";
                            }

                            ///nokia-state/state/log/event-trigger/msdp/entry/statistics/filter-fail
                            leaf filter-fail {
                                type yang:counter32;
                                description
                                    "Indicates the number of times a filter, for the specified trigger entry,
                                     does not match an logger event.";
                            }

                            ///nokia-state/state/log/event-trigger/msdp/entry/statistics/error-admin-state
                            leaf error-admin-state {
                                type yang:counter32;
                                description
                                    "Indicates the number of times the logger event will be ignored due to
                                     admin state of EHS trigger entry is out-of-service.";
                            }

                            ///nokia-state/state/log/event-trigger/msdp/entry/statistics/error-filter
                            leaf error-filter {
                                type yang:counter32;
                                description
                                    "Indicates the number of times the logger event will be ignored due to filter
                                     is not operational or is not configured in EHS trigger entry.";
                            }

                            ///nokia-state/state/log/event-trigger/msdp/entry/statistics/error-handler
                            leaf error-handler {
                                type yang:counter32;
                                description
                                    "Indicates the number of times the logger event will be ignored due to handler
                                     is not operational or is not configured in EHS trigger entry.";
                            }

                            ///nokia-state/state/log/event-trigger/msdp/entry/statistics/trigger-count
                            leaf trigger-count {
                                type yang:counter32;
                                description
                                    "Indicates the number of times script execution is triggered after filter match
                                     for the specified trigger entry.";
                            }

                            ///nokia-state/state/log/event-trigger/msdp/entry/statistics/debounce-count
                            leaf debounce-count {
                                type yang:counter32;
                                description
                                    "Indicates the number of times script is not executed due to debounce rule
                                     for the specified trigger entry.";
                            }

                        } // container statistics

                    } // list entry

                } // list msdp

                ///nokia-state/state/log/event-trigger/nat
                list nat {
                    key "event";
                    description "Enter the nat list instance";

                    ///nokia-state/state/log/event-trigger/nat/event
                    leaf event {
                        type types-log:nat-events;
                        description "Log event as a trigger for one or more EHS handlers";
                    }

                    ///nokia-state/state/log/event-trigger/nat/oper-state
                    leaf oper-state {
                        type types-sros:oper-state;
                        description "Indicates the operational state of the EHS Event Trigger.";
                    }

                    ///nokia-state/state/log/event-trigger/nat/statistics
                    container statistics {
                        description "Enter the statistics context";

                        ///nokia-state/state/log/event-trigger/nat/statistics/success
                        leaf success {
                            type yang:counter32;
                            description
                                "Indicates the number of not ignored logger event occurrences
                                 associated with EHS trigger.";
                        }

                        ///nokia-state/state/log/event-trigger/nat/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/nat/statistics/error-admin-state
                        leaf error-admin-state {
                            type yang:counter32;
                            description
                                "Indicates the number of ignored logger event occurrences associated
                                 with EHS trigger.

                                 Event is ignored due to trigger may be out-of-service.";
                        }

                        ///nokia-state/state/log/event-trigger/nat/statistics/total
                        leaf total {
                            type yang:counter32;
                            description "Sum of success + error-no-entry + error-admin-state.";
                        }

                    } // container statistics

                    ///nokia-state/state/log/event-trigger/nat/summary-entry-statistics
                    container summary-entry-statistics {
                        description "Enter the summary-entry-statistics context";

                        ///nokia-state/state/log/event-trigger/nat/summary-entry-statistics/filter-match
                        leaf filter-match {
                            type yang:counter32;
                            description "Indicates the number of times a filter matches an logger event.";
                        }

                        ///nokia-state/state/log/event-trigger/nat/summary-entry-statistics/filter-fail
                        leaf filter-fail {
                            type yang:counter32;
                            description "Indicates the number of times a filter does not match an logger event.";
                        }

                        ///nokia-state/state/log/event-trigger/nat/summary-entry-statistics/error-admin-state
                        leaf error-admin-state {
                            type yang:counter32;
                            description
                                "Indicates the number of times the logger event will be ignored due to
                                 admin state of EHS trigger entries is out-of-service.";
                        }

                        ///nokia-state/state/log/event-trigger/nat/summary-entry-statistics/error-filter
                        leaf error-filter {
                            type yang:counter32;
                            description
                                "Indicates the number of times the logger event will be ignored due to filter
                                 is not operational or is not configured in EHS trigger entries.";
                        }

                        ///nokia-state/state/log/event-trigger/nat/summary-entry-statistics/error-handler
                        leaf error-handler {
                            type yang:counter32;
                            description
                                "Indicates the number of times the logger event will be ignored due to handler
                                 is not operational or is not configured in EHS trigger entries.";
                        }

                        ///nokia-state/state/log/event-trigger/nat/summary-entry-statistics/trigger-count
                        leaf trigger-count {
                            type yang:counter32;
                            description "Indicates the number of times script execution is triggered after filter match.";
                        }

                        ///nokia-state/state/log/event-trigger/nat/summary-entry-statistics/debounce-count
                        leaf debounce-count {
                            type yang:counter32;
                            description "Indicates the number of times script is not executed due to debounce rule.";
                        }

                    } // container summary-entry-statistics

                    ///nokia-state/state/log/event-trigger/nat/entry
                    list entry {
                        key "id";
                        description "Enter the entry list instance";

                        ///nokia-state/state/log/event-trigger/nat/entry/id
                        leaf id {
                            type uint32 {
                                range "1..1500";
                            }
                            description "ID of the EHS event trigger entry";
                        }

                        ///nokia-state/state/log/event-trigger/nat/entry/oper-state
                        leaf oper-state {
                            type types-sros:oper-state;
                            description "Indicates the operational state of the EHS Event Trigger Entry.";
                        }

                        ///nokia-state/state/log/event-trigger/nat/entry/statistics
                        container statistics {
                            description "Enter the statistics context";

                            ///nokia-state/state/log/event-trigger/nat/entry/statistics/filter-match
                            leaf filter-match {
                                type yang:counter32;
                                description
                                    "Indicates the number of times a filter, for the specified trigger entry,
                                     matches an logger event.";
                            }

                            ///nokia-state/state/log/event-trigger/nat/entry/statistics/filter-fail
                            leaf filter-fail {
                                type yang:counter32;
                                description
                                    "Indicates the number of times a filter, for the specified trigger entry,
                                     does not match an logger event.";
                            }

                            ///nokia-state/state/log/event-trigger/nat/entry/statistics/error-admin-state
                            leaf error-admin-state {
                                type yang:counter32;
                                description
                                    "Indicates the number of times the logger event will be ignored due to
                                     admin state of EHS trigger entry is out-of-service.";
                            }

                            ///nokia-state/state/log/event-trigger/nat/entry/statistics/error-filter
                            leaf error-filter {
                                type yang:counter32;
                                description
                                    "Indicates the number of times the logger event will be ignored due to filter
                                     is not operational or is not configured in EHS trigger entry.";
                            }

                            ///nokia-state/state/log/event-trigger/nat/entry/statistics/error-handler
                            leaf error-handler {
                                type yang:counter32;
                                description
                                    "Indicates the number of times the logger event will be ignored due to handler
                                     is not operational or is not configured in EHS trigger entry.";
                            }

                            ///nokia-state/state/log/event-trigger/nat/entry/statistics/trigger-count
                            leaf trigger-count {
                                type yang:counter32;
                                description
                                    "Indicates the number of times script execution is triggered after filter match
                                     for the specified trigger entry.";
                            }

                            ///nokia-state/state/log/event-trigger/nat/entry/statistics/debounce-count
                            leaf debounce-count {
                                type yang:counter32;
                                description
                                    "Indicates the number of times script is not executed due to debounce rule
                                     for the specified trigger entry.";
                            }

                        } // container statistics

                    } // list entry

                } // list nat

                ///nokia-state/state/log/event-trigger/ntp
                list ntp {
                    key "event";
                    description "Enter the ntp list instance";

                    ///nokia-state/state/log/event-trigger/ntp/event
                    leaf event {
                        type types-log:ntp-events;
                        description "Log event as a trigger for one or more EHS handlers";
                    }

                    ///nokia-state/state/log/event-trigger/ntp/oper-state
                    leaf oper-state {
                        type types-sros:oper-state;
                        description "Indicates the operational state of the EHS Event Trigger.";
                    }

                    ///nokia-state/state/log/event-trigger/ntp/statistics
                    container statistics {
                        description "Enter the statistics context";

                        ///nokia-state/state/log/event-trigger/ntp/statistics/success
                        leaf success {
                            type yang:counter32;
                            description
                                "Indicates the number of not ignored logger event occurrences
                                 associated with EHS trigger.";
                        }

                        ///nokia-state/state/log/event-trigger/ntp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ntp/statistics/error-admin-state
                        leaf error-admin-state {
                            type yang:counter32;
                            description
                                "Indicates the number of ignored logger event occurrences associated
                                 with EHS trigger.

                                 Event is ignored due to trigger may be out-of-service.";
                        }

                        ///nokia-state/state/log/event-trigger/ntp/statistics/total
                        leaf total {
                            type yang:counter32;
                            description "Sum of success + error-no-entry + error-admin-state.";
                        }

                    } // container statistics

                    ///nokia-state/state/log/event-trigger/ntp/summary-entry-statistics
                    container summary-entry-statistics {
                        description "Enter the summary-entry-statistics context";

                        ///nokia-state/state/log/event-trigger/ntp/summary-entry-statistics/filter-match
                        leaf filter-match {
                            type yang:counter32;
                            description "Indicates the number of times a filter matches an logger event.";
                        }

                        ///nokia-state/state/log/event-trigger/ntp/summary-entry-statistics/filter-fail
                        leaf filter-fail {
                            type yang:counter32;
                            description "Indicates the number of times a filter does not match an logger event.";
                        }

                        ///nokia-state/state/log/event-trigger/ntp/summary-entry-statistics/error-admin-state
                        leaf error-admin-state {
                            type yang:counter32;
                            description
                                "Indicates the number of times the logger event will be ignored due to
                                 admin state of EHS trigger entries is out-of-service.";
                        }

                        ///nokia-state/state/log/event-trigger/ntp/summary-entry-statistics/error-filter
                        leaf error-filter {
                            type yang:counter32;
                            description
                                "Indicates the number of times the logger event will be ignored due to filter
                                 is not operational or is not configured in EHS trigger entries.";
                        }

                        ///nokia-state/state/log/event-trigger/ntp/summary-entry-statistics/error-handler
                        leaf error-handler {
                            type yang:counter32;
                            description
                                "Indicates the number of times the logger event will be ignored due to handler
                                 is not operational or is not configured in EHS trigger entries.";
                        }

                        ///nokia-state/state/log/event-trigger/ntp/summary-entry-statistics/trigger-count
                        leaf trigger-count {
                            type yang:counter32;
                            description "Indicates the number of times script execution is triggered after filter match.";
                        }

                        ///nokia-state/state/log/event-trigger/ntp/summary-entry-statistics/debounce-count
                        leaf debounce-count {
                            type yang:counter32;
                            description "Indicates the number of times script is not executed due to debounce rule.";
                        }

                    } // container summary-entry-statistics

                    ///nokia-state/state/log/event-trigger/ntp/entry
                    list entry {
                        key "id";
                        description "Enter the entry list instance";

                        ///nokia-state/state/log/event-trigger/ntp/entry/id
                        leaf id {
                            type uint32 {
                                range "1..1500";
                            }
                            description "ID of the EHS event trigger entry";
                        }

                        ///nokia-state/state/log/event-trigger/ntp/entry/oper-state
                        leaf oper-state {
                            type types-sros:oper-state;
                            description "Indicates the operational state of the EHS Event Trigger Entry.";
                        }

                        ///nokia-state/state/log/event-trigger/ntp/entry/statistics
                        container statistics {
                            description "Enter the statistics context";

                            ///nokia-state/state/log/event-trigger/ntp/entry/statistics/filter-match
                            leaf filter-match {
                                type yang:counter32;
                                description
                                    "Indicates the number of times a filter, for the specified trigger entry,
                                     matches an logger event.";
                            }

                            ///nokia-state/state/log/event-trigger/ntp/entry/statistics/filter-fail
                            leaf filter-fail {
                                type yang:counter32;
                                description
                                    "Indicates the number of times a filter, for the specified trigger entry,
                                     does not match an logger event.";
                            }

                            ///nokia-state/state/log/event-trigger/ntp/entry/statistics/error-admin-state
                            leaf error-admin-state {
                                type yang:counter32;
                                description
                                    "Indicates the number of times the logger event will be ignored due to
                                     admin state of EHS trigger entry is out-of-service.";
                            }

                            ///nokia-state/state/log/event-trigger/ntp/entry/statistics/error-filter
                            leaf error-filter {
                                type yang:counter32;
                                description
                                    "Indicates the number of times the logger event will be ignored due to filter
                                     is not operational or is not configured in EHS trigger entry.";
                            }

                            ///nokia-state/state/log/event-trigger/ntp/entry/statistics/error-handler
                            leaf error-handler {
                                type yang:counter32;
                                description
                                    "Indicates the number of times the logger event will be ignored due to handler
                                     is not operational or is not configured in EHS trigger entry.";
                            }

                            ///nokia-state/state/log/event-trigger/ntp/entry/statistics/trigger-count
                            leaf trigger-count {
                                type yang:counter32;
                                description
                                    "Indicates the number of times script execution is triggered after filter match
                                     for the specified trigger entry.";
                            }

                            ///nokia-state/state/log/event-trigger/ntp/entry/statistics/debounce-count
                            leaf debounce-count {
                                type yang:counter32;
                                description
                                    "Indicates the number of times script is not executed due to debounce rule
                                     for the specified trigger entry.";
                            }

                        } // container statistics

                    } // list entry

                } // list ntp

                ///nokia-state/state/log/event-trigger/oam
                list oam {
                    key "event";
                    description "Enter the oam list instance";

                    ///nokia-state/state/log/event-trigger/oam/event
                    leaf event {
                        type types-log:oam-events;
                        description "Log event as a trigger for one or more EHS handlers";
                    }

                    ///nokia-state/state/log/event-trigger/oam/oper-state
                    leaf oper-state {
                        type types-sros:oper-state;
                        description "Indicates the operational state of the EHS Event Trigger.";
                    }

                    ///nokia-state/state/log/event-trigger/oam/statistics
                    container statistics {
                        description "Enter the statistics context";

                        ///nokia-state/state/log/event-trigger/oam/statistics/success
                        leaf success {
                            type yang:counter32;
                            description
                                "Indicates the number of not ignored logger event occurrences
                                 associated with EHS trigger.";
                        }

                        ///nokia-state/state/log/event-trigger/oam/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/oam/statistics/error-admin-state
                        leaf error-admin-state {
                            type yang:counter32;
                            description
                                "Indicates the number of ignored logger event occurrences associated
                                 with EHS trigger.

                                 Event is ignored due to trigger may be out-of-service.";
                        }

                        ///nokia-state/state/log/event-trigger/oam/statistics/total
                        leaf total {
                            type yang:counter32;
                            description "Sum of success + error-no-entry + error-admin-state.";
                        }

                    } // container statistics

                    ///nokia-state/state/log/event-trigger/oam/summary-entry-statistics
                    container summary-entry-statistics {
                        description "Enter the summary-entry-statistics context";

                        ///nokia-state/state/log/event-trigger/oam/summary-entry-statistics/filter-match
                        leaf filter-match {
                            type yang:counter32;
                            description "Indicates the number of times a filter matches an logger event.";
                        }

                        ///nokia-state/state/log/event-trigger/oam/summary-entry-statistics/filter-fail
                        leaf filter-fail {
                            type yang:counter32;
                            description "Indicates the number of times a filter does not match an logger event.";
                        }

                        ///nokia-state/state/log/event-trigger/oam/summary-entry-statistics/error-admin-state
                        leaf error-admin-state {
                            type yang:counter32;
                            description
                                "Indicates the number of times the logger event will be ignored due to
                                 admin state of EHS trigger entries is out-of-service.";
                        }

                        ///nokia-state/state/log/event-trigger/oam/summary-entry-statistics/error-filter
                        leaf error-filter {
                            type yang:counter32;
                            description
                                "Indicates the number of times the logger event will be ignored due to filter
                                 is not operational or is not configured in EHS trigger entries.";
                        }

                        ///nokia-state/state/log/event-trigger/oam/summary-entry-statistics/error-handler
                        leaf error-handler {
                            type yang:counter32;
                            description
                                "Indicates the number of times the logger event will be ignored due to handler
                                 is not operational or is not configured in EHS trigger entries.";
                        }

                        ///nokia-state/state/log/event-trigger/oam/summary-entry-statistics/trigger-count
                        leaf trigger-count {
                            type yang:counter32;
                            description "Indicates the number of times script execution is triggered after filter match.";
                        }

                        ///nokia-state/state/log/event-trigger/oam/summary-entry-statistics/debounce-count
                        leaf debounce-count {
                            type yang:counter32;
                            description "Indicates the number of times script is not executed due to debounce rule.";
                        }

                    } // container summary-entry-statistics

                    ///nokia-state/state/log/event-trigger/oam/entry
                    list entry {
                        key "id";
                        description "Enter the entry list instance";

                        ///nokia-state/state/log/event-trigger/oam/entry/id
                        leaf id {
                            type uint32 {
                                range "1..1500";
                            }
                            description "ID of the EHS event trigger entry";
                        }

                        ///nokia-state/state/log/event-trigger/oam/entry/oper-state
                        leaf oper-state {
                            type types-sros:oper-state;
                            description "Indicates the operational state of the EHS Event Trigger Entry.";
                        }

                        ///nokia-state/state/log/event-trigger/oam/entry/statistics
                        container statistics {
                            description "Enter the statistics context";

                            ///nokia-state/state/log/event-trigger/oam/entry/statistics/filter-match
                            leaf filter-match {
                                type yang:counter32;
                                description
                                    "Indicates the number of times a filter, for the specified trigger entry,
                                     matches an logger event.";
                            }

                            ///nokia-state/state/log/event-trigger/oam/entry/statistics/filter-fail
                            leaf filter-fail {
                                type yang:counter32;
                                description
                                    "Indicates the number of times a filter, for the specified trigger entry,
                                     does not match an logger event.";
                            }

                            ///nokia-state/state/log/event-trigger/oam/entry/statistics/error-admin-state
                            leaf error-admin-state {
                                type yang:counter32;
                                description
                                    "Indicates the number of times the logger event will be ignored due to
                                     admin state of EHS trigger entry is out-of-service.";
                            }

                            ///nokia-state/state/log/event-trigger/oam/entry/statistics/error-filter
                            leaf error-filter {
                                type yang:counter32;
                                description
                                    "Indicates the number of times the logger event will be ignored due to filter
                                     is not operational or is not configured in EHS trigger entry.";
                            }

                            ///nokia-state/state/log/event-trigger/oam/entry/statistics/error-handler
                            leaf error-handler {
                                type yang:counter32;
                                description
                                    "Indicates the number of times the logger event will be ignored due to handler
                                     is not operational or is not configured in EHS trigger entry.";
                            }

                            ///nokia-state/state/log/event-trigger/oam/entry/statistics/trigger-count
                            leaf trigger-count {
                                type yang:counter32;
                                description
                                    "Indicates the number of times script execution is triggered after filter match
                                     for the specified trigger entry.";
                            }

                            ///nokia-state/state/log/event-trigger/oam/entry/statistics/debounce-count
                            leaf debounce-count {
                                type yang:counter32;
                                description
                                    "Indicates the number of times script is not executed due to debounce rule
                                     for the specified trigger entry.";
                            }

                        } // container statistics

                    } // list entry

                } // list oam

                ///nokia-state/state/log/event-trigger/openflow
                list openflow {
                    key "event";
                    description "Enter the openflow list instance";

                    ///nokia-state/state/log/event-trigger/openflow/event
                    leaf event {
                        type types-log:openflow-events;
                        description "Log event as a trigger for one or more EHS handlers";
                    }

                    ///nokia-state/state/log/event-trigger/openflow/oper-state
                    leaf oper-state {
                        type types-sros:oper-state;
                        description "Indicates the operational state of the EHS Event Trigger.";
                    }

                    ///nokia-state/state/log/event-trigger/openflow/statistics
                    container statistics {
                        description "Enter the statistics context";

                        ///nokia-state/state/log/event-trigger/openflow/statistics/success
                        leaf success {
                            type yang:counter32;
                            description
                                "Indicates the number of not ignored logger event occurrences
                                 associated with EHS trigger.";
                        }

                        ///nokia-state/state/log/event-trigger/openflow/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/openflow/statistics/error-admin-state
                        leaf error-admin-state {
                            type yang:counter32;
                            description
                                "Indicates the number of ignored logger event occurrences associated
                                 with EHS trigger.

                                 Event is ignored due to trigger may be out-of-service.";
                        }

                        ///nokia-state/state/log/event-trigger/openflow/statistics/total
                        leaf total {
                            type yang:counter32;
                            description "Sum of success + error-no-entry + error-admin-state.";
                        }

                    } // container statistics

                    ///nokia-state/state/log/event-trigger/openflow/summary-entry-statistics
                    container summary-entry-statistics {
                        description "Enter the summary-entry-statistics context";

                        ///nokia-state/state/log/event-trigger/openflow/summary-entry-statistics/filter-match
                        leaf filter-match {
                            type yang:counter32;
                            description "Indicates the number of times a filter matches an logger event.";
                        }

                        ///nokia-state/state/log/event-trigger/openflow/summary-entry-statistics/filter-fail
                        leaf filter-fail {
                            type yang:counter32;
                            description "Indicates the number of times a filter does not match an logger event.";
                        }

                        ///nokia-state/state/log/event-trigger/openflow/summary-entry-statistics/error-admin-state
                        leaf error-admin-state {
                            type yang:counter32;
                            description
                                "Indicates the number of times the logger event will be ignored due to
                                 admin state of EHS trigger entries is out-of-service.";
                        }

                        ///nokia-state/state/log/event-trigger/openflow/summary-entry-statistics/error-filter
                        leaf error-filter {
                            type yang:counter32;
                            description
                                "Indicates the number of times the logger event will be ignored due to filter
                                 is not operational or is not configured in EHS trigger entries.";
                        }

                        ///nokia-state/state/log/event-trigger/openflow/summary-entry-statistics/error-handler
                        leaf error-handler {
                            type yang:counter32;
                            description
                                "Indicates the number of times the logger event will be ignored due to handler
                                 is not operational or is not configured in EHS trigger entries.";
                        }

                        ///nokia-state/state/log/event-trigger/openflow/summary-entry-statistics/trigger-count
                        leaf trigger-count {
                            type yang:counter32;
                            description "Indicates the number of times script execution is triggered after filter match.";
                        }

                        ///nokia-state/state/log/event-trigger/openflow/summary-entry-statistics/debounce-count
                        leaf debounce-count {
                            type yang:counter32;
                            description "Indicates the number of times script is not executed due to debounce rule.";
                        }

                    } // container summary-entry-statistics

                    ///nokia-state/state/log/event-trigger/openflow/entry
                    list entry {
                        key "id";
                        description "Enter the entry list instance";

                        ///nokia-state/state/log/event-trigger/openflow/entry/id
                        leaf id {
                            type uint32 {
                                range "1..1500";
                            }
                            description "ID of the EHS event trigger entry";
                        }

                        ///nokia-state/state/log/event-trigger/openflow/entry/oper-state
                        leaf oper-state {
                            type types-sros:oper-state;
                            description "Indicates the operational state of the EHS Event Trigger Entry.";
                        }

                        ///nokia-state/state/log/event-trigger/openflow/entry/statistics
                        container statistics {
                            description "Enter the statistics context";

                            ///nokia-state/state/log/event-trigger/openflow/entry/statistics/filter-match
                            leaf filter-match {
                                type yang:counter32;
                                description
                                    "Indicates the number of times a filter, for the specified trigger entry,
                                     matches an logger event.";
                            }

                            ///nokia-state/state/log/event-trigger/openflow/entry/statistics/filter-fail
                            leaf filter-fail {
                                type yang:counter32;
                                description
                                    "Indicates the number of times a filter, for the specified trigger entry,
                                     does not match an logger event.";
                            }

                            ///nokia-state/state/log/event-trigger/openflow/entry/statistics/error-admin-state
                            leaf error-admin-state {
                                type yang:counter32;
                                description
                                    "Indicates the number of times the logger event will be ignored due to
                                     admin state of EHS trigger entry is out-of-service.";
                            }

                            ///nokia-state/state/log/event-trigger/openflow/entry/statistics/error-filter
                            leaf error-filter {
                                type yang:counter32;
                                description
                                    "Indicates the number of times the logger event will be ignored due to filter
                                     is not operational or is not configured in EHS trigger entry.";
                            }

                            ///nokia-state/state/log/event-trigger/openflow/entry/statistics/error-handler
                            leaf error-handler {
                                type yang:counter32;
                                description
                                    "Indicates the number of times the logger event will be ignored due to handler
                                     is not operational or is not configured in EHS trigger entry.";
                            }

                            ///nokia-state/state/log/event-trigger/openflow/entry/statistics/trigger-count
                            leaf trigger-count {
                                type yang:counter32;
                                description
                                    "Indicates the number of times script execution is triggered after filter match
                                     for the specified trigger entry.";
                            }

                            ///nokia-state/state/log/event-trigger/openflow/entry/statistics/debounce-count
                            leaf debounce-count {
                                type yang:counter32;
                                description
                                    "Indicates the number of times script is not executed due to debounce rule
                                     for the specified trigger entry.";
                            }

                        } // container statistics

                    } // list entry

                } // list openflow

                ///nokia-state/state/log/event-trigger/ospf
                list ospf {
                    key "event";
                    description "Enter the ospf list instance";

                    ///nokia-state/state/log/event-trigger/ospf/event
                    leaf event {
                        type types-log:ospf-events;
                        description "Log event as a trigger for one or more EHS handlers";
                    }

                    ///nokia-state/state/log/event-trigger/ospf/oper-state
                    leaf oper-state {
                        type types-sros:oper-state;
                        description "Indicates the operational state of the EHS Event Trigger.";
                    }

                    ///nokia-state/state/log/event-trigger/ospf/statistics
                    container statistics {
                        description "Enter the statistics context";

                        ///nokia-state/state/log/event-trigger/ospf/statistics/success
                        leaf success {
                            type yang:counter32;
                            description
                                "Indicates the number of not ignored logger event occurrences
                                 associated with EHS trigger.";
                        }

                        ///nokia-state/state/log/event-trigger/ospf/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ospf/statistics/error-admin-state
                        leaf error-admin-state {
                            type yang:counter32;
                            description
                                "Indicates the number of ignored logger event occurrences associated
                                 with EHS trigger.

                                 Event is ignored due to trigger may be out-of-service.";
                        }

                        ///nokia-state/state/log/event-trigger/ospf/statistics/total
                        leaf total {
                            type yang:counter32;
                            description "Sum of success + error-no-entry + error-admin-state.";
                        }

                    } // container statistics

                    ///nokia-state/state/log/event-trigger/ospf/summary-entry-statistics
                    container summary-entry-statistics {
                        description "Enter the summary-entry-statistics context";

                        ///nokia-state/state/log/event-trigger/ospf/summary-entry-statistics/filter-match
                        leaf filter-match {
                            type yang:counter32;
                            description "Indicates the number of times a filter matches an logger event.";
                        }

                        ///nokia-state/state/log/event-trigger/ospf/summary-entry-statistics/filter-fail
                        leaf filter-fail {
                            type yang:counter32;
                            description "Indicates the number of times a filter does not match an logger event.";
                        }

                        ///nokia-state/state/log/event-trigger/ospf/summary-entry-statistics/error-admin-state
                        leaf error-admin-state {
                            type yang:counter32;
                            description
                                "Indicates the number of times the logger event will be ignored due to
                                 admin state of EHS trigger entries is out-of-service.";
                        }

                        ///nokia-state/state/log/event-trigger/ospf/summary-entry-statistics/error-filter
                        leaf error-filter {
                            type yang:counter32;
                            description
                                "Indicates the number of times the logger event will be ignored due to filter
                                 is not operational or is not configured in EHS trigger entries.";
                        }

                        ///nokia-state/state/log/event-trigger/ospf/summary-entry-statistics/error-handler
                        leaf error-handler {
                            type yang:counter32;
                            description
                                "Indicates the number of times the logger event will be ignored due to handler
                                 is not operational or is not configured in EHS trigger entries.";
                        }

                        ///nokia-state/state/log/event-trigger/ospf/summary-entry-statistics/trigger-count
                        leaf trigger-count {
                            type yang:counter32;
                            description "Indicates the number of times script execution is triggered after filter match.";
                        }

                        ///nokia-state/state/log/event-trigger/ospf/summary-entry-statistics/debounce-count
                        leaf debounce-count {
                            type yang:counter32;
                            description "Indicates the number of times script is not executed due to debounce rule.";
                        }

                    } // container summary-entry-statistics

                    ///nokia-state/state/log/event-trigger/ospf/entry
                    list entry {
                        key "id";
                        description "Enter the entry list instance";

                        ///nokia-state/state/log/event-trigger/ospf/entry/id
                        leaf id {
                            type uint32 {
                                range "1..1500";
                            }
                            description "ID of the EHS event trigger entry";
                        }

                        ///nokia-state/state/log/event-trigger/ospf/entry/oper-state
                        leaf oper-state {
                            type types-sros:oper-state;
                            description "Indicates the operational state of the EHS Event Trigger Entry.";
                        }

                        ///nokia-state/state/log/event-trigger/ospf/entry/statistics
                        container statistics {
                            description "Enter the statistics context";

                            ///nokia-state/state/log/event-trigger/ospf/entry/statistics/filter-match
                            leaf filter-match {
                                type yang:counter32;
                                description
                                    "Indicates the number of times a filter, for the specified trigger entry,
                                     matches an logger event.";
                            }

                            ///nokia-state/state/log/event-trigger/ospf/entry/statistics/filter-fail
                            leaf filter-fail {
                                type yang:counter32;
                                description
                                    "Indicates the number of times a filter, for the specified trigger entry,
                                     does not match an logger event.";
                            }

                            ///nokia-state/state/log/event-trigger/ospf/entry/statistics/error-admin-state
                            leaf error-admin-state {
                                type yang:counter32;
                                description
                                    "Indicates the number of times the logger event will be ignored due to
                                     admin state of EHS trigger entry is out-of-service.";
                            }

                            ///nokia-state/state/log/event-trigger/ospf/entry/statistics/error-filter
                            leaf error-filter {
                                type yang:counter32;
                                description
                                    "Indicates the number of times the logger event will be ignored due to filter
                                     is not operational or is not configured in EHS trigger entry.";
                            }

                            ///nokia-state/state/log/event-trigger/ospf/entry/statistics/error-handler
                            leaf error-handler {
                                type yang:counter32;
                                description
                                    "Indicates the number of times the logger event will be ignored due to handler
                                     is not operational or is not configured in EHS trigger entry.";
                            }

                            ///nokia-state/state/log/event-trigger/ospf/entry/statistics/trigger-count
                            leaf trigger-count {
                                type yang:counter32;
                                description
                                    "Indicates the number of times script execution is triggered after filter match
                                     for the specified trigger entry.";
                            }

                            ///nokia-state/state/log/event-trigger/ospf/entry/statistics/debounce-count
                            leaf debounce-count {
                                type yang:counter32;
                                description
                                    "Indicates the number of times script is not executed due to debounce rule
                                     for the specified trigger entry.";
                            }

                        } // container statistics

                    } // list entry

                } // list ospf

                ///nokia-state/state/log/event-trigger/pcap
                list pcap {
                    key "event";
                    description "Enter the pcap list instance";

                    ///nokia-state/state/log/event-trigger/pcap/event
                    leaf event {
                        type types-log:pcap-events;
                        description "Log event as a trigger for one or more EHS handlers";
                    }

                    ///nokia-state/state/log/event-trigger/pcap/oper-state
                    leaf oper-state {
                        type types-sros:oper-state;
                        description "Indicates the operational state of the EHS Event Trigger.";
                    }

                    ///nokia-state/state/log/event-trigger/pcap/statistics
                    container statistics {
                        description "Enter the statistics context";

                        ///nokia-state/state/log/event-trigger/pcap/statistics/success
                        leaf success {
                            type yang:counter32;
                            description
                                "Indicates the number of not ignored logger event occurrences
                                 associated with EHS trigger.";
                        }

                        ///nokia-state/state/log/event-trigger/pcap/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pcap/statistics/error-admin-state
                        leaf error-admin-state {
                            type yang:counter32;
                            description
                                "Indicates the number of ignored logger event occurrences associated
                                 with EHS trigger.

                                 Event is ignored due to trigger may be out-of-service.";
                        }

                        ///nokia-state/state/log/event-trigger/pcap/statistics/total
                        leaf total {
                            type yang:counter32;
                            description "Sum of success + error-no-entry + error-admin-state.";
                        }

                    } // container statistics

                    ///nokia-state/state/log/event-trigger/pcap/summary-entry-statistics
                    container summary-entry-statistics {
                        description "Enter the summary-entry-statistics context";

                        ///nokia-state/state/log/event-trigger/pcap/summary-entry-statistics/filter-match
                        leaf filter-match {
                            type yang:counter32;
                            description "Indicates the number of times a filter matches an logger event.";
                        }

                        ///nokia-state/state/log/event-trigger/pcap/summary-entry-statistics/filter-fail
                        leaf filter-fail {
                            type yang:counter32;
                            description "Indicates the number of times a filter does not match an logger event.";
                        }

                        ///nokia-state/state/log/event-trigger/pcap/summary-entry-statistics/error-admin-state
                        leaf error-admin-state {
                            type yang:counter32;
                            description
                                "Indicates the number of times the logger event will be ignored due to
                                 admin state of EHS trigger entries is out-of-service.";
                        }

                        ///nokia-state/state/log/event-trigger/pcap/summary-entry-statistics/error-filter
                        leaf error-filter {
                            type yang:counter32;
                            description
                                "Indicates the number of times the logger event will be ignored due to filter
                                 is not operational or is not configured in EHS trigger entries.";
                        }

                        ///nokia-state/state/log/event-trigger/pcap/summary-entry-statistics/error-handler
                        leaf error-handler {
                            type yang:counter32;
                            description
                                "Indicates the number of times the logger event will be ignored due to handler
                                 is not operational or is not configured in EHS trigger entries.";
                        }

                        ///nokia-state/state/log/event-trigger/pcap/summary-entry-statistics/trigger-count
                        leaf trigger-count {
                            type yang:counter32;
                            description "Indicates the number of times script execution is triggered after filter match.";
                        }

                        ///nokia-state/state/log/event-trigger/pcap/summary-entry-statistics/debounce-count
                        leaf debounce-count {
                            type yang:counter32;
                            description "Indicates the number of times script is not executed due to debounce rule.";
                        }

                    } // container summary-entry-statistics

                    ///nokia-state/state/log/event-trigger/pcap/entry
                    list entry {
                        key "id";
                        description "Enter the entry list instance";

                        ///nokia-state/state/log/event-trigger/pcap/entry/id
                        leaf id {
                            type uint32 {
                                range "1..1500";
                            }
                            description "ID of the EHS event trigger entry";
                        }

                        ///nokia-state/state/log/event-trigger/pcap/entry/oper-state
                        leaf oper-state {
                            type types-sros:oper-state;
                            description "Indicates the operational state of the EHS Event Trigger Entry.";
                        }

                        ///nokia-state/state/log/event-trigger/pcap/entry/statistics
                        container statistics {
                            description "Enter the statistics context";

                            ///nokia-state/state/log/event-trigger/pcap/entry/statistics/filter-match
                            leaf filter-match {
                                type yang:counter32;
                                description
                                    "Indicates the number of times a filter, for the specified trigger entry,
                                     matches an logger event.";
                            }

                            ///nokia-state/state/log/event-trigger/pcap/entry/statistics/filter-fail
                            leaf filter-fail {
                                type yang:counter32;
                                description
                                    "Indicates the number of times a filter, for the specified trigger entry,
                                     does not match an logger event.";
                            }

                            ///nokia-state/state/log/event-trigger/pcap/entry/statistics/error-admin-state
                            leaf error-admin-state {
                                type yang:counter32;
                                description
                                    "Indicates the number of times the logger event will be ignored due to
                                     admin state of EHS trigger entry is out-of-service.";
                            }

                            ///nokia-state/state/log/event-trigger/pcap/entry/statistics/error-filter
                            leaf error-filter {
                                type yang:counter32;
                                description
                                    "Indicates the number of times the logger event will be ignored due to filter
                                     is not operational or is not configured in EHS trigger entry.";
                            }

                            ///nokia-state/state/log/event-trigger/pcap/entry/statistics/error-handler
                            leaf error-handler {
                                type yang:counter32;
                                description
                                    "Indicates the number of times the logger event will be ignored due to handler
                                     is not operational or is not configured in EHS trigger entry.";
                            }

                            ///nokia-state/state/log/event-trigger/pcap/entry/statistics/trigger-count
                            leaf trigger-count {
                                type yang:counter32;
                                description
                                    "Indicates the number of times script execution is triggered after filter match
                                     for the specified trigger entry.";
                            }

                            ///nokia-state/state/log/event-trigger/pcap/entry/statistics/debounce-count
                            leaf debounce-count {
                                type yang:counter32;
                                description
                                    "Indicates the number of times script is not executed due to debounce rule
                                     for the specified trigger entry.";
                            }

                        } // container statistics

                    } // list entry

                } // list pcap

                ///nokia-state/state/log/event-trigger/pcep
                list pcep {
                    key "event";
                    description "Enter the pcep list instance";

                    ///nokia-state/state/log/event-trigger/pcep/event
                    leaf event {
                        type types-log:pcep-events;
                        description "PCEP module events";
                    }

                    ///nokia-state/state/log/event-trigger/pcep/oper-state
                    leaf oper-state {
                        type types-sros:oper-state;
                        description "Indicates the operational state of the EHS Event Trigger.";
                    }

                    ///nokia-state/state/log/event-trigger/pcep/statistics
                    container statistics {
                        description "Enter the statistics context";

                        ///nokia-state/state/log/event-trigger/pcep/statistics/success
                        leaf success {
                            type yang:counter32;
                            description
                                "Indicates the number of not ignored logger event occurrences
                                 associated with EHS trigger.";
                        }

                        ///nokia-state/state/log/event-trigger/pcep/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pcep/statistics/error-admin-state
                        leaf error-admin-state {
                            type yang:counter32;
                            description
                                "Indicates the number of ignored logger event occurrences associated
                                 with EHS trigger.

                                 Event is ignored due to trigger may be out-of-service.";
                        }

                        ///nokia-state/state/log/event-trigger/pcep/statistics/total
                        leaf total {
                            type yang:counter32;
                            description "Sum of success + error-no-entry + error-admin-state.";
                        }

                    } // container statistics

                    ///nokia-state/state/log/event-trigger/pcep/summary-entry-statistics
                    container summary-entry-statistics {
                        description "Enter the summary-entry-statistics context";

                        ///nokia-state/state/log/event-trigger/pcep/summary-entry-statistics/filter-match
                        leaf filter-match {
                            type yang:counter32;
                            description "Indicates the number of times a filter matches an logger event.";
                        }

                        ///nokia-state/state/log/event-trigger/pcep/summary-entry-statistics/filter-fail
                        leaf filter-fail {
                            type yang:counter32;
                            description "Indicates the number of times a filter does not match an logger event.";
                        }

                        ///nokia-state/state/log/event-trigger/pcep/summary-entry-statistics/error-admin-state
                        leaf error-admin-state {
                            type yang:counter32;
                            description
                                "Indicates the number of times the logger event will be ignored due to
                                 admin state of EHS trigger entries is out-of-service.";
                        }

                        ///nokia-state/state/log/event-trigger/pcep/summary-entry-statistics/error-filter
                        leaf error-filter {
                            type yang:counter32;
                            description
                                "Indicates the number of times the logger event will be ignored due to filter
                                 is not operational or is not configured in EHS trigger entries.";
                        }

                        ///nokia-state/state/log/event-trigger/pcep/summary-entry-statistics/error-handler
                        leaf error-handler {
                            type yang:counter32;
                            description
                                "Indicates the number of times the logger event will be ignored due to handler
                                 is not operational or is not configured in EHS trigger entries.";
                        }

                        ///nokia-state/state/log/event-trigger/pcep/summary-entry-statistics/trigger-count
                        leaf trigger-count {
                            type yang:counter32;
                            description "Indicates the number of times script execution is triggered after filter match.";
                        }

                        ///nokia-state/state/log/event-trigger/pcep/summary-entry-statistics/debounce-count
                        leaf debounce-count {
                            type yang:counter32;
                            description "Indicates the number of times script is not executed due to debounce rule.";
                        }

                    } // container summary-entry-statistics

                    ///nokia-state/state/log/event-trigger/pcep/entry
                    list entry {
                        key "id";
                        description "Enter the entry list instance";

                        ///nokia-state/state/log/event-trigger/pcep/entry/id
                        leaf id {
                            type uint32 {
                                range "1..1500";
                            }
                            description "ID of the EHS event trigger entry";
                        }

                        ///nokia-state/state/log/event-trigger/pcep/entry/oper-state
                        leaf oper-state {
                            type types-sros:oper-state;
                            description "Indicates the operational state of the EHS Event Trigger Entry.";
                        }

                        ///nokia-state/state/log/event-trigger/pcep/entry/statistics
                        container statistics {
                            description "Enter the statistics context";

                            ///nokia-state/state/log/event-trigger/pcep/entry/statistics/filter-match
                            leaf filter-match {
                                type yang:counter32;
                                description
                                    "Indicates the number of times a filter, for the specified trigger entry,
                                     matches an logger event.";
                            }

                            ///nokia-state/state/log/event-trigger/pcep/entry/statistics/filter-fail
                            leaf filter-fail {
                                type yang:counter32;
                                description
                                    "Indicates the number of times a filter, for the specified trigger entry,
                                     does not match an logger event.";
                            }

                            ///nokia-state/state/log/event-trigger/pcep/entry/statistics/error-admin-state
                            leaf error-admin-state {
                                type yang:counter32;
                                description
                                    "Indicates the number of times the logger event will be ignored due to
                                     admin state of EHS trigger entry is out-of-service.";
                            }

                            ///nokia-state/state/log/event-trigger/pcep/entry/statistics/error-filter
                            leaf error-filter {
                                type yang:counter32;
                                description
                                    "Indicates the number of times the logger event will be ignored due to filter
                                     is not operational or is not configured in EHS trigger entry.";
                            }

                            ///nokia-state/state/log/event-trigger/pcep/entry/statistics/error-handler
                            leaf error-handler {
                                type yang:counter32;
                                description
                                    "Indicates the number of times the logger event will be ignored due to handler
                                     is not operational or is not configured in EHS trigger entry.";
                            }

                            ///nokia-state/state/log/event-trigger/pcep/entry/statistics/trigger-count
                            leaf trigger-count {
                                type yang:counter32;
                                description
                                    "Indicates the number of times script execution is triggered after filter match
                                     for the specified trigger entry.";
                            }

                            ///nokia-state/state/log/event-trigger/pcep/entry/statistics/debounce-count
                            leaf debounce-count {
                                type yang:counter32;
                                description
                                    "Indicates the number of times script is not executed due to debounce rule
                                     for the specified trigger entry.";
                            }

                        } // container statistics

                    } // list entry

                } // list pcep

                ///nokia-state/state/log/event-trigger/pfcp
                list pfcp {
                    key "event";
                    description "Enter the pfcp list instance";

                    ///nokia-state/state/log/event-trigger/pfcp/event
                    leaf event {
                        type types-log:pfcp-events;
                        description "PFCP events";
                    }

                    ///nokia-state/state/log/event-trigger/pfcp/oper-state
                    leaf oper-state {
                        type types-sros:oper-state;
                        description "Indicates the operational state of the EHS Event Trigger.";
                    }

                    ///nokia-state/state/log/event-trigger/pfcp/statistics
                    container statistics {
                        description "Enter the statistics context";

                        ///nokia-state/state/log/event-trigger/pfcp/statistics/success
                        leaf success {
                            type yang:counter32;
                            description
                                "Indicates the number of not ignored logger event occurrences
                                 associated with EHS trigger.";
                        }

                        ///nokia-state/state/log/event-trigger/pfcp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pfcp/statistics/error-admin-state
                        leaf error-admin-state {
                            type yang:counter32;
                            description
                                "Indicates the number of ignored logger event occurrences associated
                                 with EHS trigger.

                                 Event is ignored due to trigger may be out-of-service.";
                        }

                        ///nokia-state/state/log/event-trigger/pfcp/statistics/total
                        leaf total {
                            type yang:counter32;
                            description "Sum of success + error-no-entry + error-admin-state.";
                        }

                    } // container statistics

                    ///nokia-state/state/log/event-trigger/pfcp/summary-entry-statistics
                    container summary-entry-statistics {
                        description "Enter the summary-entry-statistics context";

                        ///nokia-state/state/log/event-trigger/pfcp/summary-entry-statistics/filter-match
                        leaf filter-match {
                            type yang:counter32;
                            description "Indicates the number of times a filter matches an logger event.";
                        }

                        ///nokia-state/state/log/event-trigger/pfcp/summary-entry-statistics/filter-fail
                        leaf filter-fail {
                            type yang:counter32;
                            description "Indicates the number of times a filter does not match an logger event.";
                        }

                        ///nokia-state/state/log/event-trigger/pfcp/summary-entry-statistics/error-admin-state
                        leaf error-admin-state {
                            type yang:counter32;
                            description
                                "Indicates the number of times the logger event will be ignored due to
                                 admin state of EHS trigger entries is out-of-service.";
                        }

                        ///nokia-state/state/log/event-trigger/pfcp/summary-entry-statistics/error-filter
                        leaf error-filter {
                            type yang:counter32;
                            description
                                "Indicates the number of times the logger event will be ignored due to filter
                                 is not operational or is not configured in EHS trigger entries.";
                        }

                        ///nokia-state/state/log/event-trigger/pfcp/summary-entry-statistics/error-handler
                        leaf error-handler {
                            type yang:counter32;
                            description
                                "Indicates the number of times the logger event will be ignored due to handler
                                 is not operational or is not configured in EHS trigger entries.";
                        }

                        ///nokia-state/state/log/event-trigger/pfcp/summary-entry-statistics/trigger-count
                        leaf trigger-count {
                            type yang:counter32;
                            description "Indicates the number of times script execution is triggered after filter match.";
                        }

                        ///nokia-state/state/log/event-trigger/pfcp/summary-entry-statistics/debounce-count
                        leaf debounce-count {
                            type yang:counter32;
                            description "Indicates the number of times script is not executed due to debounce rule.";
                        }

                    } // container summary-entry-statistics

                    ///nokia-state/state/log/event-trigger/pfcp/entry
                    list entry {
                        key "id";
                        description "Enter the entry list instance";

                        ///nokia-state/state/log/event-trigger/pfcp/entry/id
                        leaf id {
                            type uint32 {
                                range "1..1500";
                            }
                            description "ID of the EHS event trigger entry";
                        }

                        ///nokia-state/state/log/event-trigger/pfcp/entry/oper-state
                        leaf oper-state {
                            type types-sros:oper-state;
                            description "Indicates the operational state of the EHS Event Trigger Entry.";
                        }

                        ///nokia-state/state/log/event-trigger/pfcp/entry/statistics
                        container statistics {
                            description "Enter the statistics context";

                            ///nokia-state/state/log/event-trigger/pfcp/entry/statistics/filter-match
                            leaf filter-match {
                                type yang:counter32;
                                description
                                    "Indicates the number of times a filter, for the specified trigger entry,
                                     matches an logger event.";
                            }

                            ///nokia-state/state/log/event-trigger/pfcp/entry/statistics/filter-fail
                            leaf filter-fail {
                                type yang:counter32;
                                description
                                    "Indicates the number of times a filter, for the specified trigger entry,
                                     does not match an logger event.";
                            }

                            ///nokia-state/state/log/event-trigger/pfcp/entry/statistics/error-admin-state
                            leaf error-admin-state {
                                type yang:counter32;
                                description
                                    "Indicates the number of times the logger event will be ignored due to
                                     admin state of EHS trigger entry is out-of-service.";
                            }

                            ///nokia-state/state/log/event-trigger/pfcp/entry/statistics/error-filter
                            leaf error-filter {
                                type yang:counter32;
                                description
                                    "Indicates the number of times the logger event will be ignored due to filter
                                     is not operational or is not configured in EHS trigger entry.";
                            }

                            ///nokia-state/state/log/event-trigger/pfcp/entry/statistics/error-handler
                            leaf error-handler {
                                type yang:counter32;
                                description
                                    "Indicates the number of times the logger event will be ignored due to handler
                                     is not operational or is not configured in EHS trigger entry.";
                            }

                            ///nokia-state/state/log/event-trigger/pfcp/entry/statistics/trigger-count
                            leaf trigger-count {
                                type yang:counter32;
                                description
                                    "Indicates the number of times script execution is triggered after filter match
                                     for the specified trigger entry.";
                            }

                            ///nokia-state/state/log/event-trigger/pfcp/entry/statistics/debounce-count
                            leaf debounce-count {
                                type yang:counter32;
                                description
                                    "Indicates the number of times script is not executed due to debounce rule
                                     for the specified trigger entry.";
                            }

                        } // container statistics

                    } // list entry

                } // list pfcp

                ///nokia-state/state/log/event-trigger/pim
                list pim {
                    key "event";
                    description "Enter the pim list instance";

                    ///nokia-state/state/log/event-trigger/pim/event
                    leaf event {
                        type types-log:pim-events;
                        description "Log event as a trigger for one or more EHS handlers";
                    }

                    ///nokia-state/state/log/event-trigger/pim/oper-state
                    leaf oper-state {
                        type types-sros:oper-state;
                        description "Indicates the operational state of the EHS Event Trigger.";
                    }

                    ///nokia-state/state/log/event-trigger/pim/statistics
                    container statistics {
                        description "Enter the statistics context";

                        ///nokia-state/state/log/event-trigger/pim/statistics/success
                        leaf success {
                            type yang:counter32;
                            description
                                "Indicates the number of not ignored logger event occurrences
                                 associated with EHS trigger.";
                        }

                        ///nokia-state/state/log/event-trigger/pim/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pim/statistics/error-admin-state
                        leaf error-admin-state {
                            type yang:counter32;
                            description
                                "Indicates the number of ignored logger event occurrences associated
                                 with EHS trigger.

                                 Event is ignored due to trigger may be out-of-service.";
                        }

                        ///nokia-state/state/log/event-trigger/pim/statistics/total
                        leaf total {
                            type yang:counter32;
                            description "Sum of success + error-no-entry + error-admin-state.";
                        }

                    } // container statistics

                    ///nokia-state/state/log/event-trigger/pim/summary-entry-statistics
                    container summary-entry-statistics {
                        description "Enter the summary-entry-statistics context";

                        ///nokia-state/state/log/event-trigger/pim/summary-entry-statistics/filter-match
                        leaf filter-match {
                            type yang:counter32;
                            description "Indicates the number of times a filter matches an logger event.";
                        }

                        ///nokia-state/state/log/event-trigger/pim/summary-entry-statistics/filter-fail
                        leaf filter-fail {
                            type yang:counter32;
                            description "Indicates the number of times a filter does not match an logger event.";
                        }

                        ///nokia-state/state/log/event-trigger/pim/summary-entry-statistics/error-admin-state
                        leaf error-admin-state {
                            type yang:counter32;
                            description
                                "Indicates the number of times the logger event will be ignored due to
                                 admin state of EHS trigger entries is out-of-service.";
                        }

                        ///nokia-state/state/log/event-trigger/pim/summary-entry-statistics/error-filter
                        leaf error-filter {
                            type yang:counter32;
                            description
                                "Indicates the number of times the logger event will be ignored due to filter
                                 is not operational or is not configured in EHS trigger entries.";
                        }

                        ///nokia-state/state/log/event-trigger/pim/summary-entry-statistics/error-handler
                        leaf error-handler {
                            type yang:counter32;
                            description
                                "Indicates the number of times the logger event will be ignored due to handler
                                 is not operational or is not configured in EHS trigger entries.";
                        }

                        ///nokia-state/state/log/event-trigger/pim/summary-entry-statistics/trigger-count
                        leaf trigger-count {
                            type yang:counter32;
                            description "Indicates the number of times script execution is triggered after filter match.";
                        }

                        ///nokia-state/state/log/event-trigger/pim/summary-entry-statistics/debounce-count
                        leaf debounce-count {
                            type yang:counter32;
                            description "Indicates the number of times script is not executed due to debounce rule.";
                        }

                    } // container summary-entry-statistics

                    ///nokia-state/state/log/event-trigger/pim/entry
                    list entry {
                        key "id";
                        description "Enter the entry list instance";

                        ///nokia-state/state/log/event-trigger/pim/entry/id
                        leaf id {
                            type uint32 {
                                range "1..1500";
                            }
                            description "ID of the EHS event trigger entry";
                        }

                        ///nokia-state/state/log/event-trigger/pim/entry/oper-state
                        leaf oper-state {
                            type types-sros:oper-state;
                            description "Indicates the operational state of the EHS Event Trigger Entry.";
                        }

                        ///nokia-state/state/log/event-trigger/pim/entry/statistics
                        container statistics {
                            description "Enter the statistics context";

                            ///nokia-state/state/log/event-trigger/pim/entry/statistics/filter-match
                            leaf filter-match {
                                type yang:counter32;
                                description
                                    "Indicates the number of times a filter, for the specified trigger entry,
                                     matches an logger event.";
                            }

                            ///nokia-state/state/log/event-trigger/pim/entry/statistics/filter-fail
                            leaf filter-fail {
                                type yang:counter32;
                                description
                                    "Indicates the number of times a filter, for the specified trigger entry,
                                     does not match an logger event.";
                            }

                            ///nokia-state/state/log/event-trigger/pim/entry/statistics/error-admin-state
                            leaf error-admin-state {
                                type yang:counter32;
                                description
                                    "Indicates the number of times the logger event will be ignored due to
                                     admin state of EHS trigger entry is out-of-service.";
                            }

                            ///nokia-state/state/log/event-trigger/pim/entry/statistics/error-filter
                            leaf error-filter {
                                type yang:counter32;
                                description
                                    "Indicates the number of times the logger event will be ignored due to filter
                                     is not operational or is not configured in EHS trigger entry.";
                            }

                            ///nokia-state/state/log/event-trigger/pim/entry/statistics/error-handler
                            leaf error-handler {
                                type yang:counter32;
                                description
                                    "Indicates the number of times the logger event will be ignored due to handler
                                     is not operational or is not configured in EHS trigger entry.";
                            }

                            ///nokia-state/state/log/event-trigger/pim/entry/statistics/trigger-count
                            leaf trigger-count {
                                type yang:counter32;
                                description
                                    "Indicates the number of times script execution is triggered after filter match
                                     for the specified trigger entry.";
                            }

                            ///nokia-state/state/log/event-trigger/pim/entry/statistics/debounce-count
                            leaf debounce-count {
                                type yang:counter32;
                                description
                                    "Indicates the number of times script is not executed due to debounce rule
                                     for the specified trigger entry.";
                            }

                        } // container statistics

                    } // list entry

                } // list pim

                ///nokia-state/state/log/event-trigger/pim-snooping
                list pim-snooping {
                    key "event";
                    description "Enter the pim-snooping list instance";

                    ///nokia-state/state/log/event-trigger/pim-snooping/event
                    leaf event {
                        type types-log:pim-snooping-events;
                        description "Log event as a trigger for one or more EHS handlers";
                    }

                    ///nokia-state/state/log/event-trigger/pim-snooping/oper-state
                    leaf oper-state {
                        type types-sros:oper-state;
                        description "Indicates the operational state of the EHS Event Trigger.";
                    }

                    ///nokia-state/state/log/event-trigger/pim-snooping/statistics
                    container statistics {
                        description "Enter the statistics context";

                        ///nokia-state/state/log/event-trigger/pim-snooping/statistics/success
                        leaf success {
                            type yang:counter32;
                            description
                                "Indicates the number of not ignored logger event occurrences
                                 associated with EHS trigger.";
                        }

                        ///nokia-state/state/log/event-trigger/pim-snooping/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pim-snooping/statistics/error-admin-state
                        leaf error-admin-state {
                            type yang:counter32;
                            description
                                "Indicates the number of ignored logger event occurrences associated
                                 with EHS trigger.

                                 Event is ignored due to trigger may be out-of-service.";
                        }

                        ///nokia-state/state/log/event-trigger/pim-snooping/statistics/total
                        leaf total {
                            type yang:counter32;
                            description "Sum of success + error-no-entry + error-admin-state.";
                        }

                    } // container statistics

                    ///nokia-state/state/log/event-trigger/pim-snooping/summary-entry-statistics
                    container summary-entry-statistics {
                        description "Enter the summary-entry-statistics context";

                        ///nokia-state/state/log/event-trigger/pim-snooping/summary-entry-statistics/filter-match
                        leaf filter-match {
                            type yang:counter32;
                            description "Indicates the number of times a filter matches an logger event.";
                        }

                        ///nokia-state/state/log/event-trigger/pim-snooping/summary-entry-statistics/filter-fail
                        leaf filter-fail {
                            type yang:counter32;
                            description "Indicates the number of times a filter does not match an logger event.";
                        }

                        ///nokia-state/state/log/event-trigger/pim-snooping/summary-entry-statistics/error-admin-state
                        leaf error-admin-state {
                            type yang:counter32;
                            description
                                "Indicates the number of times the logger event will be ignored due to
                                 admin state of EHS trigger entries is out-of-service.";
                        }

                        ///nokia-state/state/log/event-trigger/pim-snooping/summary-entry-statistics/error-filter
                        leaf error-filter {
                            type yang:counter32;
                            description
                                "Indicates the number of times the logger event will be ignored due to filter
                                 is not operational or is not configured in EHS trigger entries.";
                        }

                        ///nokia-state/state/log/event-trigger/pim-snooping/summary-entry-statistics/error-handler
                        leaf error-handler {
                            type yang:counter32;
                            description
                                "Indicates the number of times the logger event will be ignored due to handler
                                 is not operational or is not configured in EHS trigger entries.";
                        }

                        ///nokia-state/state/log/event-trigger/pim-snooping/summary-entry-statistics/trigger-count
                        leaf trigger-count {
                            type yang:counter32;
                            description "Indicates the number of times script execution is triggered after filter match.";
                        }

                        ///nokia-state/state/log/event-trigger/pim-snooping/summary-entry-statistics/debounce-count
                        leaf debounce-count {
                            type yang:counter32;
                            description "Indicates the number of times script is not executed due to debounce rule.";
                        }

                    } // container summary-entry-statistics

                    ///nokia-state/state/log/event-trigger/pim-snooping/entry
                    list entry {
                        key "id";
                        description "Enter the entry list instance";

                        ///nokia-state/state/log/event-trigger/pim-snooping/entry/id
                        leaf id {
                            type uint32 {
                                range "1..1500";
                            }
                            description "ID of the EHS event trigger entry";
                        }

                        ///nokia-state/state/log/event-trigger/pim-snooping/entry/oper-state
                        leaf oper-state {
                            type types-sros:oper-state;
                            description "Indicates the operational state of the EHS Event Trigger Entry.";
                        }

                        ///nokia-state/state/log/event-trigger/pim-snooping/entry/statistics
                        container statistics {
                            description "Enter the statistics context";

                            ///nokia-state/state/log/event-trigger/pim-snooping/entry/statistics/filter-match
                            leaf filter-match {
                                type yang:counter32;
                                description
                                    "Indicates the number of times a filter, for the specified trigger entry,
                                     matches an logger event.";
                            }

                            ///nokia-state/state/log/event-trigger/pim-snooping/entry/statistics/filter-fail
                            leaf filter-fail {
                                type yang:counter32;
                                description
                                    "Indicates the number of times a filter, for the specified trigger entry,
                                     does not match an logger event.";
                            }

                            ///nokia-state/state/log/event-trigger/pim-snooping/entry/statistics/error-admin-state
                            leaf error-admin-state {
                                type yang:counter32;
                                description
                                    "Indicates the number of times the logger event will be ignored due to
                                     admin state of EHS trigger entry is out-of-service.";
                            }

                            ///nokia-state/state/log/event-trigger/pim-snooping/entry/statistics/error-filter
                            leaf error-filter {
                                type yang:counter32;
                                description
                                    "Indicates the number of times the logger event will be ignored due to filter
                                     is not operational or is not configured in EHS trigger entry.";
                            }

                            ///nokia-state/state/log/event-trigger/pim-snooping/entry/statistics/error-handler
                            leaf error-handler {
                                type yang:counter32;
                                description
                                    "Indicates the number of times the logger event will be ignored due to handler
                                     is not operational or is not configured in EHS trigger entry.";
                            }

                            ///nokia-state/state/log/event-trigger/pim-snooping/entry/statistics/trigger-count
                            leaf trigger-count {
                                type yang:counter32;
                                description
                                    "Indicates the number of times script execution is triggered after filter match
                                     for the specified trigger entry.";
                            }

                            ///nokia-state/state/log/event-trigger/pim-snooping/entry/statistics/debounce-count
                            leaf debounce-count {
                                type yang:counter32;
                                description
                                    "Indicates the number of times script is not executed due to debounce rule
                                     for the specified trigger entry.";
                            }

                        } // container statistics

                    } // list entry

                } // list pim-snooping

                ///nokia-state/state/log/event-trigger/port
                list port {
                    key "event";
                    description "Enter the port list instance";

                    ///nokia-state/state/log/event-trigger/port/event
                    leaf event {
                        type types-log:port-events;
                        description "Log event as a trigger for one or more EHS handlers";
                    }

                    ///nokia-state/state/log/event-trigger/port/oper-state
                    leaf oper-state {
                        type types-sros:oper-state;
                        description "Indicates the operational state of the EHS Event Trigger.";
                    }

                    ///nokia-state/state/log/event-trigger/port/statistics
                    container statistics {
                        description "Enter the statistics context";

                        ///nokia-state/state/log/event-trigger/port/statistics/success
                        leaf success {
                            type yang:counter32;
                            description
                                "Indicates the number of not ignored logger event occurrences
                                 associated with EHS trigger.";
                        }

                        ///nokia-state/state/log/event-trigger/port/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/port/statistics/error-admin-state
                        leaf error-admin-state {
                            type yang:counter32;
                            description
                                "Indicates the number of ignored logger event occurrences associated
                                 with EHS trigger.

                                 Event is ignored due to trigger may be out-of-service.";
                        }

                        ///nokia-state/state/log/event-trigger/port/statistics/total
                        leaf total {
                            type yang:counter32;
                            description "Sum of success + error-no-entry + error-admin-state.";
                        }

                    } // container statistics

                    ///nokia-state/state/log/event-trigger/port/summary-entry-statistics
                    container summary-entry-statistics {
                        description "Enter the summary-entry-statistics context";

                        ///nokia-state/state/log/event-trigger/port/summary-entry-statistics/filter-match
                        leaf filter-match {
                            type yang:counter32;
                            description "Indicates the number of times a filter matches an logger event.";
                        }

                        ///nokia-state/state/log/event-trigger/port/summary-entry-statistics/filter-fail
                        leaf filter-fail {
                            type yang:counter32;
                            description "Indicates the number of times a filter does not match an logger event.";
                        }

                        ///nokia-state/state/log/event-trigger/port/summary-entry-statistics/error-admin-state
                        leaf error-admin-state {
                            type yang:counter32;
                            description
                                "Indicates the number of times the logger event will be ignored due to
                                 admin state of EHS trigger entries is out-of-service.";
                        }

                        ///nokia-state/state/log/event-trigger/port/summary-entry-statistics/error-filter
                        leaf error-filter {
                            type yang:counter32;
                            description
                                "Indicates the number of times the logger event will be ignored due to filter
                                 is not operational or is not configured in EHS trigger entries.";
                        }

                        ///nokia-state/state/log/event-trigger/port/summary-entry-statistics/error-handler
                        leaf error-handler {
                            type yang:counter32;
                            description
                                "Indicates the number of times the logger event will be ignored due to handler
                                 is not operational or is not configured in EHS trigger entries.";
                        }

                        ///nokia-state/state/log/event-trigger/port/summary-entry-statistics/trigger-count
                        leaf trigger-count {
                            type yang:counter32;
                            description "Indicates the number of times script execution is triggered after filter match.";
                        }

                        ///nokia-state/state/log/event-trigger/port/summary-entry-statistics/debounce-count
                        leaf debounce-count {
                            type yang:counter32;
                            description "Indicates the number of times script is not executed due to debounce rule.";
                        }

                    } // container summary-entry-statistics

                    ///nokia-state/state/log/event-trigger/port/entry
                    list entry {
                        key "id";
                        description "Enter the entry list instance";

                        ///nokia-state/state/log/event-trigger/port/entry/id
                        leaf id {
                            type uint32 {
                                range "1..1500";
                            }
                            description "ID of the EHS event trigger entry";
                        }

                        ///nokia-state/state/log/event-trigger/port/entry/oper-state
                        leaf oper-state {
                            type types-sros:oper-state;
                            description "Indicates the operational state of the EHS Event Trigger Entry.";
                        }

                        ///nokia-state/state/log/event-trigger/port/entry/statistics
                        container statistics {
                            description "Enter the statistics context";

                            ///nokia-state/state/log/event-trigger/port/entry/statistics/filter-match
                            leaf filter-match {
                                type yang:counter32;
                                description
                                    "Indicates the number of times a filter, for the specified trigger entry,
                                     matches an logger event.";
                            }

                            ///nokia-state/state/log/event-trigger/port/entry/statistics/filter-fail
                            leaf filter-fail {
                                type yang:counter32;
                                description
                                    "Indicates the number of times a filter, for the specified trigger entry,
                                     does not match an logger event.";
                            }

                            ///nokia-state/state/log/event-trigger/port/entry/statistics/error-admin-state
                            leaf error-admin-state {
                                type yang:counter32;
                                description
                                    "Indicates the number of times the logger event will be ignored due to
                                     admin state of EHS trigger entry is out-of-service.";
                            }

                            ///nokia-state/state/log/event-trigger/port/entry/statistics/error-filter
                            leaf error-filter {
                                type yang:counter32;
                                description
                                    "Indicates the number of times the logger event will be ignored due to filter
                                     is not operational or is not configured in EHS trigger entry.";
                            }

                            ///nokia-state/state/log/event-trigger/port/entry/statistics/error-handler
                            leaf error-handler {
                                type yang:counter32;
                                description
                                    "Indicates the number of times the logger event will be ignored due to handler
                                     is not operational or is not configured in EHS trigger entry.";
                            }

                            ///nokia-state/state/log/event-trigger/port/entry/statistics/trigger-count
                            leaf trigger-count {
                                type yang:counter32;
                                description
                                    "Indicates the number of times script execution is triggered after filter match
                                     for the specified trigger entry.";
                            }

                            ///nokia-state/state/log/event-trigger/port/entry/statistics/debounce-count
                            leaf debounce-count {
                                type yang:counter32;
                                description
                                    "Indicates the number of times script is not executed due to debounce rule
                                     for the specified trigger entry.";
                            }

                        } // container statistics

                    } // list entry

                } // list port

                ///nokia-state/state/log/event-trigger/pppoe
                list pppoe {
                    key "event";
                    description "Enter the pppoe list instance";

                    ///nokia-state/state/log/event-trigger/pppoe/event
                    leaf event {
                        type types-log:pppoe-events;
                        description "Log event as a trigger for one or more EHS handlers";
                    }

                    ///nokia-state/state/log/event-trigger/pppoe/oper-state
                    leaf oper-state {
                        type types-sros:oper-state;
                        description "Indicates the operational state of the EHS Event Trigger.";
                    }

                    ///nokia-state/state/log/event-trigger/pppoe/statistics
                    container statistics {
                        description "Enter the statistics context";

                        ///nokia-state/state/log/event-trigger/pppoe/statistics/success
                        leaf success {
                            type yang:counter32;
                            description
                                "Indicates the number of not ignored logger event occurrences
                                 associated with EHS trigger.";
                        }

                        ///nokia-state/state/log/event-trigger/pppoe/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pppoe/statistics/error-admin-state
                        leaf error-admin-state {
                            type yang:counter32;
                            description
                                "Indicates the number of ignored logger event occurrences associated
                                 with EHS trigger.

                                 Event is ignored due to trigger may be out-of-service.";
                        }

                        ///nokia-state/state/log/event-trigger/pppoe/statistics/total
                        leaf total {
                            type yang:counter32;
                            description "Sum of success + error-no-entry + error-admin-state.";
                        }

                    } // container statistics

                    ///nokia-state/state/log/event-trigger/pppoe/summary-entry-statistics
                    container summary-entry-statistics {
                        description "Enter the summary-entry-statistics context";

                        ///nokia-state/state/log/event-trigger/pppoe/summary-entry-statistics/filter-match
                        leaf filter-match {
                            type yang:counter32;
                            description "Indicates the number of times a filter matches an logger event.";
                        }

                        ///nokia-state/state/log/event-trigger/pppoe/summary-entry-statistics/filter-fail
                        leaf filter-fail {
                            type yang:counter32;
                            description "Indicates the number of times a filter does not match an logger event.";
                        }

                        ///nokia-state/state/log/event-trigger/pppoe/summary-entry-statistics/error-admin-state
                        leaf error-admin-state {
                            type yang:counter32;
                            description
                                "Indicates the number of times the logger event will be ignored due to
                                 admin state of EHS trigger entries is out-of-service.";
                        }

                        ///nokia-state/state/log/event-trigger/pppoe/summary-entry-statistics/error-filter
                        leaf error-filter {
                            type yang:counter32;
                            description
                                "Indicates the number of times the logger event will be ignored due to filter
                                 is not operational or is not configured in EHS trigger entries.";
                        }

                        ///nokia-state/state/log/event-trigger/pppoe/summary-entry-statistics/error-handler
                        leaf error-handler {
                            type yang:counter32;
                            description
                                "Indicates the number of times the logger event will be ignored due to handler
                                 is not operational or is not configured in EHS trigger entries.";
                        }

                        ///nokia-state/state/log/event-trigger/pppoe/summary-entry-statistics/trigger-count
                        leaf trigger-count {
                            type yang:counter32;
                            description "Indicates the number of times script execution is triggered after filter match.";
                        }

                        ///nokia-state/state/log/event-trigger/pppoe/summary-entry-statistics/debounce-count
                        leaf debounce-count {
                            type yang:counter32;
                            description "Indicates the number of times script is not executed due to debounce rule.";
                        }

                    } // container summary-entry-statistics

                    ///nokia-state/state/log/event-trigger/pppoe/entry
                    list entry {
                        key "id";
                        description "Enter the entry list instance";

                        ///nokia-state/state/log/event-trigger/pppoe/entry/id
                        leaf id {
                            type uint32 {
                                range "1..1500";
                            }
                            description "ID of the EHS event trigger entry";
                        }

                        ///nokia-state/state/log/event-trigger/pppoe/entry/oper-state
                        leaf oper-state {
                            type types-sros:oper-state;
                            description "Indicates the operational state of the EHS Event Trigger Entry.";
                        }

                        ///nokia-state/state/log/event-trigger/pppoe/entry/statistics
                        container statistics {
                            description "Enter the statistics context";

                            ///nokia-state/state/log/event-trigger/pppoe/entry/statistics/filter-match
                            leaf filter-match {
                                type yang:counter32;
                                description
                                    "Indicates the number of times a filter, for the specified trigger entry,
                                     matches an logger event.";
                            }

                            ///nokia-state/state/log/event-trigger/pppoe/entry/statistics/filter-fail
                            leaf filter-fail {
                                type yang:counter32;
                                description
                                    "Indicates the number of times a filter, for the specified trigger entry,
                                     does not match an logger event.";
                            }

                            ///nokia-state/state/log/event-trigger/pppoe/entry/statistics/error-admin-state
                            leaf error-admin-state {
                                type yang:counter32;
                                description
                                    "Indicates the number of times the logger event will be ignored due to
                                     admin state of EHS trigger entry is out-of-service.";
                            }

                            ///nokia-state/state/log/event-trigger/pppoe/entry/statistics/error-filter
                            leaf error-filter {
                                type yang:counter32;
                                description
                                    "Indicates the number of times the logger event will be ignored due to filter
                                     is not operational or is not configured in EHS trigger entry.";
                            }

                            ///nokia-state/state/log/event-trigger/pppoe/entry/statistics/error-handler
                            leaf error-handler {
                                type yang:counter32;
                                description
                                    "Indicates the number of times the logger event will be ignored due to handler
                                     is not operational or is not configured in EHS trigger entry.";
                            }

                            ///nokia-state/state/log/event-trigger/pppoe/entry/statistics/trigger-count
                            leaf trigger-count {
                                type yang:counter32;
                                description
                                    "Indicates the number of times script execution is triggered after filter match
                                     for the specified trigger entry.";
                            }

                            ///nokia-state/state/log/event-trigger/pppoe/entry/statistics/debounce-count
                            leaf debounce-count {
                                type yang:counter32;
                                description
                                    "Indicates the number of times script is not executed due to debounce rule
                                     for the specified trigger entry.";
                            }

                        } // container statistics

                    } // list entry

                } // list pppoe

                ///nokia-state/state/log/event-trigger/pppoe-clnt
                list pppoe-clnt {
                    key "event";
                    description "Enter the pppoe-clnt list instance";

                    ///nokia-state/state/log/event-trigger/pppoe-clnt/event
                    leaf event {
                        type types-log:pppoe-clnt-events;
                        description "Log event as a trigger for one or more EHS handlers";
                    }

                    ///nokia-state/state/log/event-trigger/pppoe-clnt/oper-state
                    leaf oper-state {
                        type types-sros:oper-state;
                        description "Indicates the operational state of the EHS Event Trigger.";
                    }

                    ///nokia-state/state/log/event-trigger/pppoe-clnt/statistics
                    container statistics {
                        description "Enter the statistics context";

                        ///nokia-state/state/log/event-trigger/pppoe-clnt/statistics/success
                        leaf success {
                            type yang:counter32;
                            description
                                "Indicates the number of not ignored logger event occurrences
                                 associated with EHS trigger.";
                        }

                        ///nokia-state/state/log/event-trigger/pppoe-clnt/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/pppoe-clnt/statistics/error-admin-state
                        leaf error-admin-state {
                            type yang:counter32;
                            description
                                "Indicates the number of ignored logger event occurrences associated
                                 with EHS trigger.

                                 Event is ignored due to trigger may be out-of-service.";
                        }

                        ///nokia-state/state/log/event-trigger/pppoe-clnt/statistics/total
                        leaf total {
                            type yang:counter32;
                            description "Sum of success + error-no-entry + error-admin-state.";
                        }

                    } // container statistics

                    ///nokia-state/state/log/event-trigger/pppoe-clnt/summary-entry-statistics
                    container summary-entry-statistics {
                        description "Enter the summary-entry-statistics context";

                        ///nokia-state/state/log/event-trigger/pppoe-clnt/summary-entry-statistics/filter-match
                        leaf filter-match {
                            type yang:counter32;
                            description "Indicates the number of times a filter matches an logger event.";
                        }

                        ///nokia-state/state/log/event-trigger/pppoe-clnt/summary-entry-statistics/filter-fail
                        leaf filter-fail {
                            type yang:counter32;
                            description "Indicates the number of times a filter does not match an logger event.";
                        }

                        ///nokia-state/state/log/event-trigger/pppoe-clnt/summary-entry-statistics/error-admin-state
                        leaf error-admin-state {
                            type yang:counter32;
                            description
                                "Indicates the number of times the logger event will be ignored due to
                                 admin state of EHS trigger entries is out-of-service.";
                        }

                        ///nokia-state/state/log/event-trigger/pppoe-clnt/summary-entry-statistics/error-filter
                        leaf error-filter {
                            type yang:counter32;
                            description
                                "Indicates the number of times the logger event will be ignored due to filter
                                 is not operational or is not configured in EHS trigger entries.";
                        }

                        ///nokia-state/state/log/event-trigger/pppoe-clnt/summary-entry-statistics/error-handler
                        leaf error-handler {
                            type yang:counter32;
                            description
                                "Indicates the number of times the logger event will be ignored due to handler
                                 is not operational or is not configured in EHS trigger entries.";
                        }

                        ///nokia-state/state/log/event-trigger/pppoe-clnt/summary-entry-statistics/trigger-count
                        leaf trigger-count {
                            type yang:counter32;
                            description "Indicates the number of times script execution is triggered after filter match.";
                        }

                        ///nokia-state/state/log/event-trigger/pppoe-clnt/summary-entry-statistics/debounce-count
                        leaf debounce-count {
                            type yang:counter32;
                            description "Indicates the number of times script is not executed due to debounce rule.";
                        }

                    } // container summary-entry-statistics

                    ///nokia-state/state/log/event-trigger/pppoe-clnt/entry
                    list entry {
                        key "id";
                        description "Enter the entry list instance";

                        ///nokia-state/state/log/event-trigger/pppoe-clnt/entry/id
                        leaf id {
                            type uint32 {
                                range "1..1500";
                            }
                            description "ID of the EHS event trigger entry";
                        }

                        ///nokia-state/state/log/event-trigger/pppoe-clnt/entry/oper-state
                        leaf oper-state {
                            type types-sros:oper-state;
                            description "Indicates the operational state of the EHS Event Trigger Entry.";
                        }

                        ///nokia-state/state/log/event-trigger/pppoe-clnt/entry/statistics
                        container statistics {
                            description "Enter the statistics context";

                            ///nokia-state/state/log/event-trigger/pppoe-clnt/entry/statistics/filter-match
                            leaf filter-match {
                                type yang:counter32;
                                description
                                    "Indicates the number of times a filter, for the specified trigger entry,
                                     matches an logger event.";
                            }

                            ///nokia-state/state/log/event-trigger/pppoe-clnt/entry/statistics/filter-fail
                            leaf filter-fail {
                                type yang:counter32;
                                description
                                    "Indicates the number of times a filter, for the specified trigger entry,
                                     does not match an logger event.";
                            }

                            ///nokia-state/state/log/event-trigger/pppoe-clnt/entry/statistics/error-admin-state
                            leaf error-admin-state {
                                type yang:counter32;
                                description
                                    "Indicates the number of times the logger event will be ignored due to
                                     admin state of EHS trigger entry is out-of-service.";
                            }

                            ///nokia-state/state/log/event-trigger/pppoe-clnt/entry/statistics/error-filter
                            leaf error-filter {
                                type yang:counter32;
                                description
                                    "Indicates the number of times the logger event will be ignored due to filter
                                     is not operational or is not configured in EHS trigger entry.";
                            }

                            ///nokia-state/state/log/event-trigger/pppoe-clnt/entry/statistics/error-handler
                            leaf error-handler {
                                type yang:counter32;
                                description
                                    "Indicates the number of times the logger event will be ignored due to handler
                                     is not operational or is not configured in EHS trigger entry.";
                            }

                            ///nokia-state/state/log/event-trigger/pppoe-clnt/entry/statistics/trigger-count
                            leaf trigger-count {
                                type yang:counter32;
                                description
                                    "Indicates the number of times script execution is triggered after filter match
                                     for the specified trigger entry.";
                            }

                            ///nokia-state/state/log/event-trigger/pppoe-clnt/entry/statistics/debounce-count
                            leaf debounce-count {
                                type yang:counter32;
                                description
                                    "Indicates the number of times script is not executed due to debounce rule
                                     for the specified trigger entry.";
                            }

                        } // container statistics

                    } // list entry

                } // list pppoe-clnt

                ///nokia-state/state/log/event-trigger/ptp
                list ptp {
                    key "event";
                    description "Enter the ptp list instance";

                    ///nokia-state/state/log/event-trigger/ptp/event
                    leaf event {
                        type types-log:ptp-events;
                        description "Log event as a trigger for one or more EHS handlers";
                    }

                    ///nokia-state/state/log/event-trigger/ptp/oper-state
                    leaf oper-state {
                        type types-sros:oper-state;
                        description "Indicates the operational state of the EHS Event Trigger.";
                    }

                    ///nokia-state/state/log/event-trigger/ptp/statistics
                    container statistics {
                        description "Enter the statistics context";

                        ///nokia-state/state/log/event-trigger/ptp/statistics/success
                        leaf success {
                            type yang:counter32;
                            description
                                "Indicates the number of not ignored logger event occurrences
                                 associated with EHS trigger.";
                        }

                        ///nokia-state/state/log/event-trigger/ptp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ptp/statistics/error-admin-state
                        leaf error-admin-state {
                            type yang:counter32;
                            description
                                "Indicates the number of ignored logger event occurrences associated
                                 with EHS trigger.

                                 Event is ignored due to trigger may be out-of-service.";
                        }

                        ///nokia-state/state/log/event-trigger/ptp/statistics/total
                        leaf total {
                            type yang:counter32;
                            description "Sum of success + error-no-entry + error-admin-state.";
                        }

                    } // container statistics

                    ///nokia-state/state/log/event-trigger/ptp/summary-entry-statistics
                    container summary-entry-statistics {
                        description "Enter the summary-entry-statistics context";

                        ///nokia-state/state/log/event-trigger/ptp/summary-entry-statistics/filter-match
                        leaf filter-match {
                            type yang:counter32;
                            description "Indicates the number of times a filter matches an logger event.";
                        }

                        ///nokia-state/state/log/event-trigger/ptp/summary-entry-statistics/filter-fail
                        leaf filter-fail {
                            type yang:counter32;
                            description "Indicates the number of times a filter does not match an logger event.";
                        }

                        ///nokia-state/state/log/event-trigger/ptp/summary-entry-statistics/error-admin-state
                        leaf error-admin-state {
                            type yang:counter32;
                            description
                                "Indicates the number of times the logger event will be ignored due to
                                 admin state of EHS trigger entries is out-of-service.";
                        }

                        ///nokia-state/state/log/event-trigger/ptp/summary-entry-statistics/error-filter
                        leaf error-filter {
                            type yang:counter32;
                            description
                                "Indicates the number of times the logger event will be ignored due to filter
                                 is not operational or is not configured in EHS trigger entries.";
                        }

                        ///nokia-state/state/log/event-trigger/ptp/summary-entry-statistics/error-handler
                        leaf error-handler {
                            type yang:counter32;
                            description
                                "Indicates the number of times the logger event will be ignored due to handler
                                 is not operational or is not configured in EHS trigger entries.";
                        }

                        ///nokia-state/state/log/event-trigger/ptp/summary-entry-statistics/trigger-count
                        leaf trigger-count {
                            type yang:counter32;
                            description "Indicates the number of times script execution is triggered after filter match.";
                        }

                        ///nokia-state/state/log/event-trigger/ptp/summary-entry-statistics/debounce-count
                        leaf debounce-count {
                            type yang:counter32;
                            description "Indicates the number of times script is not executed due to debounce rule.";
                        }

                    } // container summary-entry-statistics

                    ///nokia-state/state/log/event-trigger/ptp/entry
                    list entry {
                        key "id";
                        description "Enter the entry list instance";

                        ///nokia-state/state/log/event-trigger/ptp/entry/id
                        leaf id {
                            type uint32 {
                                range "1..1500";
                            }
                            description "ID of the EHS event trigger entry";
                        }

                        ///nokia-state/state/log/event-trigger/ptp/entry/oper-state
                        leaf oper-state {
                            type types-sros:oper-state;
                            description "Indicates the operational state of the EHS Event Trigger Entry.";
                        }

                        ///nokia-state/state/log/event-trigger/ptp/entry/statistics
                        container statistics {
                            description "Enter the statistics context";

                            ///nokia-state/state/log/event-trigger/ptp/entry/statistics/filter-match
                            leaf filter-match {
                                type yang:counter32;
                                description
                                    "Indicates the number of times a filter, for the specified trigger entry,
                                     matches an logger event.";
                            }

                            ///nokia-state/state/log/event-trigger/ptp/entry/statistics/filter-fail
                            leaf filter-fail {
                                type yang:counter32;
                                description
                                    "Indicates the number of times a filter, for the specified trigger entry,
                                     does not match an logger event.";
                            }

                            ///nokia-state/state/log/event-trigger/ptp/entry/statistics/error-admin-state
                            leaf error-admin-state {
                                type yang:counter32;
                                description
                                    "Indicates the number of times the logger event will be ignored due to
                                     admin state of EHS trigger entry is out-of-service.";
                            }

                            ///nokia-state/state/log/event-trigger/ptp/entry/statistics/error-filter
                            leaf error-filter {
                                type yang:counter32;
                                description
                                    "Indicates the number of times the logger event will be ignored due to filter
                                     is not operational or is not configured in EHS trigger entry.";
                            }

                            ///nokia-state/state/log/event-trigger/ptp/entry/statistics/error-handler
                            leaf error-handler {
                                type yang:counter32;
                                description
                                    "Indicates the number of times the logger event will be ignored due to handler
                                     is not operational or is not configured in EHS trigger entry.";
                            }

                            ///nokia-state/state/log/event-trigger/ptp/entry/statistics/trigger-count
                            leaf trigger-count {
                                type yang:counter32;
                                description
                                    "Indicates the number of times script execution is triggered after filter match
                                     for the specified trigger entry.";
                            }

                            ///nokia-state/state/log/event-trigger/ptp/entry/statistics/debounce-count
                            leaf debounce-count {
                                type yang:counter32;
                                description
                                    "Indicates the number of times script is not executed due to debounce rule
                                     for the specified trigger entry.";
                            }

                        } // container statistics

                    } // list entry

                } // list ptp

                ///nokia-state/state/log/event-trigger/python
                list python {
                    key "event";
                    description "Enter the python list instance";

                    ///nokia-state/state/log/event-trigger/python/event
                    leaf event {
                        type types-log:python-events;
                        description "Python module events";
                    }

                    ///nokia-state/state/log/event-trigger/python/oper-state
                    leaf oper-state {
                        type types-sros:oper-state;
                        description "Indicates the operational state of the EHS Event Trigger.";
                    }

                    ///nokia-state/state/log/event-trigger/python/statistics
                    container statistics {
                        description "Enter the statistics context";

                        ///nokia-state/state/log/event-trigger/python/statistics/success
                        leaf success {
                            type yang:counter32;
                            description
                                "Indicates the number of not ignored logger event occurrences
                                 associated with EHS trigger.";
                        }

                        ///nokia-state/state/log/event-trigger/python/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/python/statistics/error-admin-state
                        leaf error-admin-state {
                            type yang:counter32;
                            description
                                "Indicates the number of ignored logger event occurrences associated
                                 with EHS trigger.

                                 Event is ignored due to trigger may be out-of-service.";
                        }

                        ///nokia-state/state/log/event-trigger/python/statistics/total
                        leaf total {
                            type yang:counter32;
                            description "Sum of success + error-no-entry + error-admin-state.";
                        }

                    } // container statistics

                    ///nokia-state/state/log/event-trigger/python/summary-entry-statistics
                    container summary-entry-statistics {
                        description "Enter the summary-entry-statistics context";

                        ///nokia-state/state/log/event-trigger/python/summary-entry-statistics/filter-match
                        leaf filter-match {
                            type yang:counter32;
                            description "Indicates the number of times a filter matches an logger event.";
                        }

                        ///nokia-state/state/log/event-trigger/python/summary-entry-statistics/filter-fail
                        leaf filter-fail {
                            type yang:counter32;
                            description "Indicates the number of times a filter does not match an logger event.";
                        }

                        ///nokia-state/state/log/event-trigger/python/summary-entry-statistics/error-admin-state
                        leaf error-admin-state {
                            type yang:counter32;
                            description
                                "Indicates the number of times the logger event will be ignored due to
                                 admin state of EHS trigger entries is out-of-service.";
                        }

                        ///nokia-state/state/log/event-trigger/python/summary-entry-statistics/error-filter
                        leaf error-filter {
                            type yang:counter32;
                            description
                                "Indicates the number of times the logger event will be ignored due to filter
                                 is not operational or is not configured in EHS trigger entries.";
                        }

                        ///nokia-state/state/log/event-trigger/python/summary-entry-statistics/error-handler
                        leaf error-handler {
                            type yang:counter32;
                            description
                                "Indicates the number of times the logger event will be ignored due to handler
                                 is not operational or is not configured in EHS trigger entries.";
                        }

                        ///nokia-state/state/log/event-trigger/python/summary-entry-statistics/trigger-count
                        leaf trigger-count {
                            type yang:counter32;
                            description "Indicates the number of times script execution is triggered after filter match.";
                        }

                        ///nokia-state/state/log/event-trigger/python/summary-entry-statistics/debounce-count
                        leaf debounce-count {
                            type yang:counter32;
                            description "Indicates the number of times script is not executed due to debounce rule.";
                        }

                    } // container summary-entry-statistics

                    ///nokia-state/state/log/event-trigger/python/entry
                    list entry {
                        key "id";
                        description "Enter the entry list instance";

                        ///nokia-state/state/log/event-trigger/python/entry/id
                        leaf id {
                            type uint32 {
                                range "1..1500";
                            }
                            description "ID of the EHS event trigger entry";
                        }

                        ///nokia-state/state/log/event-trigger/python/entry/oper-state
                        leaf oper-state {
                            type types-sros:oper-state;
                            description "Indicates the operational state of the EHS Event Trigger Entry.";
                        }

                        ///nokia-state/state/log/event-trigger/python/entry/statistics
                        container statistics {
                            description "Enter the statistics context";

                            ///nokia-state/state/log/event-trigger/python/entry/statistics/filter-match
                            leaf filter-match {
                                type yang:counter32;
                                description
                                    "Indicates the number of times a filter, for the specified trigger entry,
                                     matches an logger event.";
                            }

                            ///nokia-state/state/log/event-trigger/python/entry/statistics/filter-fail
                            leaf filter-fail {
                                type yang:counter32;
                                description
                                    "Indicates the number of times a filter, for the specified trigger entry,
                                     does not match an logger event.";
                            }

                            ///nokia-state/state/log/event-trigger/python/entry/statistics/error-admin-state
                            leaf error-admin-state {
                                type yang:counter32;
                                description
                                    "Indicates the number of times the logger event will be ignored due to
                                     admin state of EHS trigger entry is out-of-service.";
                            }

                            ///nokia-state/state/log/event-trigger/python/entry/statistics/error-filter
                            leaf error-filter {
                                type yang:counter32;
                                description
                                    "Indicates the number of times the logger event will be ignored due to filter
                                     is not operational or is not configured in EHS trigger entry.";
                            }

                            ///nokia-state/state/log/event-trigger/python/entry/statistics/error-handler
                            leaf error-handler {
                                type yang:counter32;
                                description
                                    "Indicates the number of times the logger event will be ignored due to handler
                                     is not operational or is not configured in EHS trigger entry.";
                            }

                            ///nokia-state/state/log/event-trigger/python/entry/statistics/trigger-count
                            leaf trigger-count {
                                type yang:counter32;
                                description
                                    "Indicates the number of times script execution is triggered after filter match
                                     for the specified trigger entry.";
                            }

                            ///nokia-state/state/log/event-trigger/python/entry/statistics/debounce-count
                            leaf debounce-count {
                                type yang:counter32;
                                description
                                    "Indicates the number of times script is not executed due to debounce rule
                                     for the specified trigger entry.";
                            }

                        } // container statistics

                    } // list entry

                } // list python

                ///nokia-state/state/log/event-trigger/radius
                list radius {
                    key "event";
                    description "Enter the radius list instance";

                    ///nokia-state/state/log/event-trigger/radius/event
                    leaf event {
                        type types-log:radius-events;
                        description "Log event as a trigger for one or more EHS handlers";
                    }

                    ///nokia-state/state/log/event-trigger/radius/oper-state
                    leaf oper-state {
                        type types-sros:oper-state;
                        description "Indicates the operational state of the EHS Event Trigger.";
                    }

                    ///nokia-state/state/log/event-trigger/radius/statistics
                    container statistics {
                        description "Enter the statistics context";

                        ///nokia-state/state/log/event-trigger/radius/statistics/success
                        leaf success {
                            type yang:counter32;
                            description
                                "Indicates the number of not ignored logger event occurrences
                                 associated with EHS trigger.";
                        }

                        ///nokia-state/state/log/event-trigger/radius/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/radius/statistics/error-admin-state
                        leaf error-admin-state {
                            type yang:counter32;
                            description
                                "Indicates the number of ignored logger event occurrences associated
                                 with EHS trigger.

                                 Event is ignored due to trigger may be out-of-service.";
                        }

                        ///nokia-state/state/log/event-trigger/radius/statistics/total
                        leaf total {
                            type yang:counter32;
                            description "Sum of success + error-no-entry + error-admin-state.";
                        }

                    } // container statistics

                    ///nokia-state/state/log/event-trigger/radius/summary-entry-statistics
                    container summary-entry-statistics {
                        description "Enter the summary-entry-statistics context";

                        ///nokia-state/state/log/event-trigger/radius/summary-entry-statistics/filter-match
                        leaf filter-match {
                            type yang:counter32;
                            description "Indicates the number of times a filter matches an logger event.";
                        }

                        ///nokia-state/state/log/event-trigger/radius/summary-entry-statistics/filter-fail
                        leaf filter-fail {
                            type yang:counter32;
                            description "Indicates the number of times a filter does not match an logger event.";
                        }

                        ///nokia-state/state/log/event-trigger/radius/summary-entry-statistics/error-admin-state
                        leaf error-admin-state {
                            type yang:counter32;
                            description
                                "Indicates the number of times the logger event will be ignored due to
                                 admin state of EHS trigger entries is out-of-service.";
                        }

                        ///nokia-state/state/log/event-trigger/radius/summary-entry-statistics/error-filter
                        leaf error-filter {
                            type yang:counter32;
                            description
                                "Indicates the number of times the logger event will be ignored due to filter
                                 is not operational or is not configured in EHS trigger entries.";
                        }

                        ///nokia-state/state/log/event-trigger/radius/summary-entry-statistics/error-handler
                        leaf error-handler {
                            type yang:counter32;
                            description
                                "Indicates the number of times the logger event will be ignored due to handler
                                 is not operational or is not configured in EHS trigger entries.";
                        }

                        ///nokia-state/state/log/event-trigger/radius/summary-entry-statistics/trigger-count
                        leaf trigger-count {
                            type yang:counter32;
                            description "Indicates the number of times script execution is triggered after filter match.";
                        }

                        ///nokia-state/state/log/event-trigger/radius/summary-entry-statistics/debounce-count
                        leaf debounce-count {
                            type yang:counter32;
                            description "Indicates the number of times script is not executed due to debounce rule.";
                        }

                    } // container summary-entry-statistics

                    ///nokia-state/state/log/event-trigger/radius/entry
                    list entry {
                        key "id";
                        description "Enter the entry list instance";

                        ///nokia-state/state/log/event-trigger/radius/entry/id
                        leaf id {
                            type uint32 {
                                range "1..1500";
                            }
                            description "ID of the EHS event trigger entry";
                        }

                        ///nokia-state/state/log/event-trigger/radius/entry/oper-state
                        leaf oper-state {
                            type types-sros:oper-state;
                            description "Indicates the operational state of the EHS Event Trigger Entry.";
                        }

                        ///nokia-state/state/log/event-trigger/radius/entry/statistics
                        container statistics {
                            description "Enter the statistics context";

                            ///nokia-state/state/log/event-trigger/radius/entry/statistics/filter-match
                            leaf filter-match {
                                type yang:counter32;
                                description
                                    "Indicates the number of times a filter, for the specified trigger entry,
                                     matches an logger event.";
                            }

                            ///nokia-state/state/log/event-trigger/radius/entry/statistics/filter-fail
                            leaf filter-fail {
                                type yang:counter32;
                                description
                                    "Indicates the number of times a filter, for the specified trigger entry,
                                     does not match an logger event.";
                            }

                            ///nokia-state/state/log/event-trigger/radius/entry/statistics/error-admin-state
                            leaf error-admin-state {
                                type yang:counter32;
                                description
                                    "Indicates the number of times the logger event will be ignored due to
                                     admin state of EHS trigger entry is out-of-service.";
                            }

                            ///nokia-state/state/log/event-trigger/radius/entry/statistics/error-filter
                            leaf error-filter {
                                type yang:counter32;
                                description
                                    "Indicates the number of times the logger event will be ignored due to filter
                                     is not operational or is not configured in EHS trigger entry.";
                            }

                            ///nokia-state/state/log/event-trigger/radius/entry/statistics/error-handler
                            leaf error-handler {
                                type yang:counter32;
                                description
                                    "Indicates the number of times the logger event will be ignored due to handler
                                     is not operational or is not configured in EHS trigger entry.";
                            }

                            ///nokia-state/state/log/event-trigger/radius/entry/statistics/trigger-count
                            leaf trigger-count {
                                type yang:counter32;
                                description
                                    "Indicates the number of times script execution is triggered after filter match
                                     for the specified trigger entry.";
                            }

                            ///nokia-state/state/log/event-trigger/radius/entry/statistics/debounce-count
                            leaf debounce-count {
                                type yang:counter32;
                                description
                                    "Indicates the number of times script is not executed due to debounce rule
                                     for the specified trigger entry.";
                            }

                        } // container statistics

                    } // list entry

                } // list radius

                ///nokia-state/state/log/event-trigger/rip
                list rip {
                    key "event";
                    description "Enter the rip list instance";

                    ///nokia-state/state/log/event-trigger/rip/event
                    leaf event {
                        type types-log:rip-events;
                        description "Log event as a trigger for one or more EHS handlers";
                    }

                    ///nokia-state/state/log/event-trigger/rip/oper-state
                    leaf oper-state {
                        type types-sros:oper-state;
                        description "Indicates the operational state of the EHS Event Trigger.";
                    }

                    ///nokia-state/state/log/event-trigger/rip/statistics
                    container statistics {
                        description "Enter the statistics context";

                        ///nokia-state/state/log/event-trigger/rip/statistics/success
                        leaf success {
                            type yang:counter32;
                            description
                                "Indicates the number of not ignored logger event occurrences
                                 associated with EHS trigger.";
                        }

                        ///nokia-state/state/log/event-trigger/rip/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/rip/statistics/error-admin-state
                        leaf error-admin-state {
                            type yang:counter32;
                            description
                                "Indicates the number of ignored logger event occurrences associated
                                 with EHS trigger.

                                 Event is ignored due to trigger may be out-of-service.";
                        }

                        ///nokia-state/state/log/event-trigger/rip/statistics/total
                        leaf total {
                            type yang:counter32;
                            description "Sum of success + error-no-entry + error-admin-state.";
                        }

                    } // container statistics

                    ///nokia-state/state/log/event-trigger/rip/summary-entry-statistics
                    container summary-entry-statistics {
                        description "Enter the summary-entry-statistics context";

                        ///nokia-state/state/log/event-trigger/rip/summary-entry-statistics/filter-match
                        leaf filter-match {
                            type yang:counter32;
                            description "Indicates the number of times a filter matches an logger event.";
                        }

                        ///nokia-state/state/log/event-trigger/rip/summary-entry-statistics/filter-fail
                        leaf filter-fail {
                            type yang:counter32;
                            description "Indicates the number of times a filter does not match an logger event.";
                        }

                        ///nokia-state/state/log/event-trigger/rip/summary-entry-statistics/error-admin-state
                        leaf error-admin-state {
                            type yang:counter32;
                            description
                                "Indicates the number of times the logger event will be ignored due to
                                 admin state of EHS trigger entries is out-of-service.";
                        }

                        ///nokia-state/state/log/event-trigger/rip/summary-entry-statistics/error-filter
                        leaf error-filter {
                            type yang:counter32;
                            description
                                "Indicates the number of times the logger event will be ignored due to filter
                                 is not operational or is not configured in EHS trigger entries.";
                        }

                        ///nokia-state/state/log/event-trigger/rip/summary-entry-statistics/error-handler
                        leaf error-handler {
                            type yang:counter32;
                            description
                                "Indicates the number of times the logger event will be ignored due to handler
                                 is not operational or is not configured in EHS trigger entries.";
                        }

                        ///nokia-state/state/log/event-trigger/rip/summary-entry-statistics/trigger-count
                        leaf trigger-count {
                            type yang:counter32;
                            description "Indicates the number of times script execution is triggered after filter match.";
                        }

                        ///nokia-state/state/log/event-trigger/rip/summary-entry-statistics/debounce-count
                        leaf debounce-count {
                            type yang:counter32;
                            description "Indicates the number of times script is not executed due to debounce rule.";
                        }

                    } // container summary-entry-statistics

                    ///nokia-state/state/log/event-trigger/rip/entry
                    list entry {
                        key "id";
                        description "Enter the entry list instance";

                        ///nokia-state/state/log/event-trigger/rip/entry/id
                        leaf id {
                            type uint32 {
                                range "1..1500";
                            }
                            description "ID of the EHS event trigger entry";
                        }

                        ///nokia-state/state/log/event-trigger/rip/entry/oper-state
                        leaf oper-state {
                            type types-sros:oper-state;
                            description "Indicates the operational state of the EHS Event Trigger Entry.";
                        }

                        ///nokia-state/state/log/event-trigger/rip/entry/statistics
                        container statistics {
                            description "Enter the statistics context";

                            ///nokia-state/state/log/event-trigger/rip/entry/statistics/filter-match
                            leaf filter-match {
                                type yang:counter32;
                                description
                                    "Indicates the number of times a filter, for the specified trigger entry,
                                     matches an logger event.";
                            }

                            ///nokia-state/state/log/event-trigger/rip/entry/statistics/filter-fail
                            leaf filter-fail {
                                type yang:counter32;
                                description
                                    "Indicates the number of times a filter, for the specified trigger entry,
                                     does not match an logger event.";
                            }

                            ///nokia-state/state/log/event-trigger/rip/entry/statistics/error-admin-state
                            leaf error-admin-state {
                                type yang:counter32;
                                description
                                    "Indicates the number of times the logger event will be ignored due to
                                     admin state of EHS trigger entry is out-of-service.";
                            }

                            ///nokia-state/state/log/event-trigger/rip/entry/statistics/error-filter
                            leaf error-filter {
                                type yang:counter32;
                                description
                                    "Indicates the number of times the logger event will be ignored due to filter
                                     is not operational or is not configured in EHS trigger entry.";
                            }

                            ///nokia-state/state/log/event-trigger/rip/entry/statistics/error-handler
                            leaf error-handler {
                                type yang:counter32;
                                description
                                    "Indicates the number of times the logger event will be ignored due to handler
                                     is not operational or is not configured in EHS trigger entry.";
                            }

                            ///nokia-state/state/log/event-trigger/rip/entry/statistics/trigger-count
                            leaf trigger-count {
                                type yang:counter32;
                                description
                                    "Indicates the number of times script execution is triggered after filter match
                                     for the specified trigger entry.";
                            }

                            ///nokia-state/state/log/event-trigger/rip/entry/statistics/debounce-count
                            leaf debounce-count {
                                type yang:counter32;
                                description
                                    "Indicates the number of times script is not executed due to debounce rule
                                     for the specified trigger entry.";
                            }

                        } // container statistics

                    } // list entry

                } // list rip

                ///nokia-state/state/log/event-trigger/ripng
                list ripng {
                    key "event";
                    description "Enter the ripng list instance";

                    ///nokia-state/state/log/event-trigger/ripng/event
                    leaf event {
                        type types-log:ripng-events;
                        description "Log event as a trigger for one or more EHS handlers";
                    }

                    ///nokia-state/state/log/event-trigger/ripng/oper-state
                    leaf oper-state {
                        type types-sros:oper-state;
                        description "Indicates the operational state of the EHS Event Trigger.";
                    }

                    ///nokia-state/state/log/event-trigger/ripng/statistics
                    container statistics {
                        description "Enter the statistics context";

                        ///nokia-state/state/log/event-trigger/ripng/statistics/success
                        leaf success {
                            type yang:counter32;
                            description
                                "Indicates the number of not ignored logger event occurrences
                                 associated with EHS trigger.";
                        }

                        ///nokia-state/state/log/event-trigger/ripng/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/ripng/statistics/error-admin-state
                        leaf error-admin-state {
                            type yang:counter32;
                            description
                                "Indicates the number of ignored logger event occurrences associated
                                 with EHS trigger.

                                 Event is ignored due to trigger may be out-of-service.";
                        }

                        ///nokia-state/state/log/event-trigger/ripng/statistics/total
                        leaf total {
                            type yang:counter32;
                            description "Sum of success + error-no-entry + error-admin-state.";
                        }

                    } // container statistics

                    ///nokia-state/state/log/event-trigger/ripng/summary-entry-statistics
                    container summary-entry-statistics {
                        description "Enter the summary-entry-statistics context";

                        ///nokia-state/state/log/event-trigger/ripng/summary-entry-statistics/filter-match
                        leaf filter-match {
                            type yang:counter32;
                            description "Indicates the number of times a filter matches an logger event.";
                        }

                        ///nokia-state/state/log/event-trigger/ripng/summary-entry-statistics/filter-fail
                        leaf filter-fail {
                            type yang:counter32;
                            description "Indicates the number of times a filter does not match an logger event.";
                        }

                        ///nokia-state/state/log/event-trigger/ripng/summary-entry-statistics/error-admin-state
                        leaf error-admin-state {
                            type yang:counter32;
                            description
                                "Indicates the number of times the logger event will be ignored due to
                                 admin state of EHS trigger entries is out-of-service.";
                        }

                        ///nokia-state/state/log/event-trigger/ripng/summary-entry-statistics/error-filter
                        leaf error-filter {
                            type yang:counter32;
                            description
                                "Indicates the number of times the logger event will be ignored due to filter
                                 is not operational or is not configured in EHS trigger entries.";
                        }

                        ///nokia-state/state/log/event-trigger/ripng/summary-entry-statistics/error-handler
                        leaf error-handler {
                            type yang:counter32;
                            description
                                "Indicates the number of times the logger event will be ignored due to handler
                                 is not operational or is not configured in EHS trigger entries.";
                        }

                        ///nokia-state/state/log/event-trigger/ripng/summary-entry-statistics/trigger-count
                        leaf trigger-count {
                            type yang:counter32;
                            description "Indicates the number of times script execution is triggered after filter match.";
                        }

                        ///nokia-state/state/log/event-trigger/ripng/summary-entry-statistics/debounce-count
                        leaf debounce-count {
                            type yang:counter32;
                            description "Indicates the number of times script is not executed due to debounce rule.";
                        }

                    } // container summary-entry-statistics

                    ///nokia-state/state/log/event-trigger/ripng/entry
                    list entry {
                        key "id";
                        description "Enter the entry list instance";

                        ///nokia-state/state/log/event-trigger/ripng/entry/id
                        leaf id {
                            type uint32 {
                                range "1..1500";
                            }
                            description "ID of the EHS event trigger entry";
                        }

                        ///nokia-state/state/log/event-trigger/ripng/entry/oper-state
                        leaf oper-state {
                            type types-sros:oper-state;
                            description "Indicates the operational state of the EHS Event Trigger Entry.";
                        }

                        ///nokia-state/state/log/event-trigger/ripng/entry/statistics
                        container statistics {
                            description "Enter the statistics context";

                            ///nokia-state/state/log/event-trigger/ripng/entry/statistics/filter-match
                            leaf filter-match {
                                type yang:counter32;
                                description
                                    "Indicates the number of times a filter, for the specified trigger entry,
                                     matches an logger event.";
                            }

                            ///nokia-state/state/log/event-trigger/ripng/entry/statistics/filter-fail
                            leaf filter-fail {
                                type yang:counter32;
                                description
                                    "Indicates the number of times a filter, for the specified trigger entry,
                                     does not match an logger event.";
                            }

                            ///nokia-state/state/log/event-trigger/ripng/entry/statistics/error-admin-state
                            leaf error-admin-state {
                                type yang:counter32;
                                description
                                    "Indicates the number of times the logger event will be ignored due to
                                     admin state of EHS trigger entry is out-of-service.";
                            }

                            ///nokia-state/state/log/event-trigger/ripng/entry/statistics/error-filter
                            leaf error-filter {
                                type yang:counter32;
                                description
                                    "Indicates the number of times the logger event will be ignored due to filter
                                     is not operational or is not configured in EHS trigger entry.";
                            }

                            ///nokia-state/state/log/event-trigger/ripng/entry/statistics/error-handler
                            leaf error-handler {
                                type yang:counter32;
                                description
                                    "Indicates the number of times the logger event will be ignored due to handler
                                     is not operational or is not configured in EHS trigger entry.";
                            }

                            ///nokia-state/state/log/event-trigger/ripng/entry/statistics/trigger-count
                            leaf trigger-count {
                                type yang:counter32;
                                description
                                    "Indicates the number of times script execution is triggered after filter match
                                     for the specified trigger entry.";
                            }

                            ///nokia-state/state/log/event-trigger/ripng/entry/statistics/debounce-count
                            leaf debounce-count {
                                type yang:counter32;
                                description
                                    "Indicates the number of times script is not executed due to debounce rule
                                     for the specified trigger entry.";
                            }

                        } // container statistics

                    } // list entry

                } // list ripng

                ///nokia-state/state/log/event-trigger/route-policy
                list route-policy {
                    key "event";
                    description "Enter the route-policy list instance";

                    ///nokia-state/state/log/event-trigger/route-policy/event
                    leaf event {
                        type types-log:route-policy-events;
                        description "Log event as a trigger for one or more EHS handlers";
                    }

                    ///nokia-state/state/log/event-trigger/route-policy/oper-state
                    leaf oper-state {
                        type types-sros:oper-state;
                        description "Indicates the operational state of the EHS Event Trigger.";
                    }

                    ///nokia-state/state/log/event-trigger/route-policy/statistics
                    container statistics {
                        description "Enter the statistics context";

                        ///nokia-state/state/log/event-trigger/route-policy/statistics/success
                        leaf success {
                            type yang:counter32;
                            description
                                "Indicates the number of not ignored logger event occurrences
                                 associated with EHS trigger.";
                        }

                        ///nokia-state/state/log/event-trigger/route-policy/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/route-policy/statistics/error-admin-state
                        leaf error-admin-state {
                            type yang:counter32;
                            description
                                "Indicates the number of ignored logger event occurrences associated
                                 with EHS trigger.

                                 Event is ignored due to trigger may be out-of-service.";
                        }

                        ///nokia-state/state/log/event-trigger/route-policy/statistics/total
                        leaf total {
                            type yang:counter32;
                            description "Sum of success + error-no-entry + error-admin-state.";
                        }

                    } // container statistics

                    ///nokia-state/state/log/event-trigger/route-policy/summary-entry-statistics
                    container summary-entry-statistics {
                        description "Enter the summary-entry-statistics context";

                        ///nokia-state/state/log/event-trigger/route-policy/summary-entry-statistics/filter-match
                        leaf filter-match {
                            type yang:counter32;
                            description "Indicates the number of times a filter matches an logger event.";
                        }

                        ///nokia-state/state/log/event-trigger/route-policy/summary-entry-statistics/filter-fail
                        leaf filter-fail {
                            type yang:counter32;
                            description "Indicates the number of times a filter does not match an logger event.";
                        }

                        ///nokia-state/state/log/event-trigger/route-policy/summary-entry-statistics/error-admin-state
                        leaf error-admin-state {
                            type yang:counter32;
                            description
                                "Indicates the number of times the logger event will be ignored due to
                                 admin state of EHS trigger entries is out-of-service.";
                        }

                        ///nokia-state/state/log/event-trigger/route-policy/summary-entry-statistics/error-filter
                        leaf error-filter {
                            type yang:counter32;
                            description
                                "Indicates the number of times the logger event will be ignored due to filter
                                 is not operational or is not configured in EHS trigger entries.";
                        }

                        ///nokia-state/state/log/event-trigger/route-policy/summary-entry-statistics/error-handler
                        leaf error-handler {
                            type yang:counter32;
                            description
                                "Indicates the number of times the logger event will be ignored due to handler
                                 is not operational or is not configured in EHS trigger entries.";
                        }

                        ///nokia-state/state/log/event-trigger/route-policy/summary-entry-statistics/trigger-count
                        leaf trigger-count {
                            type yang:counter32;
                            description "Indicates the number of times script execution is triggered after filter match.";
                        }

                        ///nokia-state/state/log/event-trigger/route-policy/summary-entry-statistics/debounce-count
                        leaf debounce-count {
                            type yang:counter32;
                            description "Indicates the number of times script is not executed due to debounce rule.";
                        }

                    } // container summary-entry-statistics

                    ///nokia-state/state/log/event-trigger/route-policy/entry
                    list entry {
                        key "id";
                        description "Enter the entry list instance";

                        ///nokia-state/state/log/event-trigger/route-policy/entry/id
                        leaf id {
                            type uint32 {
                                range "1..1500";
                            }
                            description "ID of the EHS event trigger entry";
                        }

                        ///nokia-state/state/log/event-trigger/route-policy/entry/oper-state
                        leaf oper-state {
                            type types-sros:oper-state;
                            description "Indicates the operational state of the EHS Event Trigger Entry.";
                        }

                        ///nokia-state/state/log/event-trigger/route-policy/entry/statistics
                        container statistics {
                            description "Enter the statistics context";

                            ///nokia-state/state/log/event-trigger/route-policy/entry/statistics/filter-match
                            leaf filter-match {
                                type yang:counter32;
                                description
                                    "Indicates the number of times a filter, for the specified trigger entry,
                                     matches an logger event.";
                            }

                            ///nokia-state/state/log/event-trigger/route-policy/entry/statistics/filter-fail
                            leaf filter-fail {
                                type yang:counter32;
                                description
                                    "Indicates the number of times a filter, for the specified trigger entry,
                                     does not match an logger event.";
                            }

                            ///nokia-state/state/log/event-trigger/route-policy/entry/statistics/error-admin-state
                            leaf error-admin-state {
                                type yang:counter32;
                                description
                                    "Indicates the number of times the logger event will be ignored due to
                                     admin state of EHS trigger entry is out-of-service.";
                            }

                            ///nokia-state/state/log/event-trigger/route-policy/entry/statistics/error-filter
                            leaf error-filter {
                                type yang:counter32;
                                description
                                    "Indicates the number of times the logger event will be ignored due to filter
                                     is not operational or is not configured in EHS trigger entry.";
                            }

                            ///nokia-state/state/log/event-trigger/route-policy/entry/statistics/error-handler
                            leaf error-handler {
                                type yang:counter32;
                                description
                                    "Indicates the number of times the logger event will be ignored due to handler
                                     is not operational or is not configured in EHS trigger entry.";
                            }

                            ///nokia-state/state/log/event-trigger/route-policy/entry/statistics/trigger-count
                            leaf trigger-count {
                                type yang:counter32;
                                description
                                    "Indicates the number of times script execution is triggered after filter match
                                     for the specified trigger entry.";
                            }

                            ///nokia-state/state/log/event-trigger/route-policy/entry/statistics/debounce-count
                            leaf debounce-count {
                                type yang:counter32;
                                description
                                    "Indicates the number of times script is not executed due to debounce rule
                                     for the specified trigger entry.";
                            }

                        } // container statistics

                    } // list entry

                } // list route-policy

                ///nokia-state/state/log/event-trigger/rpki
                list rpki {
                    key "event";
                    description "Enter the rpki list instance";

                    ///nokia-state/state/log/event-trigger/rpki/event
                    leaf event {
                        type types-log:rpki-events;
                        description "Log event as a trigger for one or more EHS handlers";
                    }

                    ///nokia-state/state/log/event-trigger/rpki/oper-state
                    leaf oper-state {
                        type types-sros:oper-state;
                        description "Indicates the operational state of the EHS Event Trigger.";
                    }

                    ///nokia-state/state/log/event-trigger/rpki/statistics
                    container statistics {
                        description "Enter the statistics context";

                        ///nokia-state/state/log/event-trigger/rpki/statistics/success
                        leaf success {
                            type yang:counter32;
                            description
                                "Indicates the number of not ignored logger event occurrences
                                 associated with EHS trigger.";
                        }

                        ///nokia-state/state/log/event-trigger/rpki/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/rpki/statistics/error-admin-state
                        leaf error-admin-state {
                            type yang:counter32;
                            description
                                "Indicates the number of ignored logger event occurrences associated
                                 with EHS trigger.

                                 Event is ignored due to trigger may be out-of-service.";
                        }

                        ///nokia-state/state/log/event-trigger/rpki/statistics/total
                        leaf total {
                            type yang:counter32;
                            description "Sum of success + error-no-entry + error-admin-state.";
                        }

                    } // container statistics

                    ///nokia-state/state/log/event-trigger/rpki/summary-entry-statistics
                    container summary-entry-statistics {
                        description "Enter the summary-entry-statistics context";

                        ///nokia-state/state/log/event-trigger/rpki/summary-entry-statistics/filter-match
                        leaf filter-match {
                            type yang:counter32;
                            description "Indicates the number of times a filter matches an logger event.";
                        }

                        ///nokia-state/state/log/event-trigger/rpki/summary-entry-statistics/filter-fail
                        leaf filter-fail {
                            type yang:counter32;
                            description "Indicates the number of times a filter does not match an logger event.";
                        }

                        ///nokia-state/state/log/event-trigger/rpki/summary-entry-statistics/error-admin-state
                        leaf error-admin-state {
                            type yang:counter32;
                            description
                                "Indicates the number of times the logger event will be ignored due to
                                 admin state of EHS trigger entries is out-of-service.";
                        }

                        ///nokia-state/state/log/event-trigger/rpki/summary-entry-statistics/error-filter
                        leaf error-filter {
                            type yang:counter32;
                            description
                                "Indicates the number of times the logger event will be ignored due to filter
                                 is not operational or is not configured in EHS trigger entries.";
                        }

                        ///nokia-state/state/log/event-trigger/rpki/summary-entry-statistics/error-handler
                        leaf error-handler {
                            type yang:counter32;
                            description
                                "Indicates the number of times the logger event will be ignored due to handler
                                 is not operational or is not configured in EHS trigger entries.";
                        }

                        ///nokia-state/state/log/event-trigger/rpki/summary-entry-statistics/trigger-count
                        leaf trigger-count {
                            type yang:counter32;
                            description "Indicates the number of times script execution is triggered after filter match.";
                        }

                        ///nokia-state/state/log/event-trigger/rpki/summary-entry-statistics/debounce-count
                        leaf debounce-count {
                            type yang:counter32;
                            description "Indicates the number of times script is not executed due to debounce rule.";
                        }

                    } // container summary-entry-statistics

                    ///nokia-state/state/log/event-trigger/rpki/entry
                    list entry {
                        key "id";
                        description "Enter the entry list instance";

                        ///nokia-state/state/log/event-trigger/rpki/entry/id
                        leaf id {
                            type uint32 {
                                range "1..1500";
                            }
                            description "ID of the EHS event trigger entry";
                        }

                        ///nokia-state/state/log/event-trigger/rpki/entry/oper-state
                        leaf oper-state {
                            type types-sros:oper-state;
                            description "Indicates the operational state of the EHS Event Trigger Entry.";
                        }

                        ///nokia-state/state/log/event-trigger/rpki/entry/statistics
                        container statistics {
                            description "Enter the statistics context";

                            ///nokia-state/state/log/event-trigger/rpki/entry/statistics/filter-match
                            leaf filter-match {
                                type yang:counter32;
                                description
                                    "Indicates the number of times a filter, for the specified trigger entry,
                                     matches an logger event.";
                            }

                            ///nokia-state/state/log/event-trigger/rpki/entry/statistics/filter-fail
                            leaf filter-fail {
                                type yang:counter32;
                                description
                                    "Indicates the number of times a filter, for the specified trigger entry,
                                     does not match an logger event.";
                            }

                            ///nokia-state/state/log/event-trigger/rpki/entry/statistics/error-admin-state
                            leaf error-admin-state {
                                type yang:counter32;
                                description
                                    "Indicates the number of times the logger event will be ignored due to
                                     admin state of EHS trigger entry is out-of-service.";
                            }

                            ///nokia-state/state/log/event-trigger/rpki/entry/statistics/error-filter
                            leaf error-filter {
                                type yang:counter32;
                                description
                                    "Indicates the number of times the logger event will be ignored due to filter
                                     is not operational or is not configured in EHS trigger entry.";
                            }

                            ///nokia-state/state/log/event-trigger/rpki/entry/statistics/error-handler
                            leaf error-handler {
                                type yang:counter32;
                                description
                                    "Indicates the number of times the logger event will be ignored due to handler
                                     is not operational or is not configured in EHS trigger entry.";
                            }

                            ///nokia-state/state/log/event-trigger/rpki/entry/statistics/trigger-count
                            leaf trigger-count {
                                type yang:counter32;
                                description
                                    "Indicates the number of times script execution is triggered after filter match
                                     for the specified trigger entry.";
                            }

                            ///nokia-state/state/log/event-trigger/rpki/entry/statistics/debounce-count
                            leaf debounce-count {
                                type yang:counter32;
                                description
                                    "Indicates the number of times script is not executed due to debounce rule
                                     for the specified trigger entry.";
                            }

                        } // container statistics

                    } // list entry

                } // list rpki

                ///nokia-state/state/log/event-trigger/rsvp
                list rsvp {
                    key "event";
                    description "Enter the rsvp list instance";

                    ///nokia-state/state/log/event-trigger/rsvp/event
                    leaf event {
                        type types-log:rsvp-events;
                        description "Log event as a trigger for one or more EHS handlers";
                    }

                    ///nokia-state/state/log/event-trigger/rsvp/oper-state
                    leaf oper-state {
                        type types-sros:oper-state;
                        description "Indicates the operational state of the EHS Event Trigger.";
                    }

                    ///nokia-state/state/log/event-trigger/rsvp/statistics
                    container statistics {
                        description "Enter the statistics context";

                        ///nokia-state/state/log/event-trigger/rsvp/statistics/success
                        leaf success {
                            type yang:counter32;
                            description
                                "Indicates the number of not ignored logger event occurrences
                                 associated with EHS trigger.";
                        }

                        ///nokia-state/state/log/event-trigger/rsvp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/rsvp/statistics/error-admin-state
                        leaf error-admin-state {
                            type yang:counter32;
                            description
                                "Indicates the number of ignored logger event occurrences associated
                                 with EHS trigger.

                                 Event is ignored due to trigger may be out-of-service.";
                        }

                        ///nokia-state/state/log/event-trigger/rsvp/statistics/total
                        leaf total {
                            type yang:counter32;
                            description "Sum of success + error-no-entry + error-admin-state.";
                        }

                    } // container statistics

                    ///nokia-state/state/log/event-trigger/rsvp/summary-entry-statistics
                    container summary-entry-statistics {
                        description "Enter the summary-entry-statistics context";

                        ///nokia-state/state/log/event-trigger/rsvp/summary-entry-statistics/filter-match
                        leaf filter-match {
                            type yang:counter32;
                            description "Indicates the number of times a filter matches an logger event.";
                        }

                        ///nokia-state/state/log/event-trigger/rsvp/summary-entry-statistics/filter-fail
                        leaf filter-fail {
                            type yang:counter32;
                            description "Indicates the number of times a filter does not match an logger event.";
                        }

                        ///nokia-state/state/log/event-trigger/rsvp/summary-entry-statistics/error-admin-state
                        leaf error-admin-state {
                            type yang:counter32;
                            description
                                "Indicates the number of times the logger event will be ignored due to
                                 admin state of EHS trigger entries is out-of-service.";
                        }

                        ///nokia-state/state/log/event-trigger/rsvp/summary-entry-statistics/error-filter
                        leaf error-filter {
                            type yang:counter32;
                            description
                                "Indicates the number of times the logger event will be ignored due to filter
                                 is not operational or is not configured in EHS trigger entries.";
                        }

                        ///nokia-state/state/log/event-trigger/rsvp/summary-entry-statistics/error-handler
                        leaf error-handler {
                            type yang:counter32;
                            description
                                "Indicates the number of times the logger event will be ignored due to handler
                                 is not operational or is not configured in EHS trigger entries.";
                        }

                        ///nokia-state/state/log/event-trigger/rsvp/summary-entry-statistics/trigger-count
                        leaf trigger-count {
                            type yang:counter32;
                            description "Indicates the number of times script execution is triggered after filter match.";
                        }

                        ///nokia-state/state/log/event-trigger/rsvp/summary-entry-statistics/debounce-count
                        leaf debounce-count {
                            type yang:counter32;
                            description "Indicates the number of times script is not executed due to debounce rule.";
                        }

                    } // container summary-entry-statistics

                    ///nokia-state/state/log/event-trigger/rsvp/entry
                    list entry {
                        key "id";
                        description "Enter the entry list instance";

                        ///nokia-state/state/log/event-trigger/rsvp/entry/id
                        leaf id {
                            type uint32 {
                                range "1..1500";
                            }
                            description "ID of the EHS event trigger entry";
                        }

                        ///nokia-state/state/log/event-trigger/rsvp/entry/oper-state
                        leaf oper-state {
                            type types-sros:oper-state;
                            description "Indicates the operational state of the EHS Event Trigger Entry.";
                        }

                        ///nokia-state/state/log/event-trigger/rsvp/entry/statistics
                        container statistics {
                            description "Enter the statistics context";

                            ///nokia-state/state/log/event-trigger/rsvp/entry/statistics/filter-match
                            leaf filter-match {
                                type yang:counter32;
                                description
                                    "Indicates the number of times a filter, for the specified trigger entry,
                                     matches an logger event.";
                            }

                            ///nokia-state/state/log/event-trigger/rsvp/entry/statistics/filter-fail
                            leaf filter-fail {
                                type yang:counter32;
                                description
                                    "Indicates the number of times a filter, for the specified trigger entry,
                                     does not match an logger event.";
                            }

                            ///nokia-state/state/log/event-trigger/rsvp/entry/statistics/error-admin-state
                            leaf error-admin-state {
                                type yang:counter32;
                                description
                                    "Indicates the number of times the logger event will be ignored due to
                                     admin state of EHS trigger entry is out-of-service.";
                            }

                            ///nokia-state/state/log/event-trigger/rsvp/entry/statistics/error-filter
                            leaf error-filter {
                                type yang:counter32;
                                description
                                    "Indicates the number of times the logger event will be ignored due to filter
                                     is not operational or is not configured in EHS trigger entry.";
                            }

                            ///nokia-state/state/log/event-trigger/rsvp/entry/statistics/error-handler
                            leaf error-handler {
                                type yang:counter32;
                                description
                                    "Indicates the number of times the logger event will be ignored due to handler
                                     is not operational or is not configured in EHS trigger entry.";
                            }

                            ///nokia-state/state/log/event-trigger/rsvp/entry/statistics/trigger-count
                            leaf trigger-count {
                                type yang:counter32;
                                description
                                    "Indicates the number of times script execution is triggered after filter match
                                     for the specified trigger entry.";
                            }

                            ///nokia-state/state/log/event-trigger/rsvp/entry/statistics/debounce-count
                            leaf debounce-count {
                                type yang:counter32;
                                description
                                    "Indicates the number of times script is not executed due to debounce rule
                                     for the specified trigger entry.";
                            }

                        } // container statistics

                    } // list entry

                } // list rsvp

                ///nokia-state/state/log/event-trigger/satellite
                list satellite {
                    key "event";
                    description "Enter the satellite list instance";

                    ///nokia-state/state/log/event-trigger/satellite/event
                    leaf event {
                        type types-log:satellite-events;
                        description "Log event as a trigger for one or more EHS handlers";
                    }

                    ///nokia-state/state/log/event-trigger/satellite/oper-state
                    leaf oper-state {
                        type types-sros:oper-state;
                        description "Indicates the operational state of the EHS Event Trigger.";
                    }

                    ///nokia-state/state/log/event-trigger/satellite/statistics
                    container statistics {
                        description "Enter the statistics context";

                        ///nokia-state/state/log/event-trigger/satellite/statistics/success
                        leaf success {
                            type yang:counter32;
                            description
                                "Indicates the number of not ignored logger event occurrences
                                 associated with EHS trigger.";
                        }

                        ///nokia-state/state/log/event-trigger/satellite/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/satellite/statistics/error-admin-state
                        leaf error-admin-state {
                            type yang:counter32;
                            description
                                "Indicates the number of ignored logger event occurrences associated
                                 with EHS trigger.

                                 Event is ignored due to trigger may be out-of-service.";
                        }

                        ///nokia-state/state/log/event-trigger/satellite/statistics/total
                        leaf total {
                            type yang:counter32;
                            description "Sum of success + error-no-entry + error-admin-state.";
                        }

                    } // container statistics

                    ///nokia-state/state/log/event-trigger/satellite/summary-entry-statistics
                    container summary-entry-statistics {
                        description "Enter the summary-entry-statistics context";

                        ///nokia-state/state/log/event-trigger/satellite/summary-entry-statistics/filter-match
                        leaf filter-match {
                            type yang:counter32;
                            description "Indicates the number of times a filter matches an logger event.";
                        }

                        ///nokia-state/state/log/event-trigger/satellite/summary-entry-statistics/filter-fail
                        leaf filter-fail {
                            type yang:counter32;
                            description "Indicates the number of times a filter does not match an logger event.";
                        }

                        ///nokia-state/state/log/event-trigger/satellite/summary-entry-statistics/error-admin-state
                        leaf error-admin-state {
                            type yang:counter32;
                            description
                                "Indicates the number of times the logger event will be ignored due to
                                 admin state of EHS trigger entries is out-of-service.";
                        }

                        ///nokia-state/state/log/event-trigger/satellite/summary-entry-statistics/error-filter
                        leaf error-filter {
                            type yang:counter32;
                            description
                                "Indicates the number of times the logger event will be ignored due to filter
                                 is not operational or is not configured in EHS trigger entries.";
                        }

                        ///nokia-state/state/log/event-trigger/satellite/summary-entry-statistics/error-handler
                        leaf error-handler {
                            type yang:counter32;
                            description
                                "Indicates the number of times the logger event will be ignored due to handler
                                 is not operational or is not configured in EHS trigger entries.";
                        }

                        ///nokia-state/state/log/event-trigger/satellite/summary-entry-statistics/trigger-count
                        leaf trigger-count {
                            type yang:counter32;
                            description "Indicates the number of times script execution is triggered after filter match.";
                        }

                        ///nokia-state/state/log/event-trigger/satellite/summary-entry-statistics/debounce-count
                        leaf debounce-count {
                            type yang:counter32;
                            description "Indicates the number of times script is not executed due to debounce rule.";
                        }

                    } // container summary-entry-statistics

                    ///nokia-state/state/log/event-trigger/satellite/entry
                    list entry {
                        key "id";
                        description "Enter the entry list instance";

                        ///nokia-state/state/log/event-trigger/satellite/entry/id
                        leaf id {
                            type uint32 {
                                range "1..1500";
                            }
                            description "ID of the EHS event trigger entry";
                        }

                        ///nokia-state/state/log/event-trigger/satellite/entry/oper-state
                        leaf oper-state {
                            type types-sros:oper-state;
                            description "Indicates the operational state of the EHS Event Trigger Entry.";
                        }

                        ///nokia-state/state/log/event-trigger/satellite/entry/statistics
                        container statistics {
                            description "Enter the statistics context";

                            ///nokia-state/state/log/event-trigger/satellite/entry/statistics/filter-match
                            leaf filter-match {
                                type yang:counter32;
                                description
                                    "Indicates the number of times a filter, for the specified trigger entry,
                                     matches an logger event.";
                            }

                            ///nokia-state/state/log/event-trigger/satellite/entry/statistics/filter-fail
                            leaf filter-fail {
                                type yang:counter32;
                                description
                                    "Indicates the number of times a filter, for the specified trigger entry,
                                     does not match an logger event.";
                            }

                            ///nokia-state/state/log/event-trigger/satellite/entry/statistics/error-admin-state
                            leaf error-admin-state {
                                type yang:counter32;
                                description
                                    "Indicates the number of times the logger event will be ignored due to
                                     admin state of EHS trigger entry is out-of-service.";
                            }

                            ///nokia-state/state/log/event-trigger/satellite/entry/statistics/error-filter
                            leaf error-filter {
                                type yang:counter32;
                                description
                                    "Indicates the number of times the logger event will be ignored due to filter
                                     is not operational or is not configured in EHS trigger entry.";
                            }

                            ///nokia-state/state/log/event-trigger/satellite/entry/statistics/error-handler
                            leaf error-handler {
                                type yang:counter32;
                                description
                                    "Indicates the number of times the logger event will be ignored due to handler
                                     is not operational or is not configured in EHS trigger entry.";
                            }

                            ///nokia-state/state/log/event-trigger/satellite/entry/statistics/trigger-count
                            leaf trigger-count {
                                type yang:counter32;
                                description
                                    "Indicates the number of times script execution is triggered after filter match
                                     for the specified trigger entry.";
                            }

                            ///nokia-state/state/log/event-trigger/satellite/entry/statistics/debounce-count
                            leaf debounce-count {
                                type yang:counter32;
                                description
                                    "Indicates the number of times script is not executed due to debounce rule
                                     for the specified trigger entry.";
                            }

                        } // container statistics

                    } // list entry

                } // list satellite

                ///nokia-state/state/log/event-trigger/security
                list security {
                    key "event";
                    description "Enter the security list instance";

                    ///nokia-state/state/log/event-trigger/security/event
                    leaf event {
                        type types-log:security-events;
                        description "Log event as a trigger for one or more EHS handlers";
                    }

                    ///nokia-state/state/log/event-trigger/security/oper-state
                    leaf oper-state {
                        type types-sros:oper-state;
                        description "Indicates the operational state of the EHS Event Trigger.";
                    }

                    ///nokia-state/state/log/event-trigger/security/statistics
                    container statistics {
                        description "Enter the statistics context";

                        ///nokia-state/state/log/event-trigger/security/statistics/success
                        leaf success {
                            type yang:counter32;
                            description
                                "Indicates the number of not ignored logger event occurrences
                                 associated with EHS trigger.";
                        }

                        ///nokia-state/state/log/event-trigger/security/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/security/statistics/error-admin-state
                        leaf error-admin-state {
                            type yang:counter32;
                            description
                                "Indicates the number of ignored logger event occurrences associated
                                 with EHS trigger.

                                 Event is ignored due to trigger may be out-of-service.";
                        }

                        ///nokia-state/state/log/event-trigger/security/statistics/total
                        leaf total {
                            type yang:counter32;
                            description "Sum of success + error-no-entry + error-admin-state.";
                        }

                    } // container statistics

                    ///nokia-state/state/log/event-trigger/security/summary-entry-statistics
                    container summary-entry-statistics {
                        description "Enter the summary-entry-statistics context";

                        ///nokia-state/state/log/event-trigger/security/summary-entry-statistics/filter-match
                        leaf filter-match {
                            type yang:counter32;
                            description "Indicates the number of times a filter matches an logger event.";
                        }

                        ///nokia-state/state/log/event-trigger/security/summary-entry-statistics/filter-fail
                        leaf filter-fail {
                            type yang:counter32;
                            description "Indicates the number of times a filter does not match an logger event.";
                        }

                        ///nokia-state/state/log/event-trigger/security/summary-entry-statistics/error-admin-state
                        leaf error-admin-state {
                            type yang:counter32;
                            description
                                "Indicates the number of times the logger event will be ignored due to
                                 admin state of EHS trigger entries is out-of-service.";
                        }

                        ///nokia-state/state/log/event-trigger/security/summary-entry-statistics/error-filter
                        leaf error-filter {
                            type yang:counter32;
                            description
                                "Indicates the number of times the logger event will be ignored due to filter
                                 is not operational or is not configured in EHS trigger entries.";
                        }

                        ///nokia-state/state/log/event-trigger/security/summary-entry-statistics/error-handler
                        leaf error-handler {
                            type yang:counter32;
                            description
                                "Indicates the number of times the logger event will be ignored due to handler
                                 is not operational or is not configured in EHS trigger entries.";
                        }

                        ///nokia-state/state/log/event-trigger/security/summary-entry-statistics/trigger-count
                        leaf trigger-count {
                            type yang:counter32;
                            description "Indicates the number of times script execution is triggered after filter match.";
                        }

                        ///nokia-state/state/log/event-trigger/security/summary-entry-statistics/debounce-count
                        leaf debounce-count {
                            type yang:counter32;
                            description "Indicates the number of times script is not executed due to debounce rule.";
                        }

                    } // container summary-entry-statistics

                    ///nokia-state/state/log/event-trigger/security/entry
                    list entry {
                        key "id";
                        description "Enter the entry list instance";

                        ///nokia-state/state/log/event-trigger/security/entry/id
                        leaf id {
                            type uint32 {
                                range "1..1500";
                            }
                            description "ID of the EHS event trigger entry";
                        }

                        ///nokia-state/state/log/event-trigger/security/entry/oper-state
                        leaf oper-state {
                            type types-sros:oper-state;
                            description "Indicates the operational state of the EHS Event Trigger Entry.";
                        }

                        ///nokia-state/state/log/event-trigger/security/entry/statistics
                        container statistics {
                            description "Enter the statistics context";

                            ///nokia-state/state/log/event-trigger/security/entry/statistics/filter-match
                            leaf filter-match {
                                type yang:counter32;
                                description
                                    "Indicates the number of times a filter, for the specified trigger entry,
                                     matches an logger event.";
                            }

                            ///nokia-state/state/log/event-trigger/security/entry/statistics/filter-fail
                            leaf filter-fail {
                                type yang:counter32;
                                description
                                    "Indicates the number of times a filter, for the specified trigger entry,
                                     does not match an logger event.";
                            }

                            ///nokia-state/state/log/event-trigger/security/entry/statistics/error-admin-state
                            leaf error-admin-state {
                                type yang:counter32;
                                description
                                    "Indicates the number of times the logger event will be ignored due to
                                     admin state of EHS trigger entry is out-of-service.";
                            }

                            ///nokia-state/state/log/event-trigger/security/entry/statistics/error-filter
                            leaf error-filter {
                                type yang:counter32;
                                description
                                    "Indicates the number of times the logger event will be ignored due to filter
                                     is not operational or is not configured in EHS trigger entry.";
                            }

                            ///nokia-state/state/log/event-trigger/security/entry/statistics/error-handler
                            leaf error-handler {
                                type yang:counter32;
                                description
                                    "Indicates the number of times the logger event will be ignored due to handler
                                     is not operational or is not configured in EHS trigger entry.";
                            }

                            ///nokia-state/state/log/event-trigger/security/entry/statistics/trigger-count
                            leaf trigger-count {
                                type yang:counter32;
                                description
                                    "Indicates the number of times script execution is triggered after filter match
                                     for the specified trigger entry.";
                            }

                            ///nokia-state/state/log/event-trigger/security/entry/statistics/debounce-count
                            leaf debounce-count {
                                type yang:counter32;
                                description
                                    "Indicates the number of times script is not executed due to debounce rule
                                     for the specified trigger entry.";
                            }

                        } // container statistics

                    } // list entry

                } // list security

                ///nokia-state/state/log/event-trigger/sflow
                list sflow {
                    key "event";
                    description "Enter the sflow list instance";

                    ///nokia-state/state/log/event-trigger/sflow/event
                    leaf event {
                        type types-log:sflow-events;
                        description "Log event as a trigger for one or more EHS handlers";
                    }

                    ///nokia-state/state/log/event-trigger/sflow/oper-state
                    leaf oper-state {
                        type types-sros:oper-state;
                        description "Indicates the operational state of the EHS Event Trigger.";
                    }

                    ///nokia-state/state/log/event-trigger/sflow/statistics
                    container statistics {
                        description "Enter the statistics context";

                        ///nokia-state/state/log/event-trigger/sflow/statistics/success
                        leaf success {
                            type yang:counter32;
                            description
                                "Indicates the number of not ignored logger event occurrences
                                 associated with EHS trigger.";
                        }

                        ///nokia-state/state/log/event-trigger/sflow/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/sflow/statistics/error-admin-state
                        leaf error-admin-state {
                            type yang:counter32;
                            description
                                "Indicates the number of ignored logger event occurrences associated
                                 with EHS trigger.

                                 Event is ignored due to trigger may be out-of-service.";
                        }

                        ///nokia-state/state/log/event-trigger/sflow/statistics/total
                        leaf total {
                            type yang:counter32;
                            description "Sum of success + error-no-entry + error-admin-state.";
                        }

                    } // container statistics

                    ///nokia-state/state/log/event-trigger/sflow/summary-entry-statistics
                    container summary-entry-statistics {
                        description "Enter the summary-entry-statistics context";

                        ///nokia-state/state/log/event-trigger/sflow/summary-entry-statistics/filter-match
                        leaf filter-match {
                            type yang:counter32;
                            description "Indicates the number of times a filter matches an logger event.";
                        }

                        ///nokia-state/state/log/event-trigger/sflow/summary-entry-statistics/filter-fail
                        leaf filter-fail {
                            type yang:counter32;
                            description "Indicates the number of times a filter does not match an logger event.";
                        }

                        ///nokia-state/state/log/event-trigger/sflow/summary-entry-statistics/error-admin-state
                        leaf error-admin-state {
                            type yang:counter32;
                            description
                                "Indicates the number of times the logger event will be ignored due to
                                 admin state of EHS trigger entries is out-of-service.";
                        }

                        ///nokia-state/state/log/event-trigger/sflow/summary-entry-statistics/error-filter
                        leaf error-filter {
                            type yang:counter32;
                            description
                                "Indicates the number of times the logger event will be ignored due to filter
                                 is not operational or is not configured in EHS trigger entries.";
                        }

                        ///nokia-state/state/log/event-trigger/sflow/summary-entry-statistics/error-handler
                        leaf error-handler {
                            type yang:counter32;
                            description
                                "Indicates the number of times the logger event will be ignored due to handler
                                 is not operational or is not configured in EHS trigger entries.";
                        }

                        ///nokia-state/state/log/event-trigger/sflow/summary-entry-statistics/trigger-count
                        leaf trigger-count {
                            type yang:counter32;
                            description "Indicates the number of times script execution is triggered after filter match.";
                        }

                        ///nokia-state/state/log/event-trigger/sflow/summary-entry-statistics/debounce-count
                        leaf debounce-count {
                            type yang:counter32;
                            description "Indicates the number of times script is not executed due to debounce rule.";
                        }

                    } // container summary-entry-statistics

                    ///nokia-state/state/log/event-trigger/sflow/entry
                    list entry {
                        key "id";
                        description "Enter the entry list instance";

                        ///nokia-state/state/log/event-trigger/sflow/entry/id
                        leaf id {
                            type uint32 {
                                range "1..1500";
                            }
                            description "ID of the EHS event trigger entry";
                        }

                        ///nokia-state/state/log/event-trigger/sflow/entry/oper-state
                        leaf oper-state {
                            type types-sros:oper-state;
                            description "Indicates the operational state of the EHS Event Trigger Entry.";
                        }

                        ///nokia-state/state/log/event-trigger/sflow/entry/statistics
                        container statistics {
                            description "Enter the statistics context";

                            ///nokia-state/state/log/event-trigger/sflow/entry/statistics/filter-match
                            leaf filter-match {
                                type yang:counter32;
                                description
                                    "Indicates the number of times a filter, for the specified trigger entry,
                                     matches an logger event.";
                            }

                            ///nokia-state/state/log/event-trigger/sflow/entry/statistics/filter-fail
                            leaf filter-fail {
                                type yang:counter32;
                                description
                                    "Indicates the number of times a filter, for the specified trigger entry,
                                     does not match an logger event.";
                            }

                            ///nokia-state/state/log/event-trigger/sflow/entry/statistics/error-admin-state
                            leaf error-admin-state {
                                type yang:counter32;
                                description
                                    "Indicates the number of times the logger event will be ignored due to
                                     admin state of EHS trigger entry is out-of-service.";
                            }

                            ///nokia-state/state/log/event-trigger/sflow/entry/statistics/error-filter
                            leaf error-filter {
                                type yang:counter32;
                                description
                                    "Indicates the number of times the logger event will be ignored due to filter
                                     is not operational or is not configured in EHS trigger entry.";
                            }

                            ///nokia-state/state/log/event-trigger/sflow/entry/statistics/error-handler
                            leaf error-handler {
                                type yang:counter32;
                                description
                                    "Indicates the number of times the logger event will be ignored due to handler
                                     is not operational or is not configured in EHS trigger entry.";
                            }

                            ///nokia-state/state/log/event-trigger/sflow/entry/statistics/trigger-count
                            leaf trigger-count {
                                type yang:counter32;
                                description
                                    "Indicates the number of times script execution is triggered after filter match
                                     for the specified trigger entry.";
                            }

                            ///nokia-state/state/log/event-trigger/sflow/entry/statistics/debounce-count
                            leaf debounce-count {
                                type yang:counter32;
                                description
                                    "Indicates the number of times script is not executed due to debounce rule
                                     for the specified trigger entry.";
                            }

                        } // container statistics

                    } // list entry

                } // list sflow

                ///nokia-state/state/log/event-trigger/snmp
                list snmp {
                    key "event";
                    description "Enter the snmp list instance";

                    ///nokia-state/state/log/event-trigger/snmp/event
                    leaf event {
                        type types-log:snmp-events;
                        description "Log event as a trigger for one or more EHS handlers";
                    }

                    ///nokia-state/state/log/event-trigger/snmp/oper-state
                    leaf oper-state {
                        type types-sros:oper-state;
                        description "Indicates the operational state of the EHS Event Trigger.";
                    }

                    ///nokia-state/state/log/event-trigger/snmp/statistics
                    container statistics {
                        description "Enter the statistics context";

                        ///nokia-state/state/log/event-trigger/snmp/statistics/success
                        leaf success {
                            type yang:counter32;
                            description
                                "Indicates the number of not ignored logger event occurrences
                                 associated with EHS trigger.";
                        }

                        ///nokia-state/state/log/event-trigger/snmp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/snmp/statistics/error-admin-state
                        leaf error-admin-state {
                            type yang:counter32;
                            description
                                "Indicates the number of ignored logger event occurrences associated
                                 with EHS trigger.

                                 Event is ignored due to trigger may be out-of-service.";
                        }

                        ///nokia-state/state/log/event-trigger/snmp/statistics/total
                        leaf total {
                            type yang:counter32;
                            description "Sum of success + error-no-entry + error-admin-state.";
                        }

                    } // container statistics

                    ///nokia-state/state/log/event-trigger/snmp/summary-entry-statistics
                    container summary-entry-statistics {
                        description "Enter the summary-entry-statistics context";

                        ///nokia-state/state/log/event-trigger/snmp/summary-entry-statistics/filter-match
                        leaf filter-match {
                            type yang:counter32;
                            description "Indicates the number of times a filter matches an logger event.";
                        }

                        ///nokia-state/state/log/event-trigger/snmp/summary-entry-statistics/filter-fail
                        leaf filter-fail {
                            type yang:counter32;
                            description "Indicates the number of times a filter does not match an logger event.";
                        }

                        ///nokia-state/state/log/event-trigger/snmp/summary-entry-statistics/error-admin-state
                        leaf error-admin-state {
                            type yang:counter32;
                            description
                                "Indicates the number of times the logger event will be ignored due to
                                 admin state of EHS trigger entries is out-of-service.";
                        }

                        ///nokia-state/state/log/event-trigger/snmp/summary-entry-statistics/error-filter
                        leaf error-filter {
                            type yang:counter32;
                            description
                                "Indicates the number of times the logger event will be ignored due to filter
                                 is not operational or is not configured in EHS trigger entries.";
                        }

                        ///nokia-state/state/log/event-trigger/snmp/summary-entry-statistics/error-handler
                        leaf error-handler {
                            type yang:counter32;
                            description
                                "Indicates the number of times the logger event will be ignored due to handler
                                 is not operational or is not configured in EHS trigger entries.";
                        }

                        ///nokia-state/state/log/event-trigger/snmp/summary-entry-statistics/trigger-count
                        leaf trigger-count {
                            type yang:counter32;
                            description "Indicates the number of times script execution is triggered after filter match.";
                        }

                        ///nokia-state/state/log/event-trigger/snmp/summary-entry-statistics/debounce-count
                        leaf debounce-count {
                            type yang:counter32;
                            description "Indicates the number of times script is not executed due to debounce rule.";
                        }

                    } // container summary-entry-statistics

                    ///nokia-state/state/log/event-trigger/snmp/entry
                    list entry {
                        key "id";
                        description "Enter the entry list instance";

                        ///nokia-state/state/log/event-trigger/snmp/entry/id
                        leaf id {
                            type uint32 {
                                range "1..1500";
                            }
                            description "ID of the EHS event trigger entry";
                        }

                        ///nokia-state/state/log/event-trigger/snmp/entry/oper-state
                        leaf oper-state {
                            type types-sros:oper-state;
                            description "Indicates the operational state of the EHS Event Trigger Entry.";
                        }

                        ///nokia-state/state/log/event-trigger/snmp/entry/statistics
                        container statistics {
                            description "Enter the statistics context";

                            ///nokia-state/state/log/event-trigger/snmp/entry/statistics/filter-match
                            leaf filter-match {
                                type yang:counter32;
                                description
                                    "Indicates the number of times a filter, for the specified trigger entry,
                                     matches an logger event.";
                            }

                            ///nokia-state/state/log/event-trigger/snmp/entry/statistics/filter-fail
                            leaf filter-fail {
                                type yang:counter32;
                                description
                                    "Indicates the number of times a filter, for the specified trigger entry,
                                     does not match an logger event.";
                            }

                            ///nokia-state/state/log/event-trigger/snmp/entry/statistics/error-admin-state
                            leaf error-admin-state {
                                type yang:counter32;
                                description
                                    "Indicates the number of times the logger event will be ignored due to
                                     admin state of EHS trigger entry is out-of-service.";
                            }

                            ///nokia-state/state/log/event-trigger/snmp/entry/statistics/error-filter
                            leaf error-filter {
                                type yang:counter32;
                                description
                                    "Indicates the number of times the logger event will be ignored due to filter
                                     is not operational or is not configured in EHS trigger entry.";
                            }

                            ///nokia-state/state/log/event-trigger/snmp/entry/statistics/error-handler
                            leaf error-handler {
                                type yang:counter32;
                                description
                                    "Indicates the number of times the logger event will be ignored due to handler
                                     is not operational or is not configured in EHS trigger entry.";
                            }

                            ///nokia-state/state/log/event-trigger/snmp/entry/statistics/trigger-count
                            leaf trigger-count {
                                type yang:counter32;
                                description
                                    "Indicates the number of times script execution is triggered after filter match
                                     for the specified trigger entry.";
                            }

                            ///nokia-state/state/log/event-trigger/snmp/entry/statistics/debounce-count
                            leaf debounce-count {
                                type yang:counter32;
                                description
                                    "Indicates the number of times script is not executed due to debounce rule
                                     for the specified trigger entry.";
                            }

                        } // container statistics

                    } // list entry

                } // list snmp

                ///nokia-state/state/log/event-trigger/sr-mpls
                list sr-mpls {
                    key "event";
                    description "Enter the sr-mpls list instance";

                    ///nokia-state/state/log/event-trigger/sr-mpls/event
                    leaf event {
                        type types-log:sr-mpls-events;
                        description "SR MPLS event";
                    }

                    ///nokia-state/state/log/event-trigger/sr-mpls/oper-state
                    leaf oper-state {
                        type types-sros:oper-state;
                        description "Indicates the operational state of the EHS Event Trigger.";
                    }

                    ///nokia-state/state/log/event-trigger/sr-mpls/statistics
                    container statistics {
                        description "Enter the statistics context";

                        ///nokia-state/state/log/event-trigger/sr-mpls/statistics/success
                        leaf success {
                            type yang:counter32;
                            description
                                "Indicates the number of not ignored logger event occurrences
                                 associated with EHS trigger.";
                        }

                        ///nokia-state/state/log/event-trigger/sr-mpls/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/sr-mpls/statistics/error-admin-state
                        leaf error-admin-state {
                            type yang:counter32;
                            description
                                "Indicates the number of ignored logger event occurrences associated
                                 with EHS trigger.

                                 Event is ignored due to trigger may be out-of-service.";
                        }

                        ///nokia-state/state/log/event-trigger/sr-mpls/statistics/total
                        leaf total {
                            type yang:counter32;
                            description "Sum of success + error-no-entry + error-admin-state.";
                        }

                    } // container statistics

                    ///nokia-state/state/log/event-trigger/sr-mpls/summary-entry-statistics
                    container summary-entry-statistics {
                        description "Enter the summary-entry-statistics context";

                        ///nokia-state/state/log/event-trigger/sr-mpls/summary-entry-statistics/filter-match
                        leaf filter-match {
                            type yang:counter32;
                            description "Indicates the number of times a filter matches an logger event.";
                        }

                        ///nokia-state/state/log/event-trigger/sr-mpls/summary-entry-statistics/filter-fail
                        leaf filter-fail {
                            type yang:counter32;
                            description "Indicates the number of times a filter does not match an logger event.";
                        }

                        ///nokia-state/state/log/event-trigger/sr-mpls/summary-entry-statistics/error-admin-state
                        leaf error-admin-state {
                            type yang:counter32;
                            description
                                "Indicates the number of times the logger event will be ignored due to
                                 admin state of EHS trigger entries is out-of-service.";
                        }

                        ///nokia-state/state/log/event-trigger/sr-mpls/summary-entry-statistics/error-filter
                        leaf error-filter {
                            type yang:counter32;
                            description
                                "Indicates the number of times the logger event will be ignored due to filter
                                 is not operational or is not configured in EHS trigger entries.";
                        }

                        ///nokia-state/state/log/event-trigger/sr-mpls/summary-entry-statistics/error-handler
                        leaf error-handler {
                            type yang:counter32;
                            description
                                "Indicates the number of times the logger event will be ignored due to handler
                                 is not operational or is not configured in EHS trigger entries.";
                        }

                        ///nokia-state/state/log/event-trigger/sr-mpls/summary-entry-statistics/trigger-count
                        leaf trigger-count {
                            type yang:counter32;
                            description "Indicates the number of times script execution is triggered after filter match.";
                        }

                        ///nokia-state/state/log/event-trigger/sr-mpls/summary-entry-statistics/debounce-count
                        leaf debounce-count {
                            type yang:counter32;
                            description "Indicates the number of times script is not executed due to debounce rule.";
                        }

                    } // container summary-entry-statistics

                    ///nokia-state/state/log/event-trigger/sr-mpls/entry
                    list entry {
                        key "id";
                        description "Enter the entry list instance";

                        ///nokia-state/state/log/event-trigger/sr-mpls/entry/id
                        leaf id {
                            type uint32 {
                                range "1..1500";
                            }
                            description "ID of the EHS event trigger entry";
                        }

                        ///nokia-state/state/log/event-trigger/sr-mpls/entry/oper-state
                        leaf oper-state {
                            type types-sros:oper-state;
                            description "Indicates the operational state of the EHS Event Trigger Entry.";
                        }

                        ///nokia-state/state/log/event-trigger/sr-mpls/entry/statistics
                        container statistics {
                            description "Enter the statistics context";

                            ///nokia-state/state/log/event-trigger/sr-mpls/entry/statistics/filter-match
                            leaf filter-match {
                                type yang:counter32;
                                description
                                    "Indicates the number of times a filter, for the specified trigger entry,
                                     matches an logger event.";
                            }

                            ///nokia-state/state/log/event-trigger/sr-mpls/entry/statistics/filter-fail
                            leaf filter-fail {
                                type yang:counter32;
                                description
                                    "Indicates the number of times a filter, for the specified trigger entry,
                                     does not match an logger event.";
                            }

                            ///nokia-state/state/log/event-trigger/sr-mpls/entry/statistics/error-admin-state
                            leaf error-admin-state {
                                type yang:counter32;
                                description
                                    "Indicates the number of times the logger event will be ignored due to
                                     admin state of EHS trigger entry is out-of-service.";
                            }

                            ///nokia-state/state/log/event-trigger/sr-mpls/entry/statistics/error-filter
                            leaf error-filter {
                                type yang:counter32;
                                description
                                    "Indicates the number of times the logger event will be ignored due to filter
                                     is not operational or is not configured in EHS trigger entry.";
                            }

                            ///nokia-state/state/log/event-trigger/sr-mpls/entry/statistics/error-handler
                            leaf error-handler {
                                type yang:counter32;
                                description
                                    "Indicates the number of times the logger event will be ignored due to handler
                                     is not operational or is not configured in EHS trigger entry.";
                            }

                            ///nokia-state/state/log/event-trigger/sr-mpls/entry/statistics/trigger-count
                            leaf trigger-count {
                                type yang:counter32;
                                description
                                    "Indicates the number of times script execution is triggered after filter match
                                     for the specified trigger entry.";
                            }

                            ///nokia-state/state/log/event-trigger/sr-mpls/entry/statistics/debounce-count
                            leaf debounce-count {
                                type yang:counter32;
                                description
                                    "Indicates the number of times script is not executed due to debounce rule
                                     for the specified trigger entry.";
                            }

                        } // container statistics

                    } // list entry

                } // list sr-mpls

                ///nokia-state/state/log/event-trigger/srv6
                list srv6 {
                    key "event";
                    description "Enter the srv6 list instance";

                    ///nokia-state/state/log/event-trigger/srv6/event
                    leaf event {
                        type types-log:srv6-events;
                        description "Log event as a trigger for one or more EHS handlers";
                    }

                    ///nokia-state/state/log/event-trigger/srv6/oper-state
                    leaf oper-state {
                        type types-sros:oper-state;
                        description "Indicates the operational state of the EHS Event Trigger.";
                    }

                    ///nokia-state/state/log/event-trigger/srv6/statistics
                    container statistics {
                        description "Enter the statistics context";

                        ///nokia-state/state/log/event-trigger/srv6/statistics/success
                        leaf success {
                            type yang:counter32;
                            description
                                "Indicates the number of not ignored logger event occurrences
                                 associated with EHS trigger.";
                        }

                        ///nokia-state/state/log/event-trigger/srv6/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/srv6/statistics/error-admin-state
                        leaf error-admin-state {
                            type yang:counter32;
                            description
                                "Indicates the number of ignored logger event occurrences associated
                                 with EHS trigger.

                                 Event is ignored due to trigger may be out-of-service.";
                        }

                        ///nokia-state/state/log/event-trigger/srv6/statistics/total
                        leaf total {
                            type yang:counter32;
                            description "Sum of success + error-no-entry + error-admin-state.";
                        }

                    } // container statistics

                    ///nokia-state/state/log/event-trigger/srv6/summary-entry-statistics
                    container summary-entry-statistics {
                        description "Enter the summary-entry-statistics context";

                        ///nokia-state/state/log/event-trigger/srv6/summary-entry-statistics/filter-match
                        leaf filter-match {
                            type yang:counter32;
                            description "Indicates the number of times a filter matches an logger event.";
                        }

                        ///nokia-state/state/log/event-trigger/srv6/summary-entry-statistics/filter-fail
                        leaf filter-fail {
                            type yang:counter32;
                            description "Indicates the number of times a filter does not match an logger event.";
                        }

                        ///nokia-state/state/log/event-trigger/srv6/summary-entry-statistics/error-admin-state
                        leaf error-admin-state {
                            type yang:counter32;
                            description
                                "Indicates the number of times the logger event will be ignored due to
                                 admin state of EHS trigger entries is out-of-service.";
                        }

                        ///nokia-state/state/log/event-trigger/srv6/summary-entry-statistics/error-filter
                        leaf error-filter {
                            type yang:counter32;
                            description
                                "Indicates the number of times the logger event will be ignored due to filter
                                 is not operational or is not configured in EHS trigger entries.";
                        }

                        ///nokia-state/state/log/event-trigger/srv6/summary-entry-statistics/error-handler
                        leaf error-handler {
                            type yang:counter32;
                            description
                                "Indicates the number of times the logger event will be ignored due to handler
                                 is not operational or is not configured in EHS trigger entries.";
                        }

                        ///nokia-state/state/log/event-trigger/srv6/summary-entry-statistics/trigger-count
                        leaf trigger-count {
                            type yang:counter32;
                            description "Indicates the number of times script execution is triggered after filter match.";
                        }

                        ///nokia-state/state/log/event-trigger/srv6/summary-entry-statistics/debounce-count
                        leaf debounce-count {
                            type yang:counter32;
                            description "Indicates the number of times script is not executed due to debounce rule.";
                        }

                    } // container summary-entry-statistics

                    ///nokia-state/state/log/event-trigger/srv6/entry
                    list entry {
                        key "id";
                        description "Enter the entry list instance";

                        ///nokia-state/state/log/event-trigger/srv6/entry/id
                        leaf id {
                            type uint32 {
                                range "1..1500";
                            }
                            description "ID of the EHS event trigger entry";
                        }

                        ///nokia-state/state/log/event-trigger/srv6/entry/oper-state
                        leaf oper-state {
                            type types-sros:oper-state;
                            description "Indicates the operational state of the EHS Event Trigger Entry.";
                        }

                        ///nokia-state/state/log/event-trigger/srv6/entry/statistics
                        container statistics {
                            description "Enter the statistics context";

                            ///nokia-state/state/log/event-trigger/srv6/entry/statistics/filter-match
                            leaf filter-match {
                                type yang:counter32;
                                description
                                    "Indicates the number of times a filter, for the specified trigger entry,
                                     matches an logger event.";
                            }

                            ///nokia-state/state/log/event-trigger/srv6/entry/statistics/filter-fail
                            leaf filter-fail {
                                type yang:counter32;
                                description
                                    "Indicates the number of times a filter, for the specified trigger entry,
                                     does not match an logger event.";
                            }

                            ///nokia-state/state/log/event-trigger/srv6/entry/statistics/error-admin-state
                            leaf error-admin-state {
                                type yang:counter32;
                                description
                                    "Indicates the number of times the logger event will be ignored due to
                                     admin state of EHS trigger entry is out-of-service.";
                            }

                            ///nokia-state/state/log/event-trigger/srv6/entry/statistics/error-filter
                            leaf error-filter {
                                type yang:counter32;
                                description
                                    "Indicates the number of times the logger event will be ignored due to filter
                                     is not operational or is not configured in EHS trigger entry.";
                            }

                            ///nokia-state/state/log/event-trigger/srv6/entry/statistics/error-handler
                            leaf error-handler {
                                type yang:counter32;
                                description
                                    "Indicates the number of times the logger event will be ignored due to handler
                                     is not operational or is not configured in EHS trigger entry.";
                            }

                            ///nokia-state/state/log/event-trigger/srv6/entry/statistics/trigger-count
                            leaf trigger-count {
                                type yang:counter32;
                                description
                                    "Indicates the number of times script execution is triggered after filter match
                                     for the specified trigger entry.";
                            }

                            ///nokia-state/state/log/event-trigger/srv6/entry/statistics/debounce-count
                            leaf debounce-count {
                                type yang:counter32;
                                description
                                    "Indicates the number of times script is not executed due to debounce rule
                                     for the specified trigger entry.";
                            }

                        } // container statistics

                    } // list entry

                } // list srv6

                ///nokia-state/state/log/event-trigger/stp
                list stp {
                    key "event";
                    description "Enter the stp list instance";

                    ///nokia-state/state/log/event-trigger/stp/event
                    leaf event {
                        type types-log:stp-events;
                        description "Log event as a trigger for one or more EHS handlers";
                    }

                    ///nokia-state/state/log/event-trigger/stp/oper-state
                    leaf oper-state {
                        type types-sros:oper-state;
                        description "Indicates the operational state of the EHS Event Trigger.";
                    }

                    ///nokia-state/state/log/event-trigger/stp/statistics
                    container statistics {
                        description "Enter the statistics context";

                        ///nokia-state/state/log/event-trigger/stp/statistics/success
                        leaf success {
                            type yang:counter32;
                            description
                                "Indicates the number of not ignored logger event occurrences
                                 associated with EHS trigger.";
                        }

                        ///nokia-state/state/log/event-trigger/stp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/stp/statistics/error-admin-state
                        leaf error-admin-state {
                            type yang:counter32;
                            description
                                "Indicates the number of ignored logger event occurrences associated
                                 with EHS trigger.

                                 Event is ignored due to trigger may be out-of-service.";
                        }

                        ///nokia-state/state/log/event-trigger/stp/statistics/total
                        leaf total {
                            type yang:counter32;
                            description "Sum of success + error-no-entry + error-admin-state.";
                        }

                    } // container statistics

                    ///nokia-state/state/log/event-trigger/stp/summary-entry-statistics
                    container summary-entry-statistics {
                        description "Enter the summary-entry-statistics context";

                        ///nokia-state/state/log/event-trigger/stp/summary-entry-statistics/filter-match
                        leaf filter-match {
                            type yang:counter32;
                            description "Indicates the number of times a filter matches an logger event.";
                        }

                        ///nokia-state/state/log/event-trigger/stp/summary-entry-statistics/filter-fail
                        leaf filter-fail {
                            type yang:counter32;
                            description "Indicates the number of times a filter does not match an logger event.";
                        }

                        ///nokia-state/state/log/event-trigger/stp/summary-entry-statistics/error-admin-state
                        leaf error-admin-state {
                            type yang:counter32;
                            description
                                "Indicates the number of times the logger event will be ignored due to
                                 admin state of EHS trigger entries is out-of-service.";
                        }

                        ///nokia-state/state/log/event-trigger/stp/summary-entry-statistics/error-filter
                        leaf error-filter {
                            type yang:counter32;
                            description
                                "Indicates the number of times the logger event will be ignored due to filter
                                 is not operational or is not configured in EHS trigger entries.";
                        }

                        ///nokia-state/state/log/event-trigger/stp/summary-entry-statistics/error-handler
                        leaf error-handler {
                            type yang:counter32;
                            description
                                "Indicates the number of times the logger event will be ignored due to handler
                                 is not operational or is not configured in EHS trigger entries.";
                        }

                        ///nokia-state/state/log/event-trigger/stp/summary-entry-statistics/trigger-count
                        leaf trigger-count {
                            type yang:counter32;
                            description "Indicates the number of times script execution is triggered after filter match.";
                        }

                        ///nokia-state/state/log/event-trigger/stp/summary-entry-statistics/debounce-count
                        leaf debounce-count {
                            type yang:counter32;
                            description "Indicates the number of times script is not executed due to debounce rule.";
                        }

                    } // container summary-entry-statistics

                    ///nokia-state/state/log/event-trigger/stp/entry
                    list entry {
                        key "id";
                        description "Enter the entry list instance";

                        ///nokia-state/state/log/event-trigger/stp/entry/id
                        leaf id {
                            type uint32 {
                                range "1..1500";
                            }
                            description "ID of the EHS event trigger entry";
                        }

                        ///nokia-state/state/log/event-trigger/stp/entry/oper-state
                        leaf oper-state {
                            type types-sros:oper-state;
                            description "Indicates the operational state of the EHS Event Trigger Entry.";
                        }

                        ///nokia-state/state/log/event-trigger/stp/entry/statistics
                        container statistics {
                            description "Enter the statistics context";

                            ///nokia-state/state/log/event-trigger/stp/entry/statistics/filter-match
                            leaf filter-match {
                                type yang:counter32;
                                description
                                    "Indicates the number of times a filter, for the specified trigger entry,
                                     matches an logger event.";
                            }

                            ///nokia-state/state/log/event-trigger/stp/entry/statistics/filter-fail
                            leaf filter-fail {
                                type yang:counter32;
                                description
                                    "Indicates the number of times a filter, for the specified trigger entry,
                                     does not match an logger event.";
                            }

                            ///nokia-state/state/log/event-trigger/stp/entry/statistics/error-admin-state
                            leaf error-admin-state {
                                type yang:counter32;
                                description
                                    "Indicates the number of times the logger event will be ignored due to
                                     admin state of EHS trigger entry is out-of-service.";
                            }

                            ///nokia-state/state/log/event-trigger/stp/entry/statistics/error-filter
                            leaf error-filter {
                                type yang:counter32;
                                description
                                    "Indicates the number of times the logger event will be ignored due to filter
                                     is not operational or is not configured in EHS trigger entry.";
                            }

                            ///nokia-state/state/log/event-trigger/stp/entry/statistics/error-handler
                            leaf error-handler {
                                type yang:counter32;
                                description
                                    "Indicates the number of times the logger event will be ignored due to handler
                                     is not operational or is not configured in EHS trigger entry.";
                            }

                            ///nokia-state/state/log/event-trigger/stp/entry/statistics/trigger-count
                            leaf trigger-count {
                                type yang:counter32;
                                description
                                    "Indicates the number of times script execution is triggered after filter match
                                     for the specified trigger entry.";
                            }

                            ///nokia-state/state/log/event-trigger/stp/entry/statistics/debounce-count
                            leaf debounce-count {
                                type yang:counter32;
                                description
                                    "Indicates the number of times script is not executed due to debounce rule
                                     for the specified trigger entry.";
                            }

                        } // container statistics

                    } // list entry

                } // list stp

                ///nokia-state/state/log/event-trigger/svcmgr
                list svcmgr {
                    key "event";
                    description "Enter the svcmgr list instance";

                    ///nokia-state/state/log/event-trigger/svcmgr/event
                    leaf event {
                        type types-log:svcmgr-events;
                        description "Log event as a trigger for one or more EHS handlers";
                    }

                    ///nokia-state/state/log/event-trigger/svcmgr/oper-state
                    leaf oper-state {
                        type types-sros:oper-state;
                        description "Indicates the operational state of the EHS Event Trigger.";
                    }

                    ///nokia-state/state/log/event-trigger/svcmgr/statistics
                    container statistics {
                        description "Enter the statistics context";

                        ///nokia-state/state/log/event-trigger/svcmgr/statistics/success
                        leaf success {
                            type yang:counter32;
                            description
                                "Indicates the number of not ignored logger event occurrences
                                 associated with EHS trigger.";
                        }

                        ///nokia-state/state/log/event-trigger/svcmgr/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/svcmgr/statistics/error-admin-state
                        leaf error-admin-state {
                            type yang:counter32;
                            description
                                "Indicates the number of ignored logger event occurrences associated
                                 with EHS trigger.

                                 Event is ignored due to trigger may be out-of-service.";
                        }

                        ///nokia-state/state/log/event-trigger/svcmgr/statistics/total
                        leaf total {
                            type yang:counter32;
                            description "Sum of success + error-no-entry + error-admin-state.";
                        }

                    } // container statistics

                    ///nokia-state/state/log/event-trigger/svcmgr/summary-entry-statistics
                    container summary-entry-statistics {
                        description "Enter the summary-entry-statistics context";

                        ///nokia-state/state/log/event-trigger/svcmgr/summary-entry-statistics/filter-match
                        leaf filter-match {
                            type yang:counter32;
                            description "Indicates the number of times a filter matches an logger event.";
                        }

                        ///nokia-state/state/log/event-trigger/svcmgr/summary-entry-statistics/filter-fail
                        leaf filter-fail {
                            type yang:counter32;
                            description "Indicates the number of times a filter does not match an logger event.";
                        }

                        ///nokia-state/state/log/event-trigger/svcmgr/summary-entry-statistics/error-admin-state
                        leaf error-admin-state {
                            type yang:counter32;
                            description
                                "Indicates the number of times the logger event will be ignored due to
                                 admin state of EHS trigger entries is out-of-service.";
                        }

                        ///nokia-state/state/log/event-trigger/svcmgr/summary-entry-statistics/error-filter
                        leaf error-filter {
                            type yang:counter32;
                            description
                                "Indicates the number of times the logger event will be ignored due to filter
                                 is not operational or is not configured in EHS trigger entries.";
                        }

                        ///nokia-state/state/log/event-trigger/svcmgr/summary-entry-statistics/error-handler
                        leaf error-handler {
                            type yang:counter32;
                            description
                                "Indicates the number of times the logger event will be ignored due to handler
                                 is not operational or is not configured in EHS trigger entries.";
                        }

                        ///nokia-state/state/log/event-trigger/svcmgr/summary-entry-statistics/trigger-count
                        leaf trigger-count {
                            type yang:counter32;
                            description "Indicates the number of times script execution is triggered after filter match.";
                        }

                        ///nokia-state/state/log/event-trigger/svcmgr/summary-entry-statistics/debounce-count
                        leaf debounce-count {
                            type yang:counter32;
                            description "Indicates the number of times script is not executed due to debounce rule.";
                        }

                    } // container summary-entry-statistics

                    ///nokia-state/state/log/event-trigger/svcmgr/entry
                    list entry {
                        key "id";
                        description "Enter the entry list instance";

                        ///nokia-state/state/log/event-trigger/svcmgr/entry/id
                        leaf id {
                            type uint32 {
                                range "1..1500";
                            }
                            description "ID of the EHS event trigger entry";
                        }

                        ///nokia-state/state/log/event-trigger/svcmgr/entry/oper-state
                        leaf oper-state {
                            type types-sros:oper-state;
                            description "Indicates the operational state of the EHS Event Trigger Entry.";
                        }

                        ///nokia-state/state/log/event-trigger/svcmgr/entry/statistics
                        container statistics {
                            description "Enter the statistics context";

                            ///nokia-state/state/log/event-trigger/svcmgr/entry/statistics/filter-match
                            leaf filter-match {
                                type yang:counter32;
                                description
                                    "Indicates the number of times a filter, for the specified trigger entry,
                                     matches an logger event.";
                            }

                            ///nokia-state/state/log/event-trigger/svcmgr/entry/statistics/filter-fail
                            leaf filter-fail {
                                type yang:counter32;
                                description
                                    "Indicates the number of times a filter, for the specified trigger entry,
                                     does not match an logger event.";
                            }

                            ///nokia-state/state/log/event-trigger/svcmgr/entry/statistics/error-admin-state
                            leaf error-admin-state {
                                type yang:counter32;
                                description
                                    "Indicates the number of times the logger event will be ignored due to
                                     admin state of EHS trigger entry is out-of-service.";
                            }

                            ///nokia-state/state/log/event-trigger/svcmgr/entry/statistics/error-filter
                            leaf error-filter {
                                type yang:counter32;
                                description
                                    "Indicates the number of times the logger event will be ignored due to filter
                                     is not operational or is not configured in EHS trigger entry.";
                            }

                            ///nokia-state/state/log/event-trigger/svcmgr/entry/statistics/error-handler
                            leaf error-handler {
                                type yang:counter32;
                                description
                                    "Indicates the number of times the logger event will be ignored due to handler
                                     is not operational or is not configured in EHS trigger entry.";
                            }

                            ///nokia-state/state/log/event-trigger/svcmgr/entry/statistics/trigger-count
                            leaf trigger-count {
                                type yang:counter32;
                                description
                                    "Indicates the number of times script execution is triggered after filter match
                                     for the specified trigger entry.";
                            }

                            ///nokia-state/state/log/event-trigger/svcmgr/entry/statistics/debounce-count
                            leaf debounce-count {
                                type yang:counter32;
                                description
                                    "Indicates the number of times script is not executed due to debounce rule
                                     for the specified trigger entry.";
                            }

                        } // container statistics

                    } // list entry

                } // list svcmgr

                ///nokia-state/state/log/event-trigger/system
                list system {
                    key "event";
                    description "Enter the system list instance";

                    ///nokia-state/state/log/event-trigger/system/event
                    leaf event {
                        type types-log:system-events;
                        description "Log event as a trigger for one or more EHS handlers";
                    }

                    ///nokia-state/state/log/event-trigger/system/oper-state
                    leaf oper-state {
                        type types-sros:oper-state;
                        description "Indicates the operational state of the EHS Event Trigger.";
                    }

                    ///nokia-state/state/log/event-trigger/system/statistics
                    container statistics {
                        description "Enter the statistics context";

                        ///nokia-state/state/log/event-trigger/system/statistics/success
                        leaf success {
                            type yang:counter32;
                            description
                                "Indicates the number of not ignored logger event occurrences
                                 associated with EHS trigger.";
                        }

                        ///nokia-state/state/log/event-trigger/system/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/system/statistics/error-admin-state
                        leaf error-admin-state {
                            type yang:counter32;
                            description
                                "Indicates the number of ignored logger event occurrences associated
                                 with EHS trigger.

                                 Event is ignored due to trigger may be out-of-service.";
                        }

                        ///nokia-state/state/log/event-trigger/system/statistics/total
                        leaf total {
                            type yang:counter32;
                            description "Sum of success + error-no-entry + error-admin-state.";
                        }

                    } // container statistics

                    ///nokia-state/state/log/event-trigger/system/summary-entry-statistics
                    container summary-entry-statistics {
                        description "Enter the summary-entry-statistics context";

                        ///nokia-state/state/log/event-trigger/system/summary-entry-statistics/filter-match
                        leaf filter-match {
                            type yang:counter32;
                            description "Indicates the number of times a filter matches an logger event.";
                        }

                        ///nokia-state/state/log/event-trigger/system/summary-entry-statistics/filter-fail
                        leaf filter-fail {
                            type yang:counter32;
                            description "Indicates the number of times a filter does not match an logger event.";
                        }

                        ///nokia-state/state/log/event-trigger/system/summary-entry-statistics/error-admin-state
                        leaf error-admin-state {
                            type yang:counter32;
                            description
                                "Indicates the number of times the logger event will be ignored due to
                                 admin state of EHS trigger entries is out-of-service.";
                        }

                        ///nokia-state/state/log/event-trigger/system/summary-entry-statistics/error-filter
                        leaf error-filter {
                            type yang:counter32;
                            description
                                "Indicates the number of times the logger event will be ignored due to filter
                                 is not operational or is not configured in EHS trigger entries.";
                        }

                        ///nokia-state/state/log/event-trigger/system/summary-entry-statistics/error-handler
                        leaf error-handler {
                            type yang:counter32;
                            description
                                "Indicates the number of times the logger event will be ignored due to handler
                                 is not operational or is not configured in EHS trigger entries.";
                        }

                        ///nokia-state/state/log/event-trigger/system/summary-entry-statistics/trigger-count
                        leaf trigger-count {
                            type yang:counter32;
                            description "Indicates the number of times script execution is triggered after filter match.";
                        }

                        ///nokia-state/state/log/event-trigger/system/summary-entry-statistics/debounce-count
                        leaf debounce-count {
                            type yang:counter32;
                            description "Indicates the number of times script is not executed due to debounce rule.";
                        }

                    } // container summary-entry-statistics

                    ///nokia-state/state/log/event-trigger/system/entry
                    list entry {
                        key "id";
                        description "Enter the entry list instance";

                        ///nokia-state/state/log/event-trigger/system/entry/id
                        leaf id {
                            type uint32 {
                                range "1..1500";
                            }
                            description "ID of the EHS event trigger entry";
                        }

                        ///nokia-state/state/log/event-trigger/system/entry/oper-state
                        leaf oper-state {
                            type types-sros:oper-state;
                            description "Indicates the operational state of the EHS Event Trigger Entry.";
                        }

                        ///nokia-state/state/log/event-trigger/system/entry/statistics
                        container statistics {
                            description "Enter the statistics context";

                            ///nokia-state/state/log/event-trigger/system/entry/statistics/filter-match
                            leaf filter-match {
                                type yang:counter32;
                                description
                                    "Indicates the number of times a filter, for the specified trigger entry,
                                     matches an logger event.";
                            }

                            ///nokia-state/state/log/event-trigger/system/entry/statistics/filter-fail
                            leaf filter-fail {
                                type yang:counter32;
                                description
                                    "Indicates the number of times a filter, for the specified trigger entry,
                                     does not match an logger event.";
                            }

                            ///nokia-state/state/log/event-trigger/system/entry/statistics/error-admin-state
                            leaf error-admin-state {
                                type yang:counter32;
                                description
                                    "Indicates the number of times the logger event will be ignored due to
                                     admin state of EHS trigger entry is out-of-service.";
                            }

                            ///nokia-state/state/log/event-trigger/system/entry/statistics/error-filter
                            leaf error-filter {
                                type yang:counter32;
                                description
                                    "Indicates the number of times the logger event will be ignored due to filter
                                     is not operational or is not configured in EHS trigger entry.";
                            }

                            ///nokia-state/state/log/event-trigger/system/entry/statistics/error-handler
                            leaf error-handler {
                                type yang:counter32;
                                description
                                    "Indicates the number of times the logger event will be ignored due to handler
                                     is not operational or is not configured in EHS trigger entry.";
                            }

                            ///nokia-state/state/log/event-trigger/system/entry/statistics/trigger-count
                            leaf trigger-count {
                                type yang:counter32;
                                description
                                    "Indicates the number of times script execution is triggered after filter match
                                     for the specified trigger entry.";
                            }

                            ///nokia-state/state/log/event-trigger/system/entry/statistics/debounce-count
                            leaf debounce-count {
                                type yang:counter32;
                                description
                                    "Indicates the number of times script is not executed due to debounce rule
                                     for the specified trigger entry.";
                            }

                        } // container statistics

                    } // list entry

                } // list system

                ///nokia-state/state/log/event-trigger/tls
                list tls {
                    key "event";
                    description "Enter the tls list instance";

                    ///nokia-state/state/log/event-trigger/tls/event
                    leaf event {
                        type types-log:tls-events;
                        description "Log event as a trigger for one or more EHS handlers";
                    }

                    ///nokia-state/state/log/event-trigger/tls/oper-state
                    leaf oper-state {
                        type types-sros:oper-state;
                        description "Indicates the operational state of the EHS Event Trigger.";
                    }

                    ///nokia-state/state/log/event-trigger/tls/statistics
                    container statistics {
                        description "Enter the statistics context";

                        ///nokia-state/state/log/event-trigger/tls/statistics/success
                        leaf success {
                            type yang:counter32;
                            description
                                "Indicates the number of not ignored logger event occurrences
                                 associated with EHS trigger.";
                        }

                        ///nokia-state/state/log/event-trigger/tls/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/tls/statistics/error-admin-state
                        leaf error-admin-state {
                            type yang:counter32;
                            description
                                "Indicates the number of ignored logger event occurrences associated
                                 with EHS trigger.

                                 Event is ignored due to trigger may be out-of-service.";
                        }

                        ///nokia-state/state/log/event-trigger/tls/statistics/total
                        leaf total {
                            type yang:counter32;
                            description "Sum of success + error-no-entry + error-admin-state.";
                        }

                    } // container statistics

                    ///nokia-state/state/log/event-trigger/tls/summary-entry-statistics
                    container summary-entry-statistics {
                        description "Enter the summary-entry-statistics context";

                        ///nokia-state/state/log/event-trigger/tls/summary-entry-statistics/filter-match
                        leaf filter-match {
                            type yang:counter32;
                            description "Indicates the number of times a filter matches an logger event.";
                        }

                        ///nokia-state/state/log/event-trigger/tls/summary-entry-statistics/filter-fail
                        leaf filter-fail {
                            type yang:counter32;
                            description "Indicates the number of times a filter does not match an logger event.";
                        }

                        ///nokia-state/state/log/event-trigger/tls/summary-entry-statistics/error-admin-state
                        leaf error-admin-state {
                            type yang:counter32;
                            description
                                "Indicates the number of times the logger event will be ignored due to
                                 admin state of EHS trigger entries is out-of-service.";
                        }

                        ///nokia-state/state/log/event-trigger/tls/summary-entry-statistics/error-filter
                        leaf error-filter {
                            type yang:counter32;
                            description
                                "Indicates the number of times the logger event will be ignored due to filter
                                 is not operational or is not configured in EHS trigger entries.";
                        }

                        ///nokia-state/state/log/event-trigger/tls/summary-entry-statistics/error-handler
                        leaf error-handler {
                            type yang:counter32;
                            description
                                "Indicates the number of times the logger event will be ignored due to handler
                                 is not operational or is not configured in EHS trigger entries.";
                        }

                        ///nokia-state/state/log/event-trigger/tls/summary-entry-statistics/trigger-count
                        leaf trigger-count {
                            type yang:counter32;
                            description "Indicates the number of times script execution is triggered after filter match.";
                        }

                        ///nokia-state/state/log/event-trigger/tls/summary-entry-statistics/debounce-count
                        leaf debounce-count {
                            type yang:counter32;
                            description "Indicates the number of times script is not executed due to debounce rule.";
                        }

                    } // container summary-entry-statistics

                    ///nokia-state/state/log/event-trigger/tls/entry
                    list entry {
                        key "id";
                        description "Enter the entry list instance";

                        ///nokia-state/state/log/event-trigger/tls/entry/id
                        leaf id {
                            type uint32 {
                                range "1..1500";
                            }
                            description "ID of the EHS event trigger entry";
                        }

                        ///nokia-state/state/log/event-trigger/tls/entry/oper-state
                        leaf oper-state {
                            type types-sros:oper-state;
                            description "Indicates the operational state of the EHS Event Trigger Entry.";
                        }

                        ///nokia-state/state/log/event-trigger/tls/entry/statistics
                        container statistics {
                            description "Enter the statistics context";

                            ///nokia-state/state/log/event-trigger/tls/entry/statistics/filter-match
                            leaf filter-match {
                                type yang:counter32;
                                description
                                    "Indicates the number of times a filter, for the specified trigger entry,
                                     matches an logger event.";
                            }

                            ///nokia-state/state/log/event-trigger/tls/entry/statistics/filter-fail
                            leaf filter-fail {
                                type yang:counter32;
                                description
                                    "Indicates the number of times a filter, for the specified trigger entry,
                                     does not match an logger event.";
                            }

                            ///nokia-state/state/log/event-trigger/tls/entry/statistics/error-admin-state
                            leaf error-admin-state {
                                type yang:counter32;
                                description
                                    "Indicates the number of times the logger event will be ignored due to
                                     admin state of EHS trigger entry is out-of-service.";
                            }

                            ///nokia-state/state/log/event-trigger/tls/entry/statistics/error-filter
                            leaf error-filter {
                                type yang:counter32;
                                description
                                    "Indicates the number of times the logger event will be ignored due to filter
                                     is not operational or is not configured in EHS trigger entry.";
                            }

                            ///nokia-state/state/log/event-trigger/tls/entry/statistics/error-handler
                            leaf error-handler {
                                type yang:counter32;
                                description
                                    "Indicates the number of times the logger event will be ignored due to handler
                                     is not operational or is not configured in EHS trigger entry.";
                            }

                            ///nokia-state/state/log/event-trigger/tls/entry/statistics/trigger-count
                            leaf trigger-count {
                                type yang:counter32;
                                description
                                    "Indicates the number of times script execution is triggered after filter match
                                     for the specified trigger entry.";
                            }

                            ///nokia-state/state/log/event-trigger/tls/entry/statistics/debounce-count
                            leaf debounce-count {
                                type yang:counter32;
                                description
                                    "Indicates the number of times script is not executed due to debounce rule
                                     for the specified trigger entry.";
                            }

                        } // container statistics

                    } // list entry

                } // list tls

                ///nokia-state/state/log/event-trigger/tree-sid
                list tree-sid {
                    key "event";
                    description "Enter the tree-sid list instance";

                    ///nokia-state/state/log/event-trigger/tree-sid/event
                    leaf event {
                        type types-log:treesid-events;
                        description "Log event as a trigger for one or more EHS handlers";
                    }

                    ///nokia-state/state/log/event-trigger/tree-sid/oper-state
                    leaf oper-state {
                        type types-sros:oper-state;
                        description "Indicates the operational state of the EHS Event Trigger.";
                    }

                    ///nokia-state/state/log/event-trigger/tree-sid/statistics
                    container statistics {
                        description "Enter the statistics context";

                        ///nokia-state/state/log/event-trigger/tree-sid/statistics/success
                        leaf success {
                            type yang:counter32;
                            description
                                "Indicates the number of not ignored logger event occurrences
                                 associated with EHS trigger.";
                        }

                        ///nokia-state/state/log/event-trigger/tree-sid/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/tree-sid/statistics/error-admin-state
                        leaf error-admin-state {
                            type yang:counter32;
                            description
                                "Indicates the number of ignored logger event occurrences associated
                                 with EHS trigger.

                                 Event is ignored due to trigger may be out-of-service.";
                        }

                        ///nokia-state/state/log/event-trigger/tree-sid/statistics/total
                        leaf total {
                            type yang:counter32;
                            description "Sum of success + error-no-entry + error-admin-state.";
                        }

                    } // container statistics

                    ///nokia-state/state/log/event-trigger/tree-sid/summary-entry-statistics
                    container summary-entry-statistics {
                        description "Enter the summary-entry-statistics context";

                        ///nokia-state/state/log/event-trigger/tree-sid/summary-entry-statistics/filter-match
                        leaf filter-match {
                            type yang:counter32;
                            description "Indicates the number of times a filter matches an logger event.";
                        }

                        ///nokia-state/state/log/event-trigger/tree-sid/summary-entry-statistics/filter-fail
                        leaf filter-fail {
                            type yang:counter32;
                            description "Indicates the number of times a filter does not match an logger event.";
                        }

                        ///nokia-state/state/log/event-trigger/tree-sid/summary-entry-statistics/error-admin-state
                        leaf error-admin-state {
                            type yang:counter32;
                            description
                                "Indicates the number of times the logger event will be ignored due to
                                 admin state of EHS trigger entries is out-of-service.";
                        }

                        ///nokia-state/state/log/event-trigger/tree-sid/summary-entry-statistics/error-filter
                        leaf error-filter {
                            type yang:counter32;
                            description
                                "Indicates the number of times the logger event will be ignored due to filter
                                 is not operational or is not configured in EHS trigger entries.";
                        }

                        ///nokia-state/state/log/event-trigger/tree-sid/summary-entry-statistics/error-handler
                        leaf error-handler {
                            type yang:counter32;
                            description
                                "Indicates the number of times the logger event will be ignored due to handler
                                 is not operational or is not configured in EHS trigger entries.";
                        }

                        ///nokia-state/state/log/event-trigger/tree-sid/summary-entry-statistics/trigger-count
                        leaf trigger-count {
                            type yang:counter32;
                            description "Indicates the number of times script execution is triggered after filter match.";
                        }

                        ///nokia-state/state/log/event-trigger/tree-sid/summary-entry-statistics/debounce-count
                        leaf debounce-count {
                            type yang:counter32;
                            description "Indicates the number of times script is not executed due to debounce rule.";
                        }

                    } // container summary-entry-statistics

                    ///nokia-state/state/log/event-trigger/tree-sid/entry
                    list entry {
                        key "id";
                        description "Enter the entry list instance";

                        ///nokia-state/state/log/event-trigger/tree-sid/entry/id
                        leaf id {
                            type uint32 {
                                range "1..1500";
                            }
                            description "ID of the EHS event trigger entry";
                        }

                        ///nokia-state/state/log/event-trigger/tree-sid/entry/oper-state
                        leaf oper-state {
                            type types-sros:oper-state;
                            description "Indicates the operational state of the EHS Event Trigger Entry.";
                        }

                        ///nokia-state/state/log/event-trigger/tree-sid/entry/statistics
                        container statistics {
                            description "Enter the statistics context";

                            ///nokia-state/state/log/event-trigger/tree-sid/entry/statistics/filter-match
                            leaf filter-match {
                                type yang:counter32;
                                description
                                    "Indicates the number of times a filter, for the specified trigger entry,
                                     matches an logger event.";
                            }

                            ///nokia-state/state/log/event-trigger/tree-sid/entry/statistics/filter-fail
                            leaf filter-fail {
                                type yang:counter32;
                                description
                                    "Indicates the number of times a filter, for the specified trigger entry,
                                     does not match an logger event.";
                            }

                            ///nokia-state/state/log/event-trigger/tree-sid/entry/statistics/error-admin-state
                            leaf error-admin-state {
                                type yang:counter32;
                                description
                                    "Indicates the number of times the logger event will be ignored due to
                                     admin state of EHS trigger entry is out-of-service.";
                            }

                            ///nokia-state/state/log/event-trigger/tree-sid/entry/statistics/error-filter
                            leaf error-filter {
                                type yang:counter32;
                                description
                                    "Indicates the number of times the logger event will be ignored due to filter
                                     is not operational or is not configured in EHS trigger entry.";
                            }

                            ///nokia-state/state/log/event-trigger/tree-sid/entry/statistics/error-handler
                            leaf error-handler {
                                type yang:counter32;
                                description
                                    "Indicates the number of times the logger event will be ignored due to handler
                                     is not operational or is not configured in EHS trigger entry.";
                            }

                            ///nokia-state/state/log/event-trigger/tree-sid/entry/statistics/trigger-count
                            leaf trigger-count {
                                type yang:counter32;
                                description
                                    "Indicates the number of times script execution is triggered after filter match
                                     for the specified trigger entry.";
                            }

                            ///nokia-state/state/log/event-trigger/tree-sid/entry/statistics/debounce-count
                            leaf debounce-count {
                                type yang:counter32;
                                description
                                    "Indicates the number of times script is not executed due to debounce rule
                                     for the specified trigger entry.";
                            }

                        } // container statistics

                    } // list entry

                } // list tree-sid

                ///nokia-state/state/log/event-trigger/user
                list user {
                    key "event";
                    description "Enter the user list instance";

                    ///nokia-state/state/log/event-trigger/user/event
                    leaf event {
                        type types-log:user-events;
                        description "Log event as a trigger for one or more EHS handlers";
                    }

                    ///nokia-state/state/log/event-trigger/user/oper-state
                    leaf oper-state {
                        type types-sros:oper-state;
                        description "Indicates the operational state of the EHS Event Trigger.";
                    }

                    ///nokia-state/state/log/event-trigger/user/statistics
                    container statistics {
                        description "Enter the statistics context";

                        ///nokia-state/state/log/event-trigger/user/statistics/success
                        leaf success {
                            type yang:counter32;
                            description
                                "Indicates the number of not ignored logger event occurrences
                                 associated with EHS trigger.";
                        }

                        ///nokia-state/state/log/event-trigger/user/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/user/statistics/error-admin-state
                        leaf error-admin-state {
                            type yang:counter32;
                            description
                                "Indicates the number of ignored logger event occurrences associated
                                 with EHS trigger.

                                 Event is ignored due to trigger may be out-of-service.";
                        }

                        ///nokia-state/state/log/event-trigger/user/statistics/total
                        leaf total {
                            type yang:counter32;
                            description "Sum of success + error-no-entry + error-admin-state.";
                        }

                    } // container statistics

                    ///nokia-state/state/log/event-trigger/user/summary-entry-statistics
                    container summary-entry-statistics {
                        description "Enter the summary-entry-statistics context";

                        ///nokia-state/state/log/event-trigger/user/summary-entry-statistics/filter-match
                        leaf filter-match {
                            type yang:counter32;
                            description "Indicates the number of times a filter matches an logger event.";
                        }

                        ///nokia-state/state/log/event-trigger/user/summary-entry-statistics/filter-fail
                        leaf filter-fail {
                            type yang:counter32;
                            description "Indicates the number of times a filter does not match an logger event.";
                        }

                        ///nokia-state/state/log/event-trigger/user/summary-entry-statistics/error-admin-state
                        leaf error-admin-state {
                            type yang:counter32;
                            description
                                "Indicates the number of times the logger event will be ignored due to
                                 admin state of EHS trigger entries is out-of-service.";
                        }

                        ///nokia-state/state/log/event-trigger/user/summary-entry-statistics/error-filter
                        leaf error-filter {
                            type yang:counter32;
                            description
                                "Indicates the number of times the logger event will be ignored due to filter
                                 is not operational or is not configured in EHS trigger entries.";
                        }

                        ///nokia-state/state/log/event-trigger/user/summary-entry-statistics/error-handler
                        leaf error-handler {
                            type yang:counter32;
                            description
                                "Indicates the number of times the logger event will be ignored due to handler
                                 is not operational or is not configured in EHS trigger entries.";
                        }

                        ///nokia-state/state/log/event-trigger/user/summary-entry-statistics/trigger-count
                        leaf trigger-count {
                            type yang:counter32;
                            description "Indicates the number of times script execution is triggered after filter match.";
                        }

                        ///nokia-state/state/log/event-trigger/user/summary-entry-statistics/debounce-count
                        leaf debounce-count {
                            type yang:counter32;
                            description "Indicates the number of times script is not executed due to debounce rule.";
                        }

                    } // container summary-entry-statistics

                    ///nokia-state/state/log/event-trigger/user/entry
                    list entry {
                        key "id";
                        description "Enter the entry list instance";

                        ///nokia-state/state/log/event-trigger/user/entry/id
                        leaf id {
                            type uint32 {
                                range "1..1500";
                            }
                            description "ID of the EHS event trigger entry";
                        }

                        ///nokia-state/state/log/event-trigger/user/entry/oper-state
                        leaf oper-state {
                            type types-sros:oper-state;
                            description "Indicates the operational state of the EHS Event Trigger Entry.";
                        }

                        ///nokia-state/state/log/event-trigger/user/entry/statistics
                        container statistics {
                            description "Enter the statistics context";

                            ///nokia-state/state/log/event-trigger/user/entry/statistics/filter-match
                            leaf filter-match {
                                type yang:counter32;
                                description
                                    "Indicates the number of times a filter, for the specified trigger entry,
                                     matches an logger event.";
                            }

                            ///nokia-state/state/log/event-trigger/user/entry/statistics/filter-fail
                            leaf filter-fail {
                                type yang:counter32;
                                description
                                    "Indicates the number of times a filter, for the specified trigger entry,
                                     does not match an logger event.";
                            }

                            ///nokia-state/state/log/event-trigger/user/entry/statistics/error-admin-state
                            leaf error-admin-state {
                                type yang:counter32;
                                description
                                    "Indicates the number of times the logger event will be ignored due to
                                     admin state of EHS trigger entry is out-of-service.";
                            }

                            ///nokia-state/state/log/event-trigger/user/entry/statistics/error-filter
                            leaf error-filter {
                                type yang:counter32;
                                description
                                    "Indicates the number of times the logger event will be ignored due to filter
                                     is not operational or is not configured in EHS trigger entry.";
                            }

                            ///nokia-state/state/log/event-trigger/user/entry/statistics/error-handler
                            leaf error-handler {
                                type yang:counter32;
                                description
                                    "Indicates the number of times the logger event will be ignored due to handler
                                     is not operational or is not configured in EHS trigger entry.";
                            }

                            ///nokia-state/state/log/event-trigger/user/entry/statistics/trigger-count
                            leaf trigger-count {
                                type yang:counter32;
                                description
                                    "Indicates the number of times script execution is triggered after filter match
                                     for the specified trigger entry.";
                            }

                            ///nokia-state/state/log/event-trigger/user/entry/statistics/debounce-count
                            leaf debounce-count {
                                type yang:counter32;
                                description
                                    "Indicates the number of times script is not executed due to debounce rule
                                     for the specified trigger entry.";
                            }

                        } // container statistics

                    } // list entry

                } // list user

                ///nokia-state/state/log/event-trigger/video
                list video {
                    key "event";
                    description "Enter the video list instance";

                    ///nokia-state/state/log/event-trigger/video/event
                    leaf event {
                        type types-log:video-events;
                        description "Log event as a trigger for one or more EHS handlers";
                    }

                    ///nokia-state/state/log/event-trigger/video/oper-state
                    leaf oper-state {
                        type types-sros:oper-state;
                        description "Indicates the operational state of the EHS Event Trigger.";
                    }

                    ///nokia-state/state/log/event-trigger/video/statistics
                    container statistics {
                        description "Enter the statistics context";

                        ///nokia-state/state/log/event-trigger/video/statistics/success
                        leaf success {
                            type yang:counter32;
                            description
                                "Indicates the number of not ignored logger event occurrences
                                 associated with EHS trigger.";
                        }

                        ///nokia-state/state/log/event-trigger/video/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/video/statistics/error-admin-state
                        leaf error-admin-state {
                            type yang:counter32;
                            description
                                "Indicates the number of ignored logger event occurrences associated
                                 with EHS trigger.

                                 Event is ignored due to trigger may be out-of-service.";
                        }

                        ///nokia-state/state/log/event-trigger/video/statistics/total
                        leaf total {
                            type yang:counter32;
                            description "Sum of success + error-no-entry + error-admin-state.";
                        }

                    } // container statistics

                    ///nokia-state/state/log/event-trigger/video/summary-entry-statistics
                    container summary-entry-statistics {
                        description "Enter the summary-entry-statistics context";

                        ///nokia-state/state/log/event-trigger/video/summary-entry-statistics/filter-match
                        leaf filter-match {
                            type yang:counter32;
                            description "Indicates the number of times a filter matches an logger event.";
                        }

                        ///nokia-state/state/log/event-trigger/video/summary-entry-statistics/filter-fail
                        leaf filter-fail {
                            type yang:counter32;
                            description "Indicates the number of times a filter does not match an logger event.";
                        }

                        ///nokia-state/state/log/event-trigger/video/summary-entry-statistics/error-admin-state
                        leaf error-admin-state {
                            type yang:counter32;
                            description
                                "Indicates the number of times the logger event will be ignored due to
                                 admin state of EHS trigger entries is out-of-service.";
                        }

                        ///nokia-state/state/log/event-trigger/video/summary-entry-statistics/error-filter
                        leaf error-filter {
                            type yang:counter32;
                            description
                                "Indicates the number of times the logger event will be ignored due to filter
                                 is not operational or is not configured in EHS trigger entries.";
                        }

                        ///nokia-state/state/log/event-trigger/video/summary-entry-statistics/error-handler
                        leaf error-handler {
                            type yang:counter32;
                            description
                                "Indicates the number of times the logger event will be ignored due to handler
                                 is not operational or is not configured in EHS trigger entries.";
                        }

                        ///nokia-state/state/log/event-trigger/video/summary-entry-statistics/trigger-count
                        leaf trigger-count {
                            type yang:counter32;
                            description "Indicates the number of times script execution is triggered after filter match.";
                        }

                        ///nokia-state/state/log/event-trigger/video/summary-entry-statistics/debounce-count
                        leaf debounce-count {
                            type yang:counter32;
                            description "Indicates the number of times script is not executed due to debounce rule.";
                        }

                    } // container summary-entry-statistics

                    ///nokia-state/state/log/event-trigger/video/entry
                    list entry {
                        key "id";
                        description "Enter the entry list instance";

                        ///nokia-state/state/log/event-trigger/video/entry/id
                        leaf id {
                            type uint32 {
                                range "1..1500";
                            }
                            description "ID of the EHS event trigger entry";
                        }

                        ///nokia-state/state/log/event-trigger/video/entry/oper-state
                        leaf oper-state {
                            type types-sros:oper-state;
                            description "Indicates the operational state of the EHS Event Trigger Entry.";
                        }

                        ///nokia-state/state/log/event-trigger/video/entry/statistics
                        container statistics {
                            description "Enter the statistics context";

                            ///nokia-state/state/log/event-trigger/video/entry/statistics/filter-match
                            leaf filter-match {
                                type yang:counter32;
                                description
                                    "Indicates the number of times a filter, for the specified trigger entry,
                                     matches an logger event.";
                            }

                            ///nokia-state/state/log/event-trigger/video/entry/statistics/filter-fail
                            leaf filter-fail {
                                type yang:counter32;
                                description
                                    "Indicates the number of times a filter, for the specified trigger entry,
                                     does not match an logger event.";
                            }

                            ///nokia-state/state/log/event-trigger/video/entry/statistics/error-admin-state
                            leaf error-admin-state {
                                type yang:counter32;
                                description
                                    "Indicates the number of times the logger event will be ignored due to
                                     admin state of EHS trigger entry is out-of-service.";
                            }

                            ///nokia-state/state/log/event-trigger/video/entry/statistics/error-filter
                            leaf error-filter {
                                type yang:counter32;
                                description
                                    "Indicates the number of times the logger event will be ignored due to filter
                                     is not operational or is not configured in EHS trigger entry.";
                            }

                            ///nokia-state/state/log/event-trigger/video/entry/statistics/error-handler
                            leaf error-handler {
                                type yang:counter32;
                                description
                                    "Indicates the number of times the logger event will be ignored due to handler
                                     is not operational or is not configured in EHS trigger entry.";
                            }

                            ///nokia-state/state/log/event-trigger/video/entry/statistics/trigger-count
                            leaf trigger-count {
                                type yang:counter32;
                                description
                                    "Indicates the number of times script execution is triggered after filter match
                                     for the specified trigger entry.";
                            }

                            ///nokia-state/state/log/event-trigger/video/entry/statistics/debounce-count
                            leaf debounce-count {
                                type yang:counter32;
                                description
                                    "Indicates the number of times script is not executed due to debounce rule
                                     for the specified trigger entry.";
                            }

                        } // container statistics

                    } // list entry

                } // list video

                ///nokia-state/state/log/event-trigger/vrrp
                list vrrp {
                    key "event";
                    description "Enter the vrrp list instance";

                    ///nokia-state/state/log/event-trigger/vrrp/event
                    leaf event {
                        type types-log:vrrp-events;
                        description "Log event as a trigger for one or more EHS handlers";
                    }

                    ///nokia-state/state/log/event-trigger/vrrp/oper-state
                    leaf oper-state {
                        type types-sros:oper-state;
                        description "Indicates the operational state of the EHS Event Trigger.";
                    }

                    ///nokia-state/state/log/event-trigger/vrrp/statistics
                    container statistics {
                        description "Enter the statistics context";

                        ///nokia-state/state/log/event-trigger/vrrp/statistics/success
                        leaf success {
                            type yang:counter32;
                            description
                                "Indicates the number of not ignored logger event occurrences
                                 associated with EHS trigger.";
                        }

                        ///nokia-state/state/log/event-trigger/vrrp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/vrrp/statistics/error-admin-state
                        leaf error-admin-state {
                            type yang:counter32;
                            description
                                "Indicates the number of ignored logger event occurrences associated
                                 with EHS trigger.

                                 Event is ignored due to trigger may be out-of-service.";
                        }

                        ///nokia-state/state/log/event-trigger/vrrp/statistics/total
                        leaf total {
                            type yang:counter32;
                            description "Sum of success + error-no-entry + error-admin-state.";
                        }

                    } // container statistics

                    ///nokia-state/state/log/event-trigger/vrrp/summary-entry-statistics
                    container summary-entry-statistics {
                        description "Enter the summary-entry-statistics context";

                        ///nokia-state/state/log/event-trigger/vrrp/summary-entry-statistics/filter-match
                        leaf filter-match {
                            type yang:counter32;
                            description "Indicates the number of times a filter matches an logger event.";
                        }

                        ///nokia-state/state/log/event-trigger/vrrp/summary-entry-statistics/filter-fail
                        leaf filter-fail {
                            type yang:counter32;
                            description "Indicates the number of times a filter does not match an logger event.";
                        }

                        ///nokia-state/state/log/event-trigger/vrrp/summary-entry-statistics/error-admin-state
                        leaf error-admin-state {
                            type yang:counter32;
                            description
                                "Indicates the number of times the logger event will be ignored due to
                                 admin state of EHS trigger entries is out-of-service.";
                        }

                        ///nokia-state/state/log/event-trigger/vrrp/summary-entry-statistics/error-filter
                        leaf error-filter {
                            type yang:counter32;
                            description
                                "Indicates the number of times the logger event will be ignored due to filter
                                 is not operational or is not configured in EHS trigger entries.";
                        }

                        ///nokia-state/state/log/event-trigger/vrrp/summary-entry-statistics/error-handler
                        leaf error-handler {
                            type yang:counter32;
                            description
                                "Indicates the number of times the logger event will be ignored due to handler
                                 is not operational or is not configured in EHS trigger entries.";
                        }

                        ///nokia-state/state/log/event-trigger/vrrp/summary-entry-statistics/trigger-count
                        leaf trigger-count {
                            type yang:counter32;
                            description "Indicates the number of times script execution is triggered after filter match.";
                        }

                        ///nokia-state/state/log/event-trigger/vrrp/summary-entry-statistics/debounce-count
                        leaf debounce-count {
                            type yang:counter32;
                            description "Indicates the number of times script is not executed due to debounce rule.";
                        }

                    } // container summary-entry-statistics

                    ///nokia-state/state/log/event-trigger/vrrp/entry
                    list entry {
                        key "id";
                        description "Enter the entry list instance";

                        ///nokia-state/state/log/event-trigger/vrrp/entry/id
                        leaf id {
                            type uint32 {
                                range "1..1500";
                            }
                            description "ID of the EHS event trigger entry";
                        }

                        ///nokia-state/state/log/event-trigger/vrrp/entry/oper-state
                        leaf oper-state {
                            type types-sros:oper-state;
                            description "Indicates the operational state of the EHS Event Trigger Entry.";
                        }

                        ///nokia-state/state/log/event-trigger/vrrp/entry/statistics
                        container statistics {
                            description "Enter the statistics context";

                            ///nokia-state/state/log/event-trigger/vrrp/entry/statistics/filter-match
                            leaf filter-match {
                                type yang:counter32;
                                description
                                    "Indicates the number of times a filter, for the specified trigger entry,
                                     matches an logger event.";
                            }

                            ///nokia-state/state/log/event-trigger/vrrp/entry/statistics/filter-fail
                            leaf filter-fail {
                                type yang:counter32;
                                description
                                    "Indicates the number of times a filter, for the specified trigger entry,
                                     does not match an logger event.";
                            }

                            ///nokia-state/state/log/event-trigger/vrrp/entry/statistics/error-admin-state
                            leaf error-admin-state {
                                type yang:counter32;
                                description
                                    "Indicates the number of times the logger event will be ignored due to
                                     admin state of EHS trigger entry is out-of-service.";
                            }

                            ///nokia-state/state/log/event-trigger/vrrp/entry/statistics/error-filter
                            leaf error-filter {
                                type yang:counter32;
                                description
                                    "Indicates the number of times the logger event will be ignored due to filter
                                     is not operational or is not configured in EHS trigger entry.";
                            }

                            ///nokia-state/state/log/event-trigger/vrrp/entry/statistics/error-handler
                            leaf error-handler {
                                type yang:counter32;
                                description
                                    "Indicates the number of times the logger event will be ignored due to handler
                                     is not operational or is not configured in EHS trigger entry.";
                            }

                            ///nokia-state/state/log/event-trigger/vrrp/entry/statistics/trigger-count
                            leaf trigger-count {
                                type yang:counter32;
                                description
                                    "Indicates the number of times script execution is triggered after filter match
                                     for the specified trigger entry.";
                            }

                            ///nokia-state/state/log/event-trigger/vrrp/entry/statistics/debounce-count
                            leaf debounce-count {
                                type yang:counter32;
                                description
                                    "Indicates the number of times script is not executed due to debounce rule
                                     for the specified trigger entry.";
                            }

                        } // container statistics

                    } // list entry

                } // list vrrp

                ///nokia-state/state/log/event-trigger/vrtr
                list vrtr {
                    key "event";
                    description "Enter the vrtr list instance";

                    ///nokia-state/state/log/event-trigger/vrtr/event
                    leaf event {
                        type types-log:vrtr-events;
                        description "Log event as a trigger for one or more EHS handlers";
                    }

                    ///nokia-state/state/log/event-trigger/vrtr/oper-state
                    leaf oper-state {
                        type types-sros:oper-state;
                        description "Indicates the operational state of the EHS Event Trigger.";
                    }

                    ///nokia-state/state/log/event-trigger/vrtr/statistics
                    container statistics {
                        description "Enter the statistics context";

                        ///nokia-state/state/log/event-trigger/vrtr/statistics/success
                        leaf success {
                            type yang:counter32;
                            description
                                "Indicates the number of not ignored logger event occurrences
                                 associated with EHS trigger.";
                        }

                        ///nokia-state/state/log/event-trigger/vrtr/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/vrtr/statistics/error-admin-state
                        leaf error-admin-state {
                            type yang:counter32;
                            description
                                "Indicates the number of ignored logger event occurrences associated
                                 with EHS trigger.

                                 Event is ignored due to trigger may be out-of-service.";
                        }

                        ///nokia-state/state/log/event-trigger/vrtr/statistics/total
                        leaf total {
                            type yang:counter32;
                            description "Sum of success + error-no-entry + error-admin-state.";
                        }

                    } // container statistics

                    ///nokia-state/state/log/event-trigger/vrtr/summary-entry-statistics
                    container summary-entry-statistics {
                        description "Enter the summary-entry-statistics context";

                        ///nokia-state/state/log/event-trigger/vrtr/summary-entry-statistics/filter-match
                        leaf filter-match {
                            type yang:counter32;
                            description "Indicates the number of times a filter matches an logger event.";
                        }

                        ///nokia-state/state/log/event-trigger/vrtr/summary-entry-statistics/filter-fail
                        leaf filter-fail {
                            type yang:counter32;
                            description "Indicates the number of times a filter does not match an logger event.";
                        }

                        ///nokia-state/state/log/event-trigger/vrtr/summary-entry-statistics/error-admin-state
                        leaf error-admin-state {
                            type yang:counter32;
                            description
                                "Indicates the number of times the logger event will be ignored due to
                                 admin state of EHS trigger entries is out-of-service.";
                        }

                        ///nokia-state/state/log/event-trigger/vrtr/summary-entry-statistics/error-filter
                        leaf error-filter {
                            type yang:counter32;
                            description
                                "Indicates the number of times the logger event will be ignored due to filter
                                 is not operational or is not configured in EHS trigger entries.";
                        }

                        ///nokia-state/state/log/event-trigger/vrtr/summary-entry-statistics/error-handler
                        leaf error-handler {
                            type yang:counter32;
                            description
                                "Indicates the number of times the logger event will be ignored due to handler
                                 is not operational or is not configured in EHS trigger entries.";
                        }

                        ///nokia-state/state/log/event-trigger/vrtr/summary-entry-statistics/trigger-count
                        leaf trigger-count {
                            type yang:counter32;
                            description "Indicates the number of times script execution is triggered after filter match.";
                        }

                        ///nokia-state/state/log/event-trigger/vrtr/summary-entry-statistics/debounce-count
                        leaf debounce-count {
                            type yang:counter32;
                            description "Indicates the number of times script is not executed due to debounce rule.";
                        }

                    } // container summary-entry-statistics

                    ///nokia-state/state/log/event-trigger/vrtr/entry
                    list entry {
                        key "id";
                        description "Enter the entry list instance";

                        ///nokia-state/state/log/event-trigger/vrtr/entry/id
                        leaf id {
                            type uint32 {
                                range "1..1500";
                            }
                            description "ID of the EHS event trigger entry";
                        }

                        ///nokia-state/state/log/event-trigger/vrtr/entry/oper-state
                        leaf oper-state {
                            type types-sros:oper-state;
                            description "Indicates the operational state of the EHS Event Trigger Entry.";
                        }

                        ///nokia-state/state/log/event-trigger/vrtr/entry/statistics
                        container statistics {
                            description "Enter the statistics context";

                            ///nokia-state/state/log/event-trigger/vrtr/entry/statistics/filter-match
                            leaf filter-match {
                                type yang:counter32;
                                description
                                    "Indicates the number of times a filter, for the specified trigger entry,
                                     matches an logger event.";
                            }

                            ///nokia-state/state/log/event-trigger/vrtr/entry/statistics/filter-fail
                            leaf filter-fail {
                                type yang:counter32;
                                description
                                    "Indicates the number of times a filter, for the specified trigger entry,
                                     does not match an logger event.";
                            }

                            ///nokia-state/state/log/event-trigger/vrtr/entry/statistics/error-admin-state
                            leaf error-admin-state {
                                type yang:counter32;
                                description
                                    "Indicates the number of times the logger event will be ignored due to
                                     admin state of EHS trigger entry is out-of-service.";
                            }

                            ///nokia-state/state/log/event-trigger/vrtr/entry/statistics/error-filter
                            leaf error-filter {
                                type yang:counter32;
                                description
                                    "Indicates the number of times the logger event will be ignored due to filter
                                     is not operational or is not configured in EHS trigger entry.";
                            }

                            ///nokia-state/state/log/event-trigger/vrtr/entry/statistics/error-handler
                            leaf error-handler {
                                type yang:counter32;
                                description
                                    "Indicates the number of times the logger event will be ignored due to handler
                                     is not operational or is not configured in EHS trigger entry.";
                            }

                            ///nokia-state/state/log/event-trigger/vrtr/entry/statistics/trigger-count
                            leaf trigger-count {
                                type yang:counter32;
                                description
                                    "Indicates the number of times script execution is triggered after filter match
                                     for the specified trigger entry.";
                            }

                            ///nokia-state/state/log/event-trigger/vrtr/entry/statistics/debounce-count
                            leaf debounce-count {
                                type yang:counter32;
                                description
                                    "Indicates the number of times script is not executed due to debounce rule
                                     for the specified trigger entry.";
                            }

                        } // container statistics

                    } // list entry

                } // list vrtr

                ///nokia-state/state/log/event-trigger/wlan-gw
                list wlan-gw {
                    key "event";
                    description "Enter the wlan-gw list instance";

                    ///nokia-state/state/log/event-trigger/wlan-gw/event
                    leaf event {
                        type types-log:wlan-gw-events;
                        description "Log event as a trigger for one or more EHS handlers";
                    }

                    ///nokia-state/state/log/event-trigger/wlan-gw/oper-state
                    leaf oper-state {
                        type types-sros:oper-state;
                        description "Indicates the operational state of the EHS Event Trigger.";
                    }

                    ///nokia-state/state/log/event-trigger/wlan-gw/statistics
                    container statistics {
                        description "Enter the statistics context";

                        ///nokia-state/state/log/event-trigger/wlan-gw/statistics/success
                        leaf success {
                            type yang:counter32;
                            description
                                "Indicates the number of not ignored logger event occurrences
                                 associated with EHS trigger.";
                        }

                        ///nokia-state/state/log/event-trigger/wlan-gw/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/wlan-gw/statistics/error-admin-state
                        leaf error-admin-state {
                            type yang:counter32;
                            description
                                "Indicates the number of ignored logger event occurrences associated
                                 with EHS trigger.

                                 Event is ignored due to trigger may be out-of-service.";
                        }

                        ///nokia-state/state/log/event-trigger/wlan-gw/statistics/total
                        leaf total {
                            type yang:counter32;
                            description "Sum of success + error-no-entry + error-admin-state.";
                        }

                    } // container statistics

                    ///nokia-state/state/log/event-trigger/wlan-gw/summary-entry-statistics
                    container summary-entry-statistics {
                        description "Enter the summary-entry-statistics context";

                        ///nokia-state/state/log/event-trigger/wlan-gw/summary-entry-statistics/filter-match
                        leaf filter-match {
                            type yang:counter32;
                            description "Indicates the number of times a filter matches an logger event.";
                        }

                        ///nokia-state/state/log/event-trigger/wlan-gw/summary-entry-statistics/filter-fail
                        leaf filter-fail {
                            type yang:counter32;
                            description "Indicates the number of times a filter does not match an logger event.";
                        }

                        ///nokia-state/state/log/event-trigger/wlan-gw/summary-entry-statistics/error-admin-state
                        leaf error-admin-state {
                            type yang:counter32;
                            description
                                "Indicates the number of times the logger event will be ignored due to
                                 admin state of EHS trigger entries is out-of-service.";
                        }

                        ///nokia-state/state/log/event-trigger/wlan-gw/summary-entry-statistics/error-filter
                        leaf error-filter {
                            type yang:counter32;
                            description
                                "Indicates the number of times the logger event will be ignored due to filter
                                 is not operational or is not configured in EHS trigger entries.";
                        }

                        ///nokia-state/state/log/event-trigger/wlan-gw/summary-entry-statistics/error-handler
                        leaf error-handler {
                            type yang:counter32;
                            description
                                "Indicates the number of times the logger event will be ignored due to handler
                                 is not operational or is not configured in EHS trigger entries.";
                        }

                        ///nokia-state/state/log/event-trigger/wlan-gw/summary-entry-statistics/trigger-count
                        leaf trigger-count {
                            type yang:counter32;
                            description "Indicates the number of times script execution is triggered after filter match.";
                        }

                        ///nokia-state/state/log/event-trigger/wlan-gw/summary-entry-statistics/debounce-count
                        leaf debounce-count {
                            type yang:counter32;
                            description "Indicates the number of times script is not executed due to debounce rule.";
                        }

                    } // container summary-entry-statistics

                    ///nokia-state/state/log/event-trigger/wlan-gw/entry
                    list entry {
                        key "id";
                        description "Enter the entry list instance";

                        ///nokia-state/state/log/event-trigger/wlan-gw/entry/id
                        leaf id {
                            type uint32 {
                                range "1..1500";
                            }
                            description "ID of the EHS event trigger entry";
                        }

                        ///nokia-state/state/log/event-trigger/wlan-gw/entry/oper-state
                        leaf oper-state {
                            type types-sros:oper-state;
                            description "Indicates the operational state of the EHS Event Trigger Entry.";
                        }

                        ///nokia-state/state/log/event-trigger/wlan-gw/entry/statistics
                        container statistics {
                            description "Enter the statistics context";

                            ///nokia-state/state/log/event-trigger/wlan-gw/entry/statistics/filter-match
                            leaf filter-match {
                                type yang:counter32;
                                description
                                    "Indicates the number of times a filter, for the specified trigger entry,
                                     matches an logger event.";
                            }

                            ///nokia-state/state/log/event-trigger/wlan-gw/entry/statistics/filter-fail
                            leaf filter-fail {
                                type yang:counter32;
                                description
                                    "Indicates the number of times a filter, for the specified trigger entry,
                                     does not match an logger event.";
                            }

                            ///nokia-state/state/log/event-trigger/wlan-gw/entry/statistics/error-admin-state
                            leaf error-admin-state {
                                type yang:counter32;
                                description
                                    "Indicates the number of times the logger event will be ignored due to
                                     admin state of EHS trigger entry is out-of-service.";
                            }

                            ///nokia-state/state/log/event-trigger/wlan-gw/entry/statistics/error-filter
                            leaf error-filter {
                                type yang:counter32;
                                description
                                    "Indicates the number of times the logger event will be ignored due to filter
                                     is not operational or is not configured in EHS trigger entry.";
                            }

                            ///nokia-state/state/log/event-trigger/wlan-gw/entry/statistics/error-handler
                            leaf error-handler {
                                type yang:counter32;
                                description
                                    "Indicates the number of times the logger event will be ignored due to handler
                                     is not operational or is not configured in EHS trigger entry.";
                            }

                            ///nokia-state/state/log/event-trigger/wlan-gw/entry/statistics/trigger-count
                            leaf trigger-count {
                                type yang:counter32;
                                description
                                    "Indicates the number of times script execution is triggered after filter match
                                     for the specified trigger entry.";
                            }

                            ///nokia-state/state/log/event-trigger/wlan-gw/entry/statistics/debounce-count
                            leaf debounce-count {
                                type yang:counter32;
                                description
                                    "Indicates the number of times script is not executed due to debounce rule
                                     for the specified trigger entry.";
                            }

                        } // container statistics

                    } // list entry

                } // list wlan-gw

                ///nokia-state/state/log/event-trigger/wpp
                list wpp {
                    key "event";
                    description "Enter the wpp list instance";

                    ///nokia-state/state/log/event-trigger/wpp/event
                    leaf event {
                        type types-log:wpp-events;
                        description "Log event as a trigger for one or more EHS handlers";
                    }

                    ///nokia-state/state/log/event-trigger/wpp/oper-state
                    leaf oper-state {
                        type types-sros:oper-state;
                        description "Indicates the operational state of the EHS Event Trigger.";
                    }

                    ///nokia-state/state/log/event-trigger/wpp/statistics
                    container statistics {
                        description "Enter the statistics context";

                        ///nokia-state/state/log/event-trigger/wpp/statistics/success
                        leaf success {
                            type yang:counter32;
                            description
                                "Indicates the number of not ignored logger event occurrences
                                 associated with EHS trigger.";
                        }

                        ///nokia-state/state/log/event-trigger/wpp/statistics/error-no-entry
                        leaf error-no-entry {
                            type yang:counter32;
                            description
                                "Indicates the number of ignored logger event occurrences associated
                                 with EHS trigger.

                                 Event is ignored due to no trigger entry configured for this trigger.";
                        }

                        ///nokia-state/state/log/event-trigger/wpp/statistics/error-admin-state
                        leaf error-admin-state {
                            type yang:counter32;
                            description
                                "Indicates the number of ignored logger event occurrences associated
                                 with EHS trigger.

                                 Event is ignored due to trigger may be out-of-service.";
                        }

                        ///nokia-state/state/log/event-trigger/wpp/statistics/total
                        leaf total {
                            type yang:counter32;
                            description "Sum of success + error-no-entry + error-admin-state.";
                        }

                    } // container statistics

                    ///nokia-state/state/log/event-trigger/wpp/summary-entry-statistics
                    container summary-entry-statistics {
                        description "Enter the summary-entry-statistics context";

                        ///nokia-state/state/log/event-trigger/wpp/summary-entry-statistics/filter-match
                        leaf filter-match {
                            type yang:counter32;
                            description "Indicates the number of times a filter matches an logger event.";
                        }

                        ///nokia-state/state/log/event-trigger/wpp/summary-entry-statistics/filter-fail
                        leaf filter-fail {
                            type yang:counter32;
                            description "Indicates the number of times a filter does not match an logger event.";
                        }

                        ///nokia-state/state/log/event-trigger/wpp/summary-entry-statistics/error-admin-state
                        leaf error-admin-state {
                            type yang:counter32;
                            description
                                "Indicates the number of times the logger event will be ignored due to
                                 admin state of EHS trigger entries is out-of-service.";
                        }

                        ///nokia-state/state/log/event-trigger/wpp/summary-entry-statistics/error-filter
                        leaf error-filter {
                            type yang:counter32;
                            description
                                "Indicates the number of times the logger event will be ignored due to filter
                                 is not operational or is not configured in EHS trigger entries.";
                        }

                        ///nokia-state/state/log/event-trigger/wpp/summary-entry-statistics/error-handler
                        leaf error-handler {
                            type yang:counter32;
                            description
                                "Indicates the number of times the logger event will be ignored due to handler
                                 is not operational or is not configured in EHS trigger entries.";
                        }

                        ///nokia-state/state/log/event-trigger/wpp/summary-entry-statistics/trigger-count
                        leaf trigger-count {
                            type yang:counter32;
                            description "Indicates the number of times script execution is triggered after filter match.";
                        }

                        ///nokia-state/state/log/event-trigger/wpp/summary-entry-statistics/debounce-count
                        leaf debounce-count {
                            type yang:counter32;
                            description "Indicates the number of times script is not executed due to debounce rule.";
                        }

                    } // container summary-entry-statistics

                    ///nokia-state/state/log/event-trigger/wpp/entry
                    list entry {
                        key "id";
                        description "Enter the entry list instance";

                        ///nokia-state/state/log/event-trigger/wpp/entry/id
                        leaf id {
                            type uint32 {
                                range "1..1500";
                            }
                            description "ID of the EHS event trigger entry";
                        }

                        ///nokia-state/state/log/event-trigger/wpp/entry/oper-state
                        leaf oper-state {
                            type types-sros:oper-state;
                            description "Indicates the operational state of the EHS Event Trigger Entry.";
                        }

                        ///nokia-state/state/log/event-trigger/wpp/entry/statistics
                        container statistics {
                            description "Enter the statistics context";

                            ///nokia-state/state/log/event-trigger/wpp/entry/statistics/filter-match
                            leaf filter-match {
                                type yang:counter32;
                                description
                                    "Indicates the number of times a filter, for the specified trigger entry,
                                     matches an logger event.";
                            }

                            ///nokia-state/state/log/event-trigger/wpp/entry/statistics/filter-fail
                            leaf filter-fail {
                                type yang:counter32;
                                description
                                    "Indicates the number of times a filter, for the specified trigger entry,
                                     does not match an logger event.";
                            }

                            ///nokia-state/state/log/event-trigger/wpp/entry/statistics/error-admin-state
                            leaf error-admin-state {
                                type yang:counter32;
                                description
                                    "Indicates the number of times the logger event will be ignored due to
                                     admin state of EHS trigger entry is out-of-service.";
                            }

                            ///nokia-state/state/log/event-trigger/wpp/entry/statistics/error-filter
                            leaf error-filter {
                                type yang:counter32;
                                description
                                    "Indicates the number of times the logger event will be ignored due to filter
                                     is not operational or is not configured in EHS trigger entry.";
                            }

                            ///nokia-state/state/log/event-trigger/wpp/entry/statistics/error-handler
                            leaf error-handler {
                                type yang:counter32;
                                description
                                    "Indicates the number of times the logger event will be ignored due to handler
                                     is not operational or is not configured in EHS trigger entry.";
                            }

                            ///nokia-state/state/log/event-trigger/wpp/entry/statistics/trigger-count
                            leaf trigger-count {
                                type yang:counter32;
                                description
                                    "Indicates the number of times script execution is triggered after filter match
                                     for the specified trigger entry.";
                            }

                            ///nokia-state/state/log/event-trigger/wpp/entry/statistics/debounce-count
                            leaf debounce-count {
                                type yang:counter32;
                                description
                                    "Indicates the number of times script is not executed due to debounce rule
                                     for the specified trigger entry.";
                            }

                        } // container statistics

                    } // list entry

                } // list wpp

            } // container event-trigger

            ///nokia-state/state/log/file
            list file {
                key "file-policy-name";
                description "Enter the file list instance";

                ///nokia-state/state/log/file/file-policy-name
                leaf file-policy-name {
                    type types-log:file-policy-name;
                    description "File ID for a log or accounting file";
                }

                ///nokia-state/state/log/file/log-type
                leaf log-type {
                    type types-log:file-log-type;
                    description
                        "The value of log-type indicates the type of information
                         that will be written to this file.";
                }

                ///nokia-state/state/log/file/used-by
                leaf used-by {
                    status obsolete;
                    type int32 {
                        range "0..99";
                    }
                    description
                        "The value of log-id indicates the ID of the log or
                         accounting policy this file is attached to.

                         A value of zero (0)
                         indicates that this file definition is not currently used by any
                         log or accounting policy.";
                }

                ///nokia-state/state/log/file/creation-time
                leaf creation-time {
                    type yang:date-and-time;
                    description
                        "The value of creation-time is the time the currently opened
                         file version used by this file-id entry was created.

                         The value of creation-time is affected by the value of
                         stiPreferLocalTime.";
                }

                ///nokia-state/state/log/file/current-file-name
                leaf current-file-name {
                    type types-sros:named-item-255;
                    description
                        "The value of path-name is the path name of the currently
                         opened file used by this file-id entry.

                         The value of path-name is affected by the value of
                         stiPreferLocalTime.";
                }

                ///nokia-state/state/log/file/oper-location
                leaf oper-location {
                    type types-log:compact-flash-drive;
                    description "Specify the location for a log file.";
                }

                ///nokia-state/state/log/file/associated-files
                list associated-files {
                    key "file-name";
                    description "Enter the associated-files list instance";

                    ///nokia-state/state/log/file/associated-files/file-name
                    leaf file-name {
                        type string {
                            length "0..255";
                        }
                        description "The complete pathname of the file associated with the log ID.";
                    }

                    ///nokia-state/state/log/file/associated-files/expired
                    leaf expired {
                        type enumeration {
                            enum yes                            { value 1; }
                            enum no                             { value 2; }
                        }
                        description
                            "Indicates whether or not the retention period for this file has
                             passed.";
                    }

                    ///nokia-state/state/log/file/associated-files/state
                    leaf state {
                        type enumeration {
                            enum complete                       { value 1; }
                            enum in-progress                    { value 2; }
                        }
                        description "Indicates the current open or old log file.";
                    }

                } // list associated-files

            } // list file

            ///nokia-state/state/log/filter
            list filter {
                key "filter-name";
                description "Enter the filter list instance";

                ///nokia-state/state/log/filter/filter-name
                leaf filter-name {
                    type types-log:log-filter-name;
                    description "Filter name";
                }

                ///nokia-state/state/log/filter/applied
                leaf applied {
                    type boolean;
                    description
                        "If 'true', this filter is attached to a log file configuration.
                         The same entry can be attached to more than one log file.";
                }

            } // list filter

            ///nokia-state/state/log/log-id
            list log-id {
                key "name";
                description "Enter the log-id list instance";

                ///nokia-state/state/log/log-id/name
                leaf name {
                    type types-log:log-name;
                    description "Log ID";
                }

                ///nokia-state/state/log/log-id/oper-state
                leaf oper-state {
                    type types-sros:oper-state;
                    description "Operational state.";
                }

                ///nokia-state/state/log/log-id/wrapped
                leaf wrapped {
                    type boolean;
                    description "The sequence-number for this log has wrapped.";
                }

                ///nokia-state/state/log/log-id/next-event
                leaf next-event {
                    type yang:counter64;
                    description
                        "The sequence-number that will be used for the next log event
                         in this event log.";
                }

                ///nokia-state/state/log/log-id/statistics
                container statistics {
                    description "Enter the statistics context";

                    ///nokia-state/state/log/log-id/statistics/logged-events
                    leaf logged-events {
                        type yang:counter64;
                        description
                            "The value of the this object is the count of the number
                             of events that have been forwarded to this logs's destination.";
                    }

                    ///nokia-state/state/log/log-id/statistics/dropped-events
                    leaf dropped-events {
                        type yang:counter64;
                        description
                            "The value of the this object is the count of the number
                             of events that have been sent to this logs source(s) and
                             that have not been forwarded to the log destination because
                             they were filtered out by the log filter.";
                    }

                } // container statistics

                ///nokia-state/state/log/log-id/event
                list event {
                    key "sequence-number";
                    description "Enter the event list instance";

                    ///nokia-state/state/log/log-id/event/sequence-number
                    leaf sequence-number {
                        type uint64;
                        description
                            "A sequence number to indicate the ordering of log events in the log-id.
                             If the event is replayed, the sequence number is replayed as well.";
                    }

                    ///nokia-state/state/log/log-id/event/time
                    leaf time {
                        type yang:date-and-time;
                        description "Time when the event was generated.";
                    }

                    ///nokia-state/state/log/log-id/event/severity
                    leaf severity {
                        type types-log:severity-level;
                        description "The severity level of the log event.";
                    }

                    ///nokia-state/state/log/log-id/event/application
                    leaf application {
                        type types-log:application-state;
                        description "The name of the application that reports the log event.";
                    }

                    ///nokia-state/state/log/log-id/event/event-id
                    leaf event-id {
                        type uint32 {
                            range "1..max";
                        }
                        description
                            "The id the event that was generated.
                             Each log event type has a unique identifying number.  This number is
                             unique within a particular software application, such as IP, MPLS,
                             OSPF, etc. but it is not necessarily unique across different software
                             applications.  That is MPLS event #1001 may be different from OSPF
                             event #1001.";
                    }

                    ///nokia-state/state/log/log-id/event/event-name
                    leaf event-name {
                        type types-sros:named-item;
                        description "The name of the log event that was generated.";
                    }

                    ///nokia-state/state/log/log-id/event/vrtr-name
                    leaf vrtr-name {
                        type types-log:vrtr-name;
                        description "The router context name that generated the log event.";
                    }

                    ///nokia-state/state/log/log-id/event/subject
                    leaf subject {
                        type string {
                            length "0..32";
                        }
                        description
                            "The router context name that generated the log event.
                             The subject is the entity that originated the event, such as the Port ID.";
                    }

                    ///nokia-state/state/log/log-id/event/message
                    leaf message {
                        type string {
                            length "1..4100";
                        }
                        description "The log event message.";
                    }

                } // list event

            } // list log-id

            ///nokia-state/state/log/snmp-trap-group
            list snmp-trap-group {
                key "log-name";
                description "Enter the snmp-trap-group list instance";

                ///nokia-state/state/log/snmp-trap-group/log-name
                leaf log-name {
                    type types-log:snmp-trap-group-name;
                    description "Log ID";
                }

                ///nokia-state/state/log/snmp-trap-group/trap-target
                list trap-target {
                    key "name";
                    description "Enter the trap-target list instance";

                    ///nokia-state/state/log/snmp-trap-group/trap-target/name
                    leaf name {
                        type string {
                            length "1..28";
                        }
                        description "Trap target name";
                    }

                    ///nokia-state/state/log/snmp-trap-group/trap-target/replay-start-id
                    leaf replay-start-id {
                        type uint32;
                        description
                            "Indicates the SNMP notification request ID of the first event
                             that could not be generated because there is no route to this
                              notification target address.";
                    }

                    ///nokia-state/state/log/snmp-trap-group/trap-target/last-replay-time
                    leaf last-replay-time {
                        type yang:date-and-time;
                        description
                            "Indicates the time when missed events were last replayed
                             to this SNMP notification target address.";
                    }

                } // list trap-target

            } // list snmp-trap-group

            ///nokia-state/state/log/syslog
            list syslog {
                key "syslog-name";
                description "Enter the syslog list instance";

                ///nokia-state/state/log/syslog/syslog-name
                leaf syslog-name {
                    type types-log:log-syslog-name;
                    description "Syslog name";
                }

                ///nokia-state/state/log/syslog/below-severity-drops
                leaf below-severity-drops {
                    type yang:counter32;
                    description
                        "Identifies the count of messages not sent to this syslog collector
                         target because the severity level of the message was above the configured level.";
                }

            } // list syslog

            ///nokia-state/state/log/cli-log-subscriptions
            container cli-log-subscriptions {
                description "Enter the cli-log-subscriptions context";

                ///nokia-state/state/log/cli-log-subscriptions/cli-log-subscribed-session
                list cli-log-subscribed-session {
                    key "session-id";
                    description "Enter the cli-log-subscribed-session list instance";

                    ///nokia-state/state/log/cli-log-subscriptions/cli-log-subscribed-session/session-id
                    leaf session-id {
                        type uint32;
                        description "The id of the CLI session.";
                    }

                    ///nokia-state/state/log/cli-log-subscriptions/cli-log-subscribed-session/connection-type
                    leaf connection-type {
                        type enumeration {
                            enum telnet                         { value 1; }
                            enum console                        { value 2; }
                            enum ssh                            { value 4; }
                        }
                        description "The type of the connection used for the cli session.";
                    }

                    ///nokia-state/state/log/cli-log-subscriptions/cli-log-subscribed-session/connection-ip
                    leaf connection-ip {
                        type types-sros:ip-address;
                        description "The remote IP address of the connection used for the cli session.";
                    }

                    ///nokia-state/state/log/cli-log-subscriptions/cli-log-subscribed-session/user
                    leaf user {
                        type types-sros:named-item;
                        description "Name of the user.";
                    }

                    ///nokia-state/state/log/cli-log-subscriptions/cli-log-subscribed-session/login-time
                    leaf login-time {
                        type yang:date-and-time;
                        description "The time the user logged in and created the CLI session.";
                    }

                    ///nokia-state/state/log/cli-log-subscriptions/cli-log-subscribed-session/subscription
                    list subscription {
                        key "id";
                        description "Enter the subscription list instance";

                        ///nokia-state/state/log/cli-log-subscriptions/cli-log-subscribed-session/subscription/id
                        leaf id {
                            type int32 {
                                range "1..101";
                            }
                            description "The value of id uniquely identifies an event stream log.";
                        }

                    } // list subscription

                } // list cli-log-subscribed-session

            } // container cli-log-subscriptions

        } // container log

    } // grouping state-log

}
