submodule nokia-state-system-security-pki {

    yang-version "1.1";

    belongs-to nokia-state { prefix "state"; }

    import ietf-yang-types                { prefix "yang"; }
    import nokia-sros-yang-extensions     { prefix "sros-ext"; }
    import nokia-types-security           { prefix "types-security"; }
    import nokia-types-sros               { prefix "types-sros"; }

    sros-ext:sros-major-release "rel23";
    organization "Nokia";
    contact
        "Nokia SR OS Support
         Web: <http://www.nokia.com>";
    description
        "Nokia YANG Data model with operational state for system security pki parameters. on SR OS based routers.

         Copyright 2016 Nokia. All rights reserved. Reproduction of this document
         is authorized on the condition that the foregoing copyright notice is included.

         This nokia-state-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-12-07";

    grouping state-system-security-pki {
        ///nokia-state/state/system/security/pki
        container pki {
            description "Enter the pki context";

            ///nokia-state/state/system/security/pki/statistics
            container statistics {
                description "Enter the statistics context";

                ///nokia-state/state/system/security/pki/statistics/authentication
                container authentication {
                    description "Enter the authentication context";

                    ///nokia-state/state/system/security/pki/statistics/authentication/failed
                    leaf failed {
                        type yang:counter32;
                        description "The number of authentication failures using the certificates.";
                    }

                    ///nokia-state/state/system/security/pki/statistics/authentication/passed
                    leaf passed {
                        type yang:counter32;
                        description "The number of authentication checks passed using the certificates.";
                    }

                    ///nokia-state/state/system/security/pki/statistics/authentication/attempted
                    leaf attempted {
                        type yang:counter32;
                        description "The number of authentication attempts using the certificates.";
                    }

                } // container authentication

            } // container statistics

            ///nokia-state/state/system/security/pki/ca-profile
            list ca-profile {
                key "ca-profile-name";
                description "Enter the ca-profile list instance";

                ///nokia-state/state/system/security/pki/ca-profile/ca-profile-name
                leaf ca-profile-name {
                    type types-sros:named-item;
                    description "CA profile name";
                }

                ///nokia-state/state/system/security/pki/ca-profile/oper-state
                leaf oper-state {
                    type types-sros:oper-state;
                    description "Operational state of the CA profile.";
                }

                ///nokia-state/state/system/security/pki/ca-profile/oper-flags
                leaf oper-flags {
                    type bits {
                        bit adminDown                      { position 0; }
                        bit invalid-crl                    { position 1; }
                        bit invalid-cert                   { position 2; }
                        bit invalid-cmpv2-signing-cert     { position 3; }
                        bit expired-crl                    { position 4; }
                        bit expired-cert                   { position 5; }
                        bit expired-cmpv2-signing-cert     { position 6; }
                        bit not-yet-valid-crl              { position 7; }
                        bit not-yet-valid-cert             { position 8; }
                        bit not-yet-valid-cmpv2-signing-cert { position 9; }
                        bit loading-crl                    { position 10; }
                        bit loading-cert                   { position 11; }
                        bit loading-cmpv2-signing-cert     { position 12; }
                    }
                    description "Reason why the CA profile is not in service.";
                }

                ///nokia-state/state/system/security/pki/ca-profile/cmpv2
                container cmpv2 {
                    description "Enter the cmpv2 context";

                    ///nokia-state/state/system/security/pki/ca-profile/cmpv2/request
                    container request {
                        description "Enter the request context";

                        ///nokia-state/state/system/security/pki/ca-profile/cmpv2/request/request-start-time
                        leaf request-start-time {
                            type yang:date-and-time;
                            description "Time when request started";
                        }

                        ///nokia-state/state/system/security/pki/ca-profile/cmpv2/request/last-ca-response-time
                        leaf last-ca-response-time {
                            type yang:date-and-time;
                            description "Time when CA last response";
                        }

                        ///nokia-state/state/system/security/pki/ca-profile/cmpv2/request/transaction-status
                        leaf transaction-status {
                            type types-security:cmpv2-transaction-status;
                            description "CMPv2 transaction status";
                        }

                        ///nokia-state/state/system/security/pki/ca-profile/cmpv2/request/transaction-status-code
                        leaf transaction-status-code {
                            type types-security:cmpv2-transaction-status-code;
                            description "CMPv2 transaction status code";
                        }

                        ///nokia-state/state/system/security/pki/ca-profile/cmpv2/request/transaction-status-string
                        leaf transaction-status-string {
                            type string {
                                length "1..255";
                            }
                            description "CMPv2 transaction extra status info";
                        }

                        ///nokia-state/state/system/security/pki/ca-profile/cmpv2/request/request-parameters
                        container request-parameters {
                            description "Enter the request-parameters context";

                            ///nokia-state/state/system/security/pki/ca-profile/cmpv2/request/request-parameters/request-type
                            leaf request-type {
                                type types-security:cmpv2-request-type;
                                description "CMPv2 request type";
                            }

                            ///nokia-state/state/system/security/pki/ca-profile/cmpv2/request/request-parameters/key-filename
                            leaf key-filename {
                                type types-security:pki-file-name;
                                description "The name of the key file used in cmpv2 request";
                            }

                            ///nokia-state/state/system/security/pki/ca-profile/cmpv2/request/request-parameters/new-key-filename
                            leaf new-key-filename {
                                type types-security:pki-file-name;
                                description "The name of the new key file used in cmpv2 request";
                            }

                            ///nokia-state/state/system/security/pki/ca-profile/cmpv2/request/request-parameters/subject-dn
                            leaf subject-dn {
                                type string {
                                    length "1..256";
                                }
                                description "Subject of the requesting certificate";
                            }

                            ///nokia-state/state/system/security/pki/ca-profile/cmpv2/request/request-parameters/domain-name
                            leaf domain-name {
                                type string {
                                    length "1..512";
                                }
                                description "FQDNs for the Subject Alternative Name";
                            }

                            ///nokia-state/state/system/security/pki/ca-profile/cmpv2/request/request-parameters/ip-address
                            leaf ip-address {
                                type types-sros:ip-address;
                                description "IP address for the Subject Alternative Name";
                            }

                            ///nokia-state/state/system/security/pki/ca-profile/cmpv2/request/request-parameters/save-as
                            leaf save-as {
                                type types-sros:cflash-url;
                                description "Path to result certificate file";
                            }

                            ///nokia-state/state/system/security/pki/ca-profile/cmpv2/request/request-parameters/protection-algorithm
                            choice protection-algorithm {
                                ///nokia-state/state/system/security/pki/ca-profile/cmpv2/request/request-parameters/protection-algorithm/password
                                case password {

                                    ///nokia-state/state/system/security/pki/ca-profile/cmpv2/request/request-parameters/protection-algorithm/password/reference
                                    leaf reference {
                                        type string {
                                            length "1..64";
                                        }
                                        description "Password reference number";
                                    }

                                }
                                ///nokia-state/state/system/security/pki/ca-profile/cmpv2/request/request-parameters/protection-algorithm/signature
                                case signature {

                                    ///nokia-state/state/system/security/pki/ca-profile/cmpv2/request/request-parameters/protection-algorithm/signature/certificate
                                    leaf certificate {
                                        type types-security:pki-file-name;
                                        description "Filename of the certificate for protection key";
                                    }

                                    ///nokia-state/state/system/security/pki/ca-profile/cmpv2/request/request-parameters/protection-algorithm/signature/send-chain
                                    leaf send-chain {
                                        type boolean;
                                        description "Send certificate chain";
                                    }

                                    ///nokia-state/state/system/security/pki/ca-profile/cmpv2/request/request-parameters/protection-algorithm/signature/send-chain-ca
                                    leaf send-chain-ca {
                                        type string {
                                            length "1..32";
                                        }
                                        description "Name of the ca-profile whose certificate to be included in the chain";
                                    }

                                    ///nokia-state/state/system/security/pki/ca-profile/cmpv2/request/request-parameters/protection-algorithm/signature/protection-key
                                    leaf protection-key {
                                        type types-security:pki-file-name;
                                        description "Protection key filename";
                                    }

                                    ///nokia-state/state/system/security/pki/ca-profile/cmpv2/request/request-parameters/protection-algorithm/signature/hash-algorithm
                                    leaf hash-algorithm {
                                        type types-security:hash-algorithm;
                                        description "The hash algorithm used for certificate signature";
                                    }

                                }
                            }
                        } // container request-parameters

                    } // container request

                } // container cmpv2

                ///nokia-state/state/system/security/pki/ca-profile/auto-crl-update
                container auto-crl-update {
                    description "Enable the auto-crl-update context";

                    ///nokia-state/state/system/security/pki/ca-profile/auto-crl-update/last-success-auto-crl-update-url-id
                    leaf last-success-auto-crl-update-url-id {
                        type union {
                            type uint32 {
                                range "1..8";
                            }
                            type enumeration {
                                enum not-applicable                 { value 0; }
                            }
                        }
                        description "URL entry ID of the last successful automated CRL update.";
                    }

                    ///nokia-state/state/system/security/pki/ca-profile/auto-crl-update/last-success-auto-crl-update-time-start
                    leaf last-success-auto-crl-update-time-start {
                        type uint32;
                        units "seconds";
                        description
                            "Time at which the last successful automated CRL update
                             was initiated. It is measured from 1-Jan-1970 00:00:00 UTC.";
                    }

                    ///nokia-state/state/system/security/pki/ca-profile/auto-crl-update/last-success-auto-crl-update-time-end
                    leaf last-success-auto-crl-update-time-end {
                        type uint32;
                        units "seconds";
                        description
                            "Time at which the last successful automated CRL update
                             was finished. It is measured from 1-Jan-1970 00:00:00 UTC.";
                    }

                    ///nokia-state/state/system/security/pki/ca-profile/auto-crl-update/next-scheduled-auto-crl-update-time
                    leaf next-scheduled-auto-crl-update-time {
                        type uint32;
                        units "seconds";
                        description
                            "Start time of the next scheduled update. It is measured
                             from 1-Jan-1970 00:00:00 UTC.";
                    }

                    ///nokia-state/state/system/security/pki/ca-profile/auto-crl-update/current-crl-update
                    container current-crl-update {
                        description "Enter the current-crl-update context";

                        ///nokia-state/state/system/security/pki/ca-profile/auto-crl-update/current-crl-update/status
                        leaf status {
                            type types-security:crl-update-status;
                            description "The CRL update status.";
                        }

                        ///nokia-state/state/system/security/pki/ca-profile/auto-crl-update/current-crl-update/entry-id
                        leaf entry-id {
                            type uint32 {
                                range "1..8";
                            }
                            description "The url-entry which is being used in the current update for a CRL file.";
                        }

                        ///nokia-state/state/system/security/pki/ca-profile/auto-crl-update/current-crl-update/start-time
                        leaf start-time {
                            type yang:date-and-time;
                            description "The time at which the current automated CRL update was initiated.";
                        }

                        ///nokia-state/state/system/security/pki/ca-profile/auto-crl-update/current-crl-update/last-failed-update
                        container last-failed-update {
                            description "Enter the last-failed-update context";

                            ///nokia-state/state/system/security/pki/ca-profile/auto-crl-update/current-crl-update/last-failed-update/start-time
                            leaf start-time {
                                type yang:date-and-time;
                                description "The time at which the last failed automated CRL update was initiated.";
                            }

                            ///nokia-state/state/system/security/pki/ca-profile/auto-crl-update/current-crl-update/last-failed-update/end-time
                            leaf end-time {
                                type yang:date-and-time;
                                description "The time at which the last failed automated CRL update was finished.";
                            }

                            ///nokia-state/state/system/security/pki/ca-profile/auto-crl-update/current-crl-update/last-failed-update/entry-id
                            leaf entry-id {
                                type uint32 {
                                    range "1..8";
                                }
                                description "The url-entry of the last failed automated CRL update.";
                            }

                            ///nokia-state/state/system/security/pki/ca-profile/auto-crl-update/current-crl-update/last-failed-update/cause
                            leaf cause {
                                type enumeration {
                                    enum no-failure                     { value 0; }
                                    enum download-failed                { value 1; }
                                    enum invalid-crl                    { value 2; }
                                }
                                description
                                    "The reason of the recent failed automated CRL update.

                                     noFailure      (0) -- The system never fails to update the CRL file
                                     downloadFailed (1) -- The system failed to download the CRL file
                                     invalidCRL     (2) -- The verification of the downloaded CRL file failed.";
                            }

                        } // container last-failed-update

                    } // container current-crl-update

                } // container auto-crl-update

            } // list ca-profile



            ///nokia-state/state/system/security/pki/certificate-auto-update
            list certificate-auto-update {
                key "certificate-file-name";
                description "Enter the certificate-auto-update list instance";

                ///nokia-state/state/system/security/pki/certificate-auto-update/certificate-file-name
                leaf certificate-file-name {
                    type types-security:pki-file-name;
                    description "Certificate file name";
                }

                ///nokia-state/state/system/security/pki/certificate-auto-update/update-state
                leaf update-state {
                    type enumeration {
                        enum invalid                        { value 0; }
                        enum scheduled                      { value 1; }
                        enum in-progress                    { value 2; }
                        enum wait-for-retry                 { value 3; }
                    }
                    description "State of certificate update.";
                }

                ///nokia-state/state/system/security/pki/certificate-auto-update/last-update-start-time
                leaf last-update-start-time {
                    type yang:date-and-time;
                    description "Time when last update started";
                }

                ///nokia-state/state/system/security/pki/certificate-auto-update/last-update-end-time
                leaf last-update-end-time {
                    type yang:date-and-time;
                    description "Time when last update ended";
                }

                ///nokia-state/state/system/security/pki/certificate-auto-update/next-update-time
                leaf next-update-time {
                    type yang:date-and-time;
                    description "Time when last update ended";
                }

            } // list certificate-auto-update

        } // container pki

    } // grouping state-system-security-pki

}
