module nokia-oper-perform {

    yang-version "1.1";

    namespace "urn:nokia.com:sros:ns:yang:sr:oper-perform";

    prefix "oper-perform";

    import nokia-conf                     { prefix "conf"; }
    import nokia-sros-yang-extensions     { prefix "sros-ext"; }
    import nokia-state                    { prefix "state"; }
    import nokia-types-operation          { prefix "types-operation"; }
    import nokia-types-sros               { prefix "types-sros"; }

    sros-ext:sros-major-release "rel23";
    organization "Nokia";
    contact
        "Nokia SR OS Support
         Web: <http://www.nokia.com>";
    description
        "Nokia YANG Data model for perform on SR OS based routers.

         Copyright 2016 Nokia. All rights reserved. Reproduction of this document
         is authorized on the condition that the foregoing copyright notice is included.

         This nokia-oper-perform YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2016-01-01";

    container perform {
        config false;
        description "Perform troubleshooting and debugging";

        container lag {
            description "Perform LAG operations";

            container force-active {
                description "Perform LAG force-active operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container force-active

            container force-standby {
                description "Perform LAG force-standby operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container force-standby

            container clear-force {
                description "Perform LAG clear-force operation";

                container multi-chassis {
                    description "Enter the multi-chassis context";

                    action all {
                        description "Perform LAG operation on all multi-chassis LAGs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action peer {
                        description "Perform LAG operation on the MC peer";

                        input {

                            leaf ip-address {
                                type leafref {
                                    path "/state:state/state:redundancy/state:multi-chassis/state:peer/state:ip-address";
                                }
                                mandatory true;
                                description "Peer IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action peer

                } // container multi-chassis

                action lag {
                    description "Perform LAG operation on the specified LAG";

                    input {

                        leaf lag-name {
                            type leafref {
                                path "/state:state/state:lag/state:lag-name";
                            }
                            mandatory true;
                            description "LAG name";
                        }

                        leaf sub-group {
                            type uint32 {
                                range "1..16";
                            }
                            default "1";
                            description "Sub-group in the LAG";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action lag

            } // container clear-force

            action load-balance {
                description "Perform LAG load-balance operation";

                input {

                    leaf lag-name {
                        type leafref {
                            path "/state:state/state:lag/state:lag-name";
                        }
                        mandatory true;
                        description "LAG name";
                    }

                    leaf class {
                        type uint32 {
                            range "1..3";
                        }
                        default "1";
                        description "Class used for load balancing";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action load-balance

        } // container lag


        container system {
            description "Enter the system context";


            container security {
                description "Enter the security context";

                container secure-boot {
                    description "Enter the secure-boot context";

                    container show {
                        description "Enter the show context";

                        action uefi-variables {
                            description "Display secure-boot UEFI variables";

                            input {

                                leaf card {
                                    type leafref {
                                        path "/state:state/state:cpm/state:cpm-slot";
                                    }
                                    mandatory true;
                                    description "CPM slot where UEFI variables are returned";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf enabled {
                                    type boolean;
                                    description "Whether or not secure-boot is enabled on the CPM.";
                                }

                                container pk {
                                    description "Details of the system-wide pk certificate";

                                    leaf subject {
                                        type types-sros:very-long-description;
                                        description "The subject of the certificate";
                                    }

                                    leaf serial-number {
                                        type types-sros:description;
                                        description "The serial-number of the certificate";
                                    }

                                    leaf raw {
                                        type types-sros:very-long-description;
                                        description "The contents of the certificate";
                                    }

                                } // container pk

                                list kek {
                                    description "Details of a single kek certificate";

                                    leaf subject {
                                        type types-sros:very-long-description;
                                        description "The subject of the certificate";
                                    }

                                    leaf serial-number {
                                        type types-sros:description;
                                        description "The serial-number of the certificate";
                                    }

                                    leaf raw {
                                        type types-sros:very-long-description;
                                        description "The contents of the certificate";
                                    }

                                } // list kek

                                list db {
                                    description "Details of a single db certificate";

                                    container x509 {
                                        description "The x509 signature of the db certificate";

                                        leaf subject {
                                            type types-sros:very-long-description;
                                            description "The subject of the certificate";
                                        }

                                        leaf serial-number {
                                            type types-sros:description;
                                            description "The serial-number of the certificate";
                                        }

                                        leaf raw {
                                            type types-sros:very-long-description;
                                            description "The contents of the certificate";
                                        }

                                    } // container x509

                                } // list db

                                list dbx {
                                    description "Details of a single dbx certficate";

                                    choice signature {
                                        case sha256 {
                                            description "A sha256 signature of a dbx certificate";

                                            leaf value {
                                                type types-sros:very-long-description;
                                                description "The sha256 value for the certificate";
                                            }

                                        }
                                        case x509 {
                                            description "The x509 signature of the dbx certificate";

                                            leaf subject {
                                                type types-sros:very-long-description;
                                                description "The subject of the certificate";
                                            }

                                            leaf serial-number {
                                                type types-sros:description;
                                                description "The serial-number of the certificate";
                                            }

                                            leaf raw {
                                                type types-sros:very-long-description;
                                                description "The contents of the certificate";
                                            }

                                        }
                                    }
                                } // list dbx

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action uefi-variables

                    } // container show

                } // container secure-boot

            } // container security

        } // container system

        container filter {
            description "Enter the filter context";

            list ip-filter {
                key "filter-name";
                description "Enter the ip-filter list instance";

                leaf filter-name {
                    type leafref {
                        path "/state:state/state:filter/state:ip-filter/state:filter-name";
                    }
                    description "Name to associate with the IP filter";
                }

                list entry {
                    key "entry-id";
                    description "Enter the entry list instance";

                    leaf entry-id {
                        type leafref {
                            path "/state:state/state:filter/state:ip-filter[state:filter-name=current()/../../filter-name]/state:entry/state:entry-id";
                        }
                        description "ID for the IP filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list ip-filter

            list ipv6-filter {
                key "filter-name";
                description "Enter the ipv6-filter list instance";

                leaf filter-name {
                    type leafref {
                        path "/state:state/state:filter/state:ipv6-filter/state:filter-name";
                    }
                    description "Name to associate with the IPv6 filter";
                }

                list entry {
                    key "entry-id";
                    description "Enter the entry list instance";

                    leaf entry-id {
                        type leafref {
                            path "/state:state/state:filter/state:ipv6-filter[state:filter-name=current()/../../filter-name]/state:entry/state:entry-id";
                        }
                        description "ID for the IPv6 filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list ipv6-filter

            list mac-filter {
                key "filter-name";
                description "Enter the mac-filter list instance";

                leaf filter-name {
                    type leafref {
                        path "/state:state/state:filter/state:mac-filter/state:filter-name";
                    }
                    description "Name to associate with the MAC filter";
                }

                list entry {
                    key "entry-id";
                    description "Enter the entry list instance";

                    leaf entry-id {
                        type leafref {
                            path "/state:state/state:filter/state:mac-filter[state:filter-name=current()/../../filter-name]/state:entry/state:entry-id";
                        }
                        description "ID for the MAC filter entry";
                    }

                    action activate-primary-action {
                        description "Switch from the secondary to the primary action";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action activate-primary-action

                } // list entry

            } // list mac-filter

            list redirect-policy {
                key "redirect-policy-name";
                description "Enter the redirect-policy list instance";

                leaf redirect-policy-name {
                    type leafref {
                        path "/state:state/state:filter/state:redirect-policy/state:redirect-policy-name";
                    }
                    description "Name of the redirect policy";
                }

                action activate-best-dest {
                    description "Activate the current best destination";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action activate-best-dest

            } // list redirect-policy

        } // container filter


    } // container perform

}
