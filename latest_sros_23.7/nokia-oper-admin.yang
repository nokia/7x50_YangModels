module nokia-oper-admin {

    yang-version "1.1";

    namespace "urn:nokia.com:sros:ns:yang:sr:oper-admin";

    prefix "oper-admin";

    import ietf-yang-types                { prefix "yang"; }
    import nokia-conf                     { prefix "conf"; }
    import nokia-sros-yang-extensions     { prefix "sros-ext"; }
    import nokia-state                    { prefix "state"; }
    import nokia-types-chassis            { prefix "types-chassis"; }
    import nokia-types-operation          { prefix "types-operation"; }
    import nokia-types-security           { prefix "types-security"; }
    import nokia-types-sros               { prefix "types-sros"; }

    sros-ext:sros-major-release "rel23";
    organization "Nokia";
    contact
        "Nokia SR OS Support
         Web: <http://www.nokia.com>";
    description
        "Nokia YANG Data model for admin actions on SR OS based routers.

         Copyright 2016 Nokia. All rights reserved. Reproduction of this document
         is authorized on the condition that the foregoing copyright notice is included.

         This nokia-oper-admin YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2016-01-01";

    typedef configuration-region {
        type enumeration {
            enum configure                      { value 0; }
            enum li                             { value 1; }
        }
        default "configure";
        description "The configuration region specify region which is used";
    }

    typedef cli-path-type {
        type string;
        description "Path type used for path infrastructure";
    }

    ///admin
    container admin {
        config false;
        description "Enter the administrative context for system operations";

        ///admin/disconnect
        action disconnect {
            description "Disconnect a user session";

            input {

                ///admin/disconnect/input/op-table-bypass
                leaf op-table-bypass {
                    type types-operation:operation-op-table-bypass;
                    description "Avoid operation ID allocation";
                }

                ///admin/disconnect/input/address
                leaf address {
                    type types-sros:ip-address;
                    description "IP address of the session to disconnect";
                }

                ///admin/disconnect/input/session-id
                leaf session-id {
                    type uint32 {
                        range "1..4294967295";
                    }
                    description "ID of the session to disconnect";
                }

                ///admin/disconnect/input/session-type
                leaf session-type {
                    type enumeration {
                        enum console                        { value 1; }
                        enum bluetooth                      { value 2; }
                        enum telnet                         { value 3; }
                        enum ssh                            { value 4; }
                        enum ftp                            { value 5; }
                        enum netconf                        { value 6; }
                        enum grpc                           { value 7; }
                        enum cron-ehs                       { value 8; }
                    }
                    description "Type of session to disconnect";
                }

                ///admin/disconnect/input/username
                leaf username {
                    type types-sros:named-item;
                    description "Username to disconnect";
                }

            }
            output {

                ///admin/disconnect/output/operation-id
                leaf operation-id {
                    type types-operation:operation-id;
                    description "ID assigned to the operation.";
                }

                ///admin/disconnect/output/start-time
                leaf start-time {
                    type types-operation:operation-timestamp;
                    description "Time when the operation started its execution.";
                }

                ///admin/disconnect/output/results-path
                leaf results-path {
                    type types-operation:operation-path;
                    description "Path to the results of the operation formatted as xpath.";
                }

                ///admin/disconnect/output/status
                leaf status {
                    type types-operation:operation-status;
                    description "Status of the operation";
                }

                ///admin/disconnect/output/error-message
                leaf-list error-message {
                    type types-operation:operation-message;
                    description "Error messages reported during execution of the operation.";
                }

                ///admin/disconnect/output/warning-message
                leaf-list warning-message {
                    type types-operation:operation-message;
                    description "Warning messages reported during execution of the operation.";
                }

                ///admin/disconnect/output/info-message
                leaf-list info-message {
                    type types-operation:operation-message;
                    description "Info messages reported during execution of the operation.";
                }

                ///admin/disconnect/output/end-time
                leaf end-time {
                    type types-operation:operation-timestamp;
                    description "Time when the operation ended its execution.";
                }

            }
        } // action disconnect

        ///admin/reboot
        action reboot {
            description "Reboot CPM or force an upgrade of system boot ROMs";

            input {

                ///admin/reboot/input/now
                leaf now {
                    type empty;
                    description "Reboot immediately without prompts or confirmation";
                }

                ///admin/reboot/input/card
                leaf card {
                    type enumeration {
                        enum active                         { value 1; }
                        enum standby                        { value 2; }
                        enum upgrade                        { value 3; }
                    }
                    description "Card to reboot";
                }

                ///admin/reboot/input/hold
                leaf hold {
                    type empty;
                    description "Hold a rebooted standby CPM from coming back online";
                }

            }
            output {

                ///admin/reboot/output/operation-id
                leaf operation-id {
                    type types-operation:operation-id;
                    description "ID assigned to the operation.";
                }

                ///admin/reboot/output/start-time
                leaf start-time {
                    type types-operation:operation-timestamp;
                    description "Time when the operation started its execution.";
                }

                ///admin/reboot/output/results-path
                leaf results-path {
                    type types-operation:operation-path;
                    description "Path to the results of the operation formatted as xpath.";
                }

                ///admin/reboot/output/status
                leaf status {
                    type types-operation:operation-status;
                    description "Status of the operation";
                }

                ///admin/reboot/output/error-message
                leaf-list error-message {
                    type types-operation:operation-message;
                    description "Error messages reported during execution of the operation.";
                }

                ///admin/reboot/output/warning-message
                leaf-list warning-message {
                    type types-operation:operation-message;
                    description "Warning messages reported during execution of the operation.";
                }

                ///admin/reboot/output/info-message
                leaf-list info-message {
                    type types-operation:operation-message;
                    description "Info messages reported during execution of the operation.";
                }

                ///admin/reboot/output/end-time
                leaf end-time {
                    type types-operation:operation-timestamp;
                    description "Time when the operation ended its execution.";
                }

            }
        } // action reboot

        ///admin/application-assurance
        container application-assurance {
            description "Enter the application-assurance context";

            ///admin/application-assurance/upgrade
            action upgrade {
                description "Upgrade to a new isa-aa.tim file";

                output {

                    ///admin/application-assurance/upgrade/output/operation-id
                    leaf operation-id {
                        type types-operation:operation-id;
                        description "ID assigned to the operation.";
                    }

                    ///admin/application-assurance/upgrade/output/start-time
                    leaf start-time {
                        type types-operation:operation-timestamp;
                        description "Time when the operation started its execution.";
                    }

                    ///admin/application-assurance/upgrade/output/results-path
                    leaf results-path {
                        type types-operation:operation-path;
                        description "Path to the results of the operation formatted as xpath.";
                    }

                    ///admin/application-assurance/upgrade/output/status
                    leaf status {
                        type types-operation:operation-status;
                        description "Status of the operation";
                    }

                    ///admin/application-assurance/upgrade/output/error-message
                    leaf-list error-message {
                        type types-operation:operation-message;
                        description "Error messages reported during execution of the operation.";
                    }

                    ///admin/application-assurance/upgrade/output/warning-message
                    leaf-list warning-message {
                        type types-operation:operation-message;
                        description "Warning messages reported during execution of the operation.";
                    }

                    ///admin/application-assurance/upgrade/output/info-message
                    leaf-list info-message {
                        type types-operation:operation-message;
                        description "Info messages reported during execution of the operation.";
                    }

                    ///admin/application-assurance/upgrade/output/end-time
                    leaf end-time {
                        type types-operation:operation-timestamp;
                        description "Time when the operation ended its execution.";
                    }

                }
            } // action upgrade

            ///admin/application-assurance/group
            list group {
                key "aa-group-id";
                description "Enter the group list instance";

                ///admin/application-assurance/group/aa-group-id
                leaf aa-group-id {
                    type leafref {
                        path "/state:state/state:application-assurance/state:group/state:aa-group-id";
                    }
                    description "AA group ID";
                }

                ///admin/application-assurance/group/url-list
                list url-list {
                    key "url-list-name";
                    description "Enter the url-list list instance";

                    ///admin/application-assurance/group/url-list/url-list-name
                    leaf url-list-name {
                        type leafref {
                            path "/state:state/state:application-assurance/state:group[state:aa-group-id=current()/../../aa-group-id]/state:url-list/state:url-list-name";
                        }
                        description "AA URL list name";
                    }

                    ///admin/application-assurance/group/url-list/upgrade
                    action upgrade {
                        description "Upgrade the referenced URL list";

                        output {

                            ///admin/application-assurance/group/url-list/upgrade/output/operation-id
                            leaf operation-id {
                                type types-operation:operation-id;
                                description "ID assigned to the operation.";
                            }

                            ///admin/application-assurance/group/url-list/upgrade/output/start-time
                            leaf start-time {
                                type types-operation:operation-timestamp;
                                description "Time when the operation started its execution.";
                            }

                            ///admin/application-assurance/group/url-list/upgrade/output/results-path
                            leaf results-path {
                                type types-operation:operation-path;
                                description "Path to the results of the operation formatted as xpath.";
                            }

                            ///admin/application-assurance/group/url-list/upgrade/output/status
                            leaf status {
                                type types-operation:operation-status;
                                description "Status of the operation";
                            }

                            ///admin/application-assurance/group/url-list/upgrade/output/error-message
                            leaf-list error-message {
                                type types-operation:operation-message;
                                description "Error messages reported during execution of the operation.";
                            }

                            ///admin/application-assurance/group/url-list/upgrade/output/warning-message
                            leaf-list warning-message {
                                type types-operation:operation-message;
                                description "Warning messages reported during execution of the operation.";
                            }

                            ///admin/application-assurance/group/url-list/upgrade/output/info-message
                            leaf-list info-message {
                                type types-operation:operation-message;
                                description "Info messages reported during execution of the operation.";
                            }

                            ///admin/application-assurance/group/url-list/upgrade/output/end-time
                            leaf end-time {
                                type types-operation:operation-timestamp;
                                description "Time when the operation ended its execution.";
                            }

                        }
                    } // action upgrade

                } // list url-list

            } // list group

        } // container application-assurance

        ///admin/clear
        container clear {
            description "Enter the clear context";

            ///admin/clear/security
            container security {
                description "Enter the security context";

                ///admin/clear/security/lockout
                action lockout {
                    description "Reset the lockout timer";

                    input {

                        ///admin/clear/security/lockout/input/lockout-options
                        choice lockout-options {
                            mandatory true;
                            ///admin/clear/security/lockout/input/lockout-options/user-name
                            case user-name {

                                ///admin/clear/security/lockout/input/lockout-options/user-name/user
                                leaf user {
                                    type types-sros:named-item;
                                    description "User to be cleared of lockout";
                                }

                            }
                            ///admin/clear/security/lockout/input/lockout-options/all
                            case all {

                                ///admin/clear/security/lockout/input/lockout-options/all/all
                                leaf all {
                                    type empty;
                                    description "Clear lockout of all users";
                                }

                            }
                        }
                    }
                    output {

                        ///admin/clear/security/lockout/output/operation-id
                        leaf operation-id {
                            type types-operation:operation-id;
                            description "ID assigned to the operation.";
                        }

                        ///admin/clear/security/lockout/output/start-time
                        leaf start-time {
                            type types-operation:operation-timestamp;
                            description "Time when the operation started its execution.";
                        }

                        ///admin/clear/security/lockout/output/results-path
                        leaf results-path {
                            type types-operation:operation-path;
                            description "Path to the results of the operation formatted as xpath.";
                        }

                        ///admin/clear/security/lockout/output/status
                        leaf status {
                            type types-operation:operation-status;
                            description "Status of the operation";
                        }

                        ///admin/clear/security/lockout/output/error-message
                        leaf-list error-message {
                            type types-operation:operation-message;
                            description "Error messages reported during execution of the operation.";
                        }

                        ///admin/clear/security/lockout/output/warning-message
                        leaf-list warning-message {
                            type types-operation:operation-message;
                            description "Warning messages reported during execution of the operation.";
                        }

                        ///admin/clear/security/lockout/output/info-message
                        leaf-list info-message {
                            type types-operation:operation-message;
                            description "Info messages reported during execution of the operation.";
                        }

                        ///admin/clear/security/lockout/output/end-time
                        leaf end-time {
                            type types-operation:operation-timestamp;
                            description "Time when the operation ended its execution.";
                        }

                    }
                } // action lockout

                ///admin/clear/security/password-history
                action password-history {
                    description "Clear the password history";

                    input {

                        ///admin/clear/security/password-history/input/password-history-options
                        choice password-history-options {
                            mandatory true;
                            ///admin/clear/security/password-history/input/password-history-options/user-name
                            case user-name {

                                ///admin/clear/security/password-history/input/password-history-options/user-name/user
                                leaf user {
                                    type types-sros:named-item;
                                    description "User to be cleared of password history information";
                                }

                            }
                            ///admin/clear/security/password-history/input/password-history-options/all
                            case all {

                                ///admin/clear/security/password-history/input/password-history-options/all/all
                                leaf all {
                                    type empty;
                                    description "Clear password history of all users";
                                }

                            }
                        }
                    }
                    output {

                        ///admin/clear/security/password-history/output/operation-id
                        leaf operation-id {
                            type types-operation:operation-id;
                            description "ID assigned to the operation.";
                        }

                        ///admin/clear/security/password-history/output/start-time
                        leaf start-time {
                            type types-operation:operation-timestamp;
                            description "Time when the operation started its execution.";
                        }

                        ///admin/clear/security/password-history/output/results-path
                        leaf results-path {
                            type types-operation:operation-path;
                            description "Path to the results of the operation formatted as xpath.";
                        }

                        ///admin/clear/security/password-history/output/status
                        leaf status {
                            type types-operation:operation-status;
                            description "Status of the operation";
                        }

                        ///admin/clear/security/password-history/output/error-message
                        leaf-list error-message {
                            type types-operation:operation-message;
                            description "Error messages reported during execution of the operation.";
                        }

                        ///admin/clear/security/password-history/output/warning-message
                        leaf-list warning-message {
                            type types-operation:operation-message;
                            description "Warning messages reported during execution of the operation.";
                        }

                        ///admin/clear/security/password-history/output/info-message
                        leaf-list info-message {
                            type types-operation:operation-message;
                            description "Info messages reported during execution of the operation.";
                        }

                        ///admin/clear/security/password-history/output/end-time
                        leaf end-time {
                            type types-operation:operation-timestamp;
                            description "Time when the operation ended its execution.";
                        }

                    }
                } // action password-history

            } // container security

        } // container clear

        ///admin/nat
        container nat {
            description "Enter the nat context";

            ///admin/nat/save-deterministic-script
            action save-deterministic-script {
                description "Save script that computes deterministic NAT map entries";

                output {

                    ///admin/nat/save-deterministic-script/output/operation-id
                    leaf operation-id {
                        type types-operation:operation-id;
                        description "ID assigned to the operation.";
                    }

                    ///admin/nat/save-deterministic-script/output/start-time
                    leaf start-time {
                        type types-operation:operation-timestamp;
                        description "Time when the operation started its execution.";
                    }

                    ///admin/nat/save-deterministic-script/output/results-path
                    leaf results-path {
                        type types-operation:operation-path;
                        description "Path to the results of the operation formatted as xpath.";
                    }

                    ///admin/nat/save-deterministic-script/output/status
                    leaf status {
                        type types-operation:operation-status;
                        description "Status of the operation";
                    }

                    ///admin/nat/save-deterministic-script/output/error-message
                    leaf-list error-message {
                        type types-operation:operation-message;
                        description "Error messages reported during execution of the operation.";
                    }

                    ///admin/nat/save-deterministic-script/output/warning-message
                    leaf-list warning-message {
                        type types-operation:operation-message;
                        description "Warning messages reported during execution of the operation.";
                    }

                    ///admin/nat/save-deterministic-script/output/info-message
                    leaf-list info-message {
                        type types-operation:operation-message;
                        description "Info messages reported during execution of the operation.";
                    }

                    ///admin/nat/save-deterministic-script/output/end-time
                    leaf end-time {
                        type types-operation:operation-timestamp;
                        description "Time when the operation ended its execution.";
                    }

                }
            } // action save-deterministic-script

        } // container nat

        ///admin/redundancy
        container redundancy {
            description "Enter the redundancy context";

            ///admin/redundancy/force-switchover
            action force-switchover {
                description "Force a switchover to the standby CPM";

                input {

                    ///admin/redundancy/force-switchover/input/now
                    leaf now {
                        type empty;
                        description "Force the switchover to the standby CPM immediately";
                    }

                    ///admin/redundancy/force-switchover/input/ignore-status
                    leaf ignore-status {
                        type empty;
                        description "Switch to the standby CPM regardless of its status";
                    }

                }
                output {

                    ///admin/redundancy/force-switchover/output/operation-id
                    leaf operation-id {
                        type types-operation:operation-id;
                        description "ID assigned to the operation.";
                    }

                    ///admin/redundancy/force-switchover/output/start-time
                    leaf start-time {
                        type types-operation:operation-timestamp;
                        description "Time when the operation started its execution.";
                    }

                    ///admin/redundancy/force-switchover/output/results-path
                    leaf results-path {
                        type types-operation:operation-path;
                        description "Path to the results of the operation formatted as xpath.";
                    }

                    ///admin/redundancy/force-switchover/output/status
                    leaf status {
                        type types-operation:operation-status;
                        description "Status of the operation";
                    }

                    ///admin/redundancy/force-switchover/output/error-message
                    leaf-list error-message {
                        type types-operation:operation-message;
                        description "Error messages reported during execution of the operation.";
                    }

                    ///admin/redundancy/force-switchover/output/warning-message
                    leaf-list warning-message {
                        type types-operation:operation-message;
                        description "Warning messages reported during execution of the operation.";
                    }

                    ///admin/redundancy/force-switchover/output/info-message
                    leaf-list info-message {
                        type types-operation:operation-message;
                        description "Info messages reported during execution of the operation.";
                    }

                    ///admin/redundancy/force-switchover/output/end-time
                    leaf end-time {
                        type types-operation:operation-timestamp;
                        description "Time when the operation ended its execution.";
                    }

                }
            } // action force-switchover

            ///admin/redundancy/synchronize
            action synchronize {
                description "Synchronize the standby CPM";

                input {

                    ///admin/redundancy/synchronize/input/synchronize
                    choice synchronize {
                        mandatory true;
                        ///admin/redundancy/synchronize/input/synchronize/boot-environment
                        case boot-environment {

                            ///admin/redundancy/synchronize/input/synchronize/boot-environment/boot-environment
                            leaf boot-environment {
                                type empty;
                                description "Synchronize all files required for the boot process";
                            }

                        }
                        ///admin/redundancy/synchronize/input/synchronize/configuration
                        case configuration {

                            ///admin/redundancy/synchronize/input/synchronize/configuration/configuration
                            leaf configuration {
                                type empty;
                                description "Synchronize the configuration files";
                            }

                        }
                        ///admin/redundancy/synchronize/input/synchronize/certificate
                        case certificate {

                            ///admin/redundancy/synchronize/input/synchronize/certificate/certificate
                            leaf certificate {
                                type empty;
                                description "Synchronize imported certificate, key, and CRL files";
                            }

                        }
                    }
                }
                output {

                    ///admin/redundancy/synchronize/output/operation-id
                    leaf operation-id {
                        type types-operation:operation-id;
                        description "ID assigned to the operation.";
                    }

                    ///admin/redundancy/synchronize/output/start-time
                    leaf start-time {
                        type types-operation:operation-timestamp;
                        description "Time when the operation started its execution.";
                    }

                    ///admin/redundancy/synchronize/output/results-path
                    leaf results-path {
                        type types-operation:operation-path;
                        description "Path to the results of the operation formatted as xpath.";
                    }

                    ///admin/redundancy/synchronize/output/status
                    leaf status {
                        type types-operation:operation-status;
                        description "Status of the operation";
                    }

                    ///admin/redundancy/synchronize/output/error-message
                    leaf-list error-message {
                        type types-operation:operation-message;
                        description "Error messages reported during execution of the operation.";
                    }

                    ///admin/redundancy/synchronize/output/warning-message
                    leaf-list warning-message {
                        type types-operation:operation-message;
                        description "Warning messages reported during execution of the operation.";
                    }

                    ///admin/redundancy/synchronize/output/info-message
                    leaf-list info-message {
                        type types-operation:operation-message;
                        description "Info messages reported during execution of the operation.";
                    }

                    ///admin/redundancy/synchronize/output/end-time
                    leaf end-time {
                        type types-operation:operation-timestamp;
                        description "Time when the operation ended its execution.";
                    }

                }
            } // action synchronize

        } // container redundancy

        ///admin/satellite
        container satellite {
            description "Perform administrative operations for satellites";

            ///admin/satellite/ethernet-satellite
            list ethernet-satellite {
                key "satellite-id";
                description "Enter the ethernet-satellite list instance";

                ///admin/satellite/ethernet-satellite/satellite-id
                leaf satellite-id {
                    type leafref {
                        path "/state:state/state:satellite/state:ethernet-satellite/state:satellite-id";
                    }
                    description "Satellite ID";
                }

                ///admin/satellite/ethernet-satellite/reboot
                action reboot {
                    description "Initiate an administrative reboot of the chassis";

                    input {

                        ///admin/satellite/ethernet-satellite/reboot/input/now
                        leaf now {
                            type empty;
                            description "Reboot immediately without prompts or confirmation";
                        }

                        ///admin/satellite/ethernet-satellite/reboot/input/upgrade
                        leaf upgrade {
                            type empty;
                            description "Initiate a firmware image update during the reboot";
                        }

                    }
                    output {

                        ///admin/satellite/ethernet-satellite/reboot/output/operation-id
                        leaf operation-id {
                            type types-operation:operation-id;
                            description "ID assigned to the operation.";
                        }

                        ///admin/satellite/ethernet-satellite/reboot/output/start-time
                        leaf start-time {
                            type types-operation:operation-timestamp;
                            description "Time when the operation started its execution.";
                        }

                        ///admin/satellite/ethernet-satellite/reboot/output/results-path
                        leaf results-path {
                            type types-operation:operation-path;
                            description "Path to the results of the operation formatted as xpath.";
                        }

                        ///admin/satellite/ethernet-satellite/reboot/output/status
                        leaf status {
                            type types-operation:operation-status;
                            description "Status of the operation";
                        }

                        ///admin/satellite/ethernet-satellite/reboot/output/error-message
                        leaf-list error-message {
                            type types-operation:operation-message;
                            description "Error messages reported during execution of the operation.";
                        }

                        ///admin/satellite/ethernet-satellite/reboot/output/warning-message
                        leaf-list warning-message {
                            type types-operation:operation-message;
                            description "Warning messages reported during execution of the operation.";
                        }

                        ///admin/satellite/ethernet-satellite/reboot/output/info-message
                        leaf-list info-message {
                            type types-operation:operation-message;
                            description "Info messages reported during execution of the operation.";
                        }

                        ///admin/satellite/ethernet-satellite/reboot/output/end-time
                        leaf end-time {
                            type types-operation:operation-timestamp;
                            description "Time when the operation ended its execution.";
                        }

                    }
                } // action reboot

                ///admin/satellite/ethernet-satellite/synchronize
                action synchronize {
                    description "Synchronize the chassis to the boot image";

                    output {

                        ///admin/satellite/ethernet-satellite/synchronize/output/operation-id
                        leaf operation-id {
                            type types-operation:operation-id;
                            description "ID assigned to the operation.";
                        }

                        ///admin/satellite/ethernet-satellite/synchronize/output/start-time
                        leaf start-time {
                            type types-operation:operation-timestamp;
                            description "Time when the operation started its execution.";
                        }

                        ///admin/satellite/ethernet-satellite/synchronize/output/results-path
                        leaf results-path {
                            type types-operation:operation-path;
                            description "Path to the results of the operation formatted as xpath.";
                        }

                        ///admin/satellite/ethernet-satellite/synchronize/output/status
                        leaf status {
                            type types-operation:operation-status;
                            description "Status of the operation";
                        }

                        ///admin/satellite/ethernet-satellite/synchronize/output/error-message
                        leaf-list error-message {
                            type types-operation:operation-message;
                            description "Error messages reported during execution of the operation.";
                        }

                        ///admin/satellite/ethernet-satellite/synchronize/output/warning-message
                        leaf-list warning-message {
                            type types-operation:operation-message;
                            description "Warning messages reported during execution of the operation.";
                        }

                        ///admin/satellite/ethernet-satellite/synchronize/output/info-message
                        leaf-list info-message {
                            type types-operation:operation-message;
                            description "Info messages reported during execution of the operation.";
                        }

                        ///admin/satellite/ethernet-satellite/synchronize/output/end-time
                        leaf end-time {
                            type types-operation:operation-timestamp;
                            description "Time when the operation ended its execution.";
                        }

                    }
                } // action synchronize

            } // list ethernet-satellite


        } // container satellite

        ///admin/set
        container set {
            description "Enter the set context";

            ///admin/set/time
            action time {
                description "System date and time";

                input {

                    ///admin/set/time/input/system-time
                    leaf system-time {
                        type yang:date-and-time;
                        mandatory true;
                        description "System date and time";
                    }

                }
                output {

                    ///admin/set/time/output/operation-id
                    leaf operation-id {
                        type types-operation:operation-id;
                        description "ID assigned to the operation.";
                    }

                    ///admin/set/time/output/start-time
                    leaf start-time {
                        type types-operation:operation-timestamp;
                        description "Time when the operation started its execution.";
                    }

                    ///admin/set/time/output/results-path
                    leaf results-path {
                        type types-operation:operation-path;
                        description "Path to the results of the operation formatted as xpath.";
                    }

                    ///admin/set/time/output/status
                    leaf status {
                        type types-operation:operation-status;
                        description "Status of the operation";
                    }

                    ///admin/set/time/output/error-message
                    leaf-list error-message {
                        type types-operation:operation-message;
                        description "Error messages reported during execution of the operation.";
                    }

                    ///admin/set/time/output/warning-message
                    leaf-list warning-message {
                        type types-operation:operation-message;
                        description "Warning messages reported during execution of the operation.";
                    }

                    ///admin/set/time/output/info-message
                    leaf-list info-message {
                        type types-operation:operation-message;
                        description "Info messages reported during execution of the operation.";
                    }

                    ///admin/set/time/output/end-time
                    leaf end-time {
                        type types-operation:operation-timestamp;
                        description "Time when the operation ended its execution.";
                    }

                }
            } // action time

        } // container set

        ///admin/system
        container system {
            description "Enter the system context";

            ///admin/system/security
            container security {
                description "Enter the security context";

                ///admin/system/security/hash-control
                container hash-control {
                    description "Enter the hash-control context";

                    ///admin/system/security/hash-control/custom-hash
                    action custom-hash {
                        description "Custom encryption";

                        input {

                            ///admin/system/security/hash-control/custom-hash/input/algorithm
                            leaf algorithm {
                                type enumeration {
                                    enum 3des {
                                        value 0;
                                        description "DES-EDE3-ECB with PKCS #5 padding";
                                    }
                                    enum aes128 {
                                        value 1;
                                        description "AES-128-ECB with PKCS #7 padding";
                                    }
                                    enum aes192 {
                                        value 2;
                                        description "AES-192-ECB with PKCS #7 padding";
                                    }
                                    enum aes256 {
                                        value 3;
                                        description "AES-256-ECB with PKCS #7 padding";
                                    }
                                }
                                mandatory true;
                                description "Algorithm for custom encryption";
                            }

                            ///admin/system/security/hash-control/custom-hash/input/key
                            leaf key {
                                type string {
                                    length "1..71";
                                }
                                mandatory true;
                                description "Key for encryption algorithm";
                            }

                        }
                        output {

                            ///admin/system/security/hash-control/custom-hash/output/operation-id
                            leaf operation-id {
                                type types-operation:operation-id;
                                description "ID assigned to the operation.";
                            }

                            ///admin/system/security/hash-control/custom-hash/output/start-time
                            leaf start-time {
                                type types-operation:operation-timestamp;
                                description "Time when the operation started its execution.";
                            }

                            ///admin/system/security/hash-control/custom-hash/output/results-path
                            leaf results-path {
                                type types-operation:operation-path;
                                description "Path to the results of the operation formatted as xpath.";
                            }

                            ///admin/system/security/hash-control/custom-hash/output/status
                            leaf status {
                                type types-operation:operation-status;
                                description "Status of the operation";
                            }

                            ///admin/system/security/hash-control/custom-hash/output/error-message
                            leaf-list error-message {
                                type types-operation:operation-message;
                                description "Error messages reported during execution of the operation.";
                            }

                            ///admin/system/security/hash-control/custom-hash/output/warning-message
                            leaf-list warning-message {
                                type types-operation:operation-message;
                                description "Warning messages reported during execution of the operation.";
                            }

                            ///admin/system/security/hash-control/custom-hash/output/info-message
                            leaf-list info-message {
                                type types-operation:operation-message;
                                description "Info messages reported during execution of the operation.";
                            }

                            ///admin/system/security/hash-control/custom-hash/output/end-time
                            leaf end-time {
                                type types-operation:operation-timestamp;
                                description "Time when the operation ended its execution.";
                            }

                        }
                    } // action custom-hash

                    ///admin/system/security/hash-control/remove-custom-hash
                    action remove-custom-hash {
                        description "Remove the custom encryption";

                        output {

                            ///admin/system/security/hash-control/remove-custom-hash/output/operation-id
                            leaf operation-id {
                                type types-operation:operation-id;
                                description "ID assigned to the operation.";
                            }

                            ///admin/system/security/hash-control/remove-custom-hash/output/start-time
                            leaf start-time {
                                type types-operation:operation-timestamp;
                                description "Time when the operation started its execution.";
                            }

                            ///admin/system/security/hash-control/remove-custom-hash/output/results-path
                            leaf results-path {
                                type types-operation:operation-path;
                                description "Path to the results of the operation formatted as xpath.";
                            }

                            ///admin/system/security/hash-control/remove-custom-hash/output/status
                            leaf status {
                                type types-operation:operation-status;
                                description "Status of the operation";
                            }

                            ///admin/system/security/hash-control/remove-custom-hash/output/error-message
                            leaf-list error-message {
                                type types-operation:operation-message;
                                description "Error messages reported during execution of the operation.";
                            }

                            ///admin/system/security/hash-control/remove-custom-hash/output/warning-message
                            leaf-list warning-message {
                                type types-operation:operation-message;
                                description "Warning messages reported during execution of the operation.";
                            }

                            ///admin/system/security/hash-control/remove-custom-hash/output/info-message
                            leaf-list info-message {
                                type types-operation:operation-message;
                                description "Info messages reported during execution of the operation.";
                            }

                            ///admin/system/security/hash-control/remove-custom-hash/output/end-time
                            leaf end-time {
                                type types-operation:operation-timestamp;
                                description "Time when the operation ended its execution.";
                            }

                        }
                    } // action remove-custom-hash

                } // container hash-control

                ///admin/system/security/secure-boot
                container secure-boot {
                    description "Enter the secure-boot context";

                    ///admin/system/security/secure-boot/activate
                    action activate {
                        description "Activate secure boot on a CPM";

                        input {

                            ///admin/system/security/secure-boot/activate/input/card
                            leaf card {
                                type leafref {
                                    path "/state:state/state:cpm/state:cpm-slot";
                                }
                                mandatory true;
                                description "CPM slot where secure boot is activated or modified";
                            }

                            ///admin/system/security/secure-boot/activate/input/confirmation-code
                            leaf confirmation-code {
                                type types-sros:string-not-all-spaces {
                                    length "1..32";
                                }
                                description "Confirmation code";
                            }

                            ///admin/system/security/secure-boot/activate/input/now
                            leaf now {
                                type empty;
                                description "Perform the action immediately";
                            }

                            ///admin/system/security/secure-boot/activate/input/serial-number
                            leaf serial-number {
                                type types-sros:string-not-all-spaces {
                                    length "1..32";
                                }
                                description "CPM card serial number which secure-boot activates";
                            }

                        }
                        output {

                            ///admin/system/security/secure-boot/activate/output/operation-id
                            leaf operation-id {
                                type types-operation:operation-id;
                                description "ID assigned to the operation.";
                            }

                            ///admin/system/security/secure-boot/activate/output/start-time
                            leaf start-time {
                                type types-operation:operation-timestamp;
                                description "Time when the operation started its execution.";
                            }

                            ///admin/system/security/secure-boot/activate/output/results-path
                            leaf results-path {
                                type types-operation:operation-path;
                                description "Path to the results of the operation formatted as xpath.";
                            }

                            ///admin/system/security/secure-boot/activate/output/status
                            leaf status {
                                type types-operation:operation-status;
                                description "Status of the operation";
                            }

                            ///admin/system/security/secure-boot/activate/output/error-message
                            leaf-list error-message {
                                type types-operation:operation-message;
                                description "Error messages reported during execution of the operation.";
                            }

                            ///admin/system/security/secure-boot/activate/output/warning-message
                            leaf-list warning-message {
                                type types-operation:operation-message;
                                description "Warning messages reported during execution of the operation.";
                            }

                            ///admin/system/security/secure-boot/activate/output/info-message
                            leaf-list info-message {
                                type types-operation:operation-message;
                                description "Info messages reported during execution of the operation.";
                            }

                            ///admin/system/security/secure-boot/activate/output/end-time
                            leaf end-time {
                                type types-operation:operation-timestamp;
                                description "Time when the operation ended its execution.";
                            }

                        }
                    } // action activate

                    ///admin/system/security/secure-boot/revoke-key
                    action revoke-key {
                        description "Revoke secure boot keys";

                        input {

                            ///admin/system/security/secure-boot/revoke-key/input/card
                            leaf card {
                                type leafref {
                                    path "/state:state/state:cpm/state:cpm-slot";
                                }
                                mandatory true;
                                description "CPM slot where secure boot is activated or modified";
                            }

                            ///admin/system/security/secure-boot/revoke-key/input/confirmation-code
                            leaf confirmation-code {
                                type types-sros:string-not-all-spaces {
                                    length "1..32";
                                }
                                description "Confirmation code";
                            }

                            ///admin/system/security/secure-boot/revoke-key/input/now
                            leaf now {
                                type empty;
                                description "Perform the action immediately";
                            }

                            ///admin/system/security/secure-boot/revoke-key/input/serial-number
                            leaf serial-number {
                                type types-sros:string-not-all-spaces {
                                    length "1..32";
                                }
                                description "CPM card serial number which secure-boot activates";
                            }

                        }
                        output {

                            ///admin/system/security/secure-boot/revoke-key/output/operation-id
                            leaf operation-id {
                                type types-operation:operation-id;
                                description "ID assigned to the operation.";
                            }

                            ///admin/system/security/secure-boot/revoke-key/output/start-time
                            leaf start-time {
                                type types-operation:operation-timestamp;
                                description "Time when the operation started its execution.";
                            }

                            ///admin/system/security/secure-boot/revoke-key/output/results-path
                            leaf results-path {
                                type types-operation:operation-path;
                                description "Path to the results of the operation formatted as xpath.";
                            }

                            ///admin/system/security/secure-boot/revoke-key/output/status
                            leaf status {
                                type types-operation:operation-status;
                                description "Status of the operation";
                            }

                            ///admin/system/security/secure-boot/revoke-key/output/error-message
                            leaf-list error-message {
                                type types-operation:operation-message;
                                description "Error messages reported during execution of the operation.";
                            }

                            ///admin/system/security/secure-boot/revoke-key/output/warning-message
                            leaf-list warning-message {
                                type types-operation:operation-message;
                                description "Warning messages reported during execution of the operation.";
                            }

                            ///admin/system/security/secure-boot/revoke-key/output/info-message
                            leaf-list info-message {
                                type types-operation:operation-message;
                                description "Info messages reported during execution of the operation.";
                            }

                            ///admin/system/security/secure-boot/revoke-key/output/end-time
                            leaf end-time {
                                type types-operation:operation-timestamp;
                                description "Time when the operation ended its execution.";
                            }

                        }
                    } // action revoke-key

                    ///admin/system/security/secure-boot/update-key
                    action update-key {
                        description "Update secure boot keys";

                        input {

                            ///admin/system/security/secure-boot/update-key/input/card
                            leaf card {
                                type leafref {
                                    path "/state:state/state:cpm/state:cpm-slot";
                                }
                                mandatory true;
                                description "CPM slot where secure boot is activated or modified";
                            }

                            ///admin/system/security/secure-boot/update-key/input/confirmation-code
                            leaf confirmation-code {
                                type types-sros:string-not-all-spaces {
                                    length "1..32";
                                }
                                description "Confirmation code";
                            }

                            ///admin/system/security/secure-boot/update-key/input/now
                            leaf now {
                                type empty;
                                description "Perform the action immediately";
                            }

                            ///admin/system/security/secure-boot/update-key/input/serial-number
                            leaf serial-number {
                                type types-sros:string-not-all-spaces {
                                    length "1..32";
                                }
                                description "CPM card serial number which secure-boot activates";
                            }

                            ///admin/system/security/secure-boot/update-key/input/software-image
                            leaf software-image {
                                type types-sros:cflash-and-url;
                                mandatory true;
                                description "Location of the target software image";
                            }

                        }
                        output {

                            ///admin/system/security/secure-boot/update-key/output/operation-id
                            leaf operation-id {
                                type types-operation:operation-id;
                                description "ID assigned to the operation.";
                            }

                            ///admin/system/security/secure-boot/update-key/output/start-time
                            leaf start-time {
                                type types-operation:operation-timestamp;
                                description "Time when the operation started its execution.";
                            }

                            ///admin/system/security/secure-boot/update-key/output/results-path
                            leaf results-path {
                                type types-operation:operation-path;
                                description "Path to the results of the operation formatted as xpath.";
                            }

                            ///admin/system/security/secure-boot/update-key/output/status
                            leaf status {
                                type types-operation:operation-status;
                                description "Status of the operation";
                            }

                            ///admin/system/security/secure-boot/update-key/output/error-message
                            leaf-list error-message {
                                type types-operation:operation-message;
                                description "Error messages reported during execution of the operation.";
                            }

                            ///admin/system/security/secure-boot/update-key/output/warning-message
                            leaf-list warning-message {
                                type types-operation:operation-message;
                                description "Warning messages reported during execution of the operation.";
                            }

                            ///admin/system/security/secure-boot/update-key/output/info-message
                            leaf-list info-message {
                                type types-operation:operation-message;
                                description "Info messages reported during execution of the operation.";
                            }

                            ///admin/system/security/secure-boot/update-key/output/end-time
                            leaf end-time {
                                type types-operation:operation-timestamp;
                                description "Time when the operation ended its execution.";
                            }

                        }
                    } // action update-key

                    ///admin/system/security/secure-boot/validate
                    action validate {
                        description "Validate software signature for the specified image";

                        input {

                            ///admin/system/security/secure-boot/validate/input/software-image
                            leaf software-image {
                                type types-sros:cflash-and-url;
                                mandatory true;
                                description "Location of the target software image";
                            }

                        }
                        output {

                            ///admin/system/security/secure-boot/validate/output/operation-id
                            leaf operation-id {
                                type types-operation:operation-id;
                                description "ID assigned to the operation.";
                            }

                            ///admin/system/security/secure-boot/validate/output/start-time
                            leaf start-time {
                                type types-operation:operation-timestamp;
                                description "Time when the operation started its execution.";
                            }

                            ///admin/system/security/secure-boot/validate/output/results-path
                            leaf results-path {
                                type types-operation:operation-path;
                                description "Path to the results of the operation formatted as xpath.";
                            }

                            ///admin/system/security/secure-boot/validate/output/status
                            leaf status {
                                type types-operation:operation-status;
                                description "Status of the operation";
                            }

                            ///admin/system/security/secure-boot/validate/output/error-message
                            leaf-list error-message {
                                type types-operation:operation-message;
                                description "Error messages reported during execution of the operation.";
                            }

                            ///admin/system/security/secure-boot/validate/output/warning-message
                            leaf-list warning-message {
                                type types-operation:operation-message;
                                description "Warning messages reported during execution of the operation.";
                            }

                            ///admin/system/security/secure-boot/validate/output/info-message
                            leaf-list info-message {
                                type types-operation:operation-message;
                                description "Info messages reported during execution of the operation.";
                            }

                            ///admin/system/security/secure-boot/validate/output/end-time
                            leaf end-time {
                                type types-operation:operation-timestamp;
                                description "Time when the operation ended its execution.";
                            }

                        }
                    } // action validate

                } // container secure-boot

                ///admin/system/security/system-password
                action system-password {
                    description "Change a local system password";

                    input {

                        ///admin/system/security/system-password/input/admin-password
                        leaf admin-password {
                            type empty;
                            mandatory true;
                            description "Administrative password";
                        }

                    }
                    output {

                        ///admin/system/security/system-password/output/operation-id
                        leaf operation-id {
                            type types-operation:operation-id;
                            description "ID assigned to the operation.";
                        }

                        ///admin/system/security/system-password/output/start-time
                        leaf start-time {
                            type types-operation:operation-timestamp;
                            description "Time when the operation started its execution.";
                        }

                        ///admin/system/security/system-password/output/results-path
                        leaf results-path {
                            type types-operation:operation-path;
                            description "Path to the results of the operation formatted as xpath.";
                        }

                        ///admin/system/security/system-password/output/status
                        leaf status {
                            type types-operation:operation-status;
                            description "Status of the operation";
                        }

                        ///admin/system/security/system-password/output/error-message
                        leaf-list error-message {
                            type types-operation:operation-message;
                            description "Error messages reported during execution of the operation.";
                        }

                        ///admin/system/security/system-password/output/warning-message
                        leaf-list warning-message {
                            type types-operation:operation-message;
                            description "Warning messages reported during execution of the operation.";
                        }

                        ///admin/system/security/system-password/output/info-message
                        leaf-list info-message {
                            type types-operation:operation-message;
                            description "Info messages reported during execution of the operation.";
                        }

                        ///admin/system/security/system-password/output/end-time
                        leaf end-time {
                            type types-operation:operation-timestamp;
                            description "Time when the operation ended its execution.";
                        }

                    }
                } // action system-password

                ///admin/system/security/pki
                container pki {
                    description "Perform PKI related operations";

                    ///admin/system/security/pki/clear-ocsp-cache
                    action clear-ocsp-cache {
                        description "Clear the current OCSP response cache";

                        input {

                            ///admin/system/security/pki/clear-ocsp-cache/input/entry-id
                            leaf entry-id {
                                type uint32 {
                                    range "1..2000";
                                }
                                description "Local OCSP response cache entry ID to clear";
                            }

                        }
                        output {

                            ///admin/system/security/pki/clear-ocsp-cache/output/operation-id
                            leaf operation-id {
                                type types-operation:operation-id;
                                description "ID assigned to the operation.";
                            }

                            ///admin/system/security/pki/clear-ocsp-cache/output/start-time
                            leaf start-time {
                                type types-operation:operation-timestamp;
                                description "Time when the operation started its execution.";
                            }

                            ///admin/system/security/pki/clear-ocsp-cache/output/results-path
                            leaf results-path {
                                type types-operation:operation-path;
                                description "Path to the results of the operation formatted as xpath.";
                            }

                            ///admin/system/security/pki/clear-ocsp-cache/output/status
                            leaf status {
                                type types-operation:operation-status;
                                description "Status of the operation";
                            }

                            ///admin/system/security/pki/clear-ocsp-cache/output/error-message
                            leaf-list error-message {
                                type types-operation:operation-message;
                                description "Error messages reported during execution of the operation.";
                            }

                            ///admin/system/security/pki/clear-ocsp-cache/output/warning-message
                            leaf-list warning-message {
                                type types-operation:operation-message;
                                description "Warning messages reported during execution of the operation.";
                            }

                            ///admin/system/security/pki/clear-ocsp-cache/output/info-message
                            leaf-list info-message {
                                type types-operation:operation-message;
                                description "Info messages reported during execution of the operation.";
                            }

                            ///admin/system/security/pki/clear-ocsp-cache/output/end-time
                            leaf end-time {
                                type types-operation:operation-timestamp;
                                description "Time when the operation ended its execution.";
                            }

                        }
                    } // action clear-ocsp-cache

                    ///admin/system/security/pki/cmpv2
                    container cmpv2 {
                        description "Perform CMPv2 operations";

                        ///admin/system/security/pki/cmpv2/cert-request
                        action cert-request {
                            description "Request an additional certificate";

                            input {

                                ///admin/system/security/pki/cmpv2/cert-request/input/ca-profile
                                leaf ca-profile {
                                    type leafref {
                                        path "/state:state/state:system/state:security/state:pki/state:ca-profile/state:ca-profile-name";
                                    }
                                    mandatory true;
                                    description "PKI CA profile name";
                                }

                                ///admin/system/security/pki/cmpv2/cert-request/input/current-key
                                leaf current-key {
                                    type types-security:pki-file-name;
                                    mandatory true;
                                    description "Imported key file used to create the request";
                                }

                                ///admin/system/security/pki/cmpv2/cert-request/input/current-certificate
                                leaf current-certificate {
                                    type types-security:pki-file-name;
                                    mandatory true;
                                    description "Existing imported certificate file to create request";
                                }

                                ///admin/system/security/pki/cmpv2/cert-request/input/new-key
                                leaf new-key {
                                    type types-security:pki-file-name;
                                    mandatory true;
                                    description "New imported key file to create certificate request";
                                }

                                ///admin/system/security/pki/cmpv2/cert-request/input/hash-algorithm
                                leaf hash-algorithm {
                                    type types-security:hash-algorithm;
                                    description "Hash algorithm used for the certificate signature";
                                }

                                ///admin/system/security/pki/cmpv2/cert-request/input/subject-dn
                                leaf subject-dn {
                                    type string {
                                        length "1..256";
                                    }
                                    description "Subject of the requesting certificate";
                                }

                                ///admin/system/security/pki/cmpv2/cert-request/input/domain-name
                                leaf domain-name {
                                    type string {
                                        length "1..512";
                                    }
                                    description "FQDNs for the Subject Alternative Name";
                                }

                                ///admin/system/security/pki/cmpv2/cert-request/input/ip-address
                                leaf ip-address {
                                    type types-sros:ip-address;
                                    description "IP address for the Subject Alternative Name";
                                }

                                ///admin/system/security/pki/cmpv2/cert-request/input/save-as
                                leaf save-as {
                                    type types-sros:cflash-url;
                                    mandatory true;
                                    description "Full path to save the result certificate";
                                }

                            }
                            output {

                                ///admin/system/security/pki/cmpv2/cert-request/output/operation-id
                                leaf operation-id {
                                    type types-operation:operation-id;
                                    description "ID assigned to the operation.";
                                }

                                ///admin/system/security/pki/cmpv2/cert-request/output/start-time
                                leaf start-time {
                                    type types-operation:operation-timestamp;
                                    description "Time when the operation started its execution.";
                                }

                                ///admin/system/security/pki/cmpv2/cert-request/output/results-path
                                leaf results-path {
                                    type types-operation:operation-path;
                                    description "Path to the results of the operation formatted as xpath.";
                                }

                                ///admin/system/security/pki/cmpv2/cert-request/output/results
                                container results {
                                    description "Enter the results context";

                                    ///admin/system/security/pki/cmpv2/cert-request/output/results/request-parameters
                                    container request-parameters {
                                        description "Enter the request-parameters context";

                                        ///admin/system/security/pki/cmpv2/cert-request/output/results/request-parameters/ca-profile
                                        leaf ca-profile {
                                            type string {
                                                length "1..32";
                                            }
                                            description "The pki ca-profile name";
                                        }

                                        ///admin/system/security/pki/cmpv2/cert-request/output/results/request-parameters/save-as
                                        leaf save-as {
                                            type types-sros:cflash-url;
                                            description "Path to result certificate file";
                                        }

                                        ///admin/system/security/pki/cmpv2/cert-request/output/results/request-parameters/current-key
                                        leaf current-key {
                                            type types-security:pki-file-name;
                                        }

                                        ///admin/system/security/pki/cmpv2/cert-request/output/results/request-parameters/current-certificate
                                        leaf current-certificate {
                                            type types-security:pki-file-name;
                                        }

                                        ///admin/system/security/pki/cmpv2/cert-request/output/results/request-parameters/new-key
                                        leaf new-key {
                                            type types-security:pki-file-name;
                                        }

                                        ///admin/system/security/pki/cmpv2/cert-request/output/results/request-parameters/hash-algorithm
                                        leaf hash-algorithm {
                                            type types-security:hash-algorithm;
                                            description "Hash algorithm used for the certificate signature";
                                        }

                                        ///admin/system/security/pki/cmpv2/cert-request/output/results/request-parameters/subject-dn
                                        leaf subject-dn {
                                            type string {
                                                length "1..256";
                                            }
                                            description "Subject of the requesting certificate";
                                        }

                                        ///admin/system/security/pki/cmpv2/cert-request/output/results/request-parameters/domain-name
                                        leaf domain-name {
                                            type string {
                                                length "1..512";
                                            }
                                            description "FQDNs for the Subject Alternative Name";
                                        }

                                        ///admin/system/security/pki/cmpv2/cert-request/output/results/request-parameters/ip-address
                                        leaf ip-address {
                                            type types-sros:ip-address;
                                            description "IP address for the Subject Alternative Name";
                                        }

                                    } // container request-parameters

                                    ///admin/system/security/pki/cmpv2/cert-request/output/results/last-ca-response-time
                                    leaf last-ca-response-time {
                                        type yang:date-and-time;
                                        description "Time when CA last response";
                                    }

                                    ///admin/system/security/pki/cmpv2/cert-request/output/results/transaction-status
                                    leaf transaction-status {
                                        type types-security:cmpv2-transaction-status;
                                        description "CMPv2 transaction status";
                                    }

                                    ///admin/system/security/pki/cmpv2/cert-request/output/results/transaction-status-code
                                    leaf transaction-status-code {
                                        type types-security:cmpv2-transaction-status-code;
                                        description "CMPv2 transaction status code";
                                    }

                                    ///admin/system/security/pki/cmpv2/cert-request/output/results/transaction-status-string
                                    leaf transaction-status-string {
                                        type string {
                                            length "1..255";
                                        }
                                        description "CMPv2 transaction extra status info";
                                    }

                                } // container results

                                ///admin/system/security/pki/cmpv2/cert-request/output/status
                                leaf status {
                                    type types-operation:operation-status;
                                    description "Status of the operation";
                                }

                                ///admin/system/security/pki/cmpv2/cert-request/output/error-message
                                leaf-list error-message {
                                    type types-operation:operation-message;
                                    description "Error messages reported during execution of the operation.";
                                }

                                ///admin/system/security/pki/cmpv2/cert-request/output/warning-message
                                leaf-list warning-message {
                                    type types-operation:operation-message;
                                    description "Warning messages reported during execution of the operation.";
                                }

                                ///admin/system/security/pki/cmpv2/cert-request/output/info-message
                                leaf-list info-message {
                                    type types-operation:operation-message;
                                    description "Info messages reported during execution of the operation.";
                                }

                                ///admin/system/security/pki/cmpv2/cert-request/output/end-time
                                leaf end-time {
                                    type types-operation:operation-timestamp;
                                    description "Time when the operation ended its execution.";
                                }

                            }
                        } // action cert-request

                        ///admin/system/security/pki/cmpv2/clear-request
                        action clear-request {
                            description "Clear pending CMPv2 requests";

                            input {

                                ///admin/system/security/pki/cmpv2/clear-request/input/ca-profile
                                leaf ca-profile {
                                    type leafref {
                                        path "/state:state/state:system/state:security/state:pki/state:ca-profile/state:ca-profile-name";
                                    }
                                    mandatory true;
                                    description "PKI CA profile name";
                                }

                            }
                            output {

                                ///admin/system/security/pki/cmpv2/clear-request/output/operation-id
                                leaf operation-id {
                                    type types-operation:operation-id;
                                    description "ID assigned to the operation.";
                                }

                                ///admin/system/security/pki/cmpv2/clear-request/output/start-time
                                leaf start-time {
                                    type types-operation:operation-timestamp;
                                    description "Time when the operation started its execution.";
                                }

                                ///admin/system/security/pki/cmpv2/clear-request/output/results-path
                                leaf results-path {
                                    type types-operation:operation-path;
                                    description "Path to the results of the operation formatted as xpath.";
                                }

                                ///admin/system/security/pki/cmpv2/clear-request/output/status
                                leaf status {
                                    type types-operation:operation-status;
                                    description "Status of the operation";
                                }

                                ///admin/system/security/pki/cmpv2/clear-request/output/error-message
                                leaf-list error-message {
                                    type types-operation:operation-message;
                                    description "Error messages reported during execution of the operation.";
                                }

                                ///admin/system/security/pki/cmpv2/clear-request/output/warning-message
                                leaf-list warning-message {
                                    type types-operation:operation-message;
                                    description "Warning messages reported during execution of the operation.";
                                }

                                ///admin/system/security/pki/cmpv2/clear-request/output/info-message
                                leaf-list info-message {
                                    type types-operation:operation-message;
                                    description "Info messages reported during execution of the operation.";
                                }

                                ///admin/system/security/pki/cmpv2/clear-request/output/end-time
                                leaf end-time {
                                    type types-operation:operation-timestamp;
                                    description "Time when the operation ended its execution.";
                                }

                            }
                        } // action clear-request

                        ///admin/system/security/pki/cmpv2/initial-registration
                        action initial-registration {
                            description "Request initial certificate using the CMPv2 protocol";

                            input {

                                ///admin/system/security/pki/cmpv2/initial-registration/input/ca-profile
                                leaf ca-profile {
                                    type leafref {
                                        path "/state:state/state:system/state:security/state:pki/state:ca-profile/state:ca-profile-name";
                                    }
                                    mandatory true;
                                    description "PKI CA profile name";
                                }

                                ///admin/system/security/pki/cmpv2/initial-registration/input/key-to-certify
                                leaf key-to-certify {
                                    type types-security:pki-file-name;
                                    mandatory true;
                                    description "Name of the key file used to create initial request";
                                }

                                ///admin/system/security/pki/cmpv2/initial-registration/input/protection-algorithm
                                choice protection-algorithm {
                                    mandatory true;
                                    ///admin/system/security/pki/cmpv2/initial-registration/input/protection-algorithm/password
                                    case password {

                                        ///admin/system/security/pki/cmpv2/initial-registration/input/protection-algorithm/password/password
                                        leaf password {
                                            type string {
                                                length "1..64";
                                            }
                                            description "Password for message protection";
                                        }

                                        ///admin/system/security/pki/cmpv2/initial-registration/input/protection-algorithm/password/reference
                                        leaf reference {
                                            type string {
                                                length "1..64";
                                            }
                                            description "Password reference number";
                                        }

                                    }
                                    ///admin/system/security/pki/cmpv2/initial-registration/input/protection-algorithm/signature
                                    case signature {

                                        ///admin/system/security/pki/cmpv2/initial-registration/input/protection-algorithm/signature/certificate
                                        leaf certificate {
                                            type types-security:pki-file-name;
                                            description "Filename of the certificate for the protection key";
                                        }

                                        ///admin/system/security/pki/cmpv2/initial-registration/input/protection-algorithm/signature/send-chain
                                        leaf send-chain {
                                            type empty;
                                            description "Send a certificate chain";
                                        }

                                        ///admin/system/security/pki/cmpv2/initial-registration/input/protection-algorithm/signature/with-ca
                                        leaf with-ca {
                                            type leafref {
                                                path "/state:state/state:system/state:security/state:pki/state:ca-profile/state:ca-profile-name";
                                            }
                                            description "Name of CA profile with certificate in the send chain";
                                        }

                                        ///admin/system/security/pki/cmpv2/initial-registration/input/protection-algorithm/signature/protection-key
                                        leaf protection-key {
                                            type types-security:pki-file-name;
                                            description "Key file used to generate message protection signature";
                                        }

                                        ///admin/system/security/pki/cmpv2/initial-registration/input/protection-algorithm/signature/hash-algorithm
                                        leaf hash-algorithm {
                                            type types-security:hash-algorithm;
                                            description "Hash algorithm used for the certificate signature";
                                        }

                                    }
                                }
                                ///admin/system/security/pki/cmpv2/initial-registration/input/subject-dn
                                leaf subject-dn {
                                    type string {
                                        length "1..256";
                                    }
                                    description "Subject of the requesting certificate";
                                }

                                ///admin/system/security/pki/cmpv2/initial-registration/input/domain-name
                                leaf domain-name {
                                    type string {
                                        length "1..512";
                                    }
                                    description "FQDNs for the Subject Alternative Name";
                                }

                                ///admin/system/security/pki/cmpv2/initial-registration/input/ip-address
                                leaf ip-address {
                                    type types-sros:ip-address;
                                    description "IP address for the Subject Alternative Name";
                                }

                                ///admin/system/security/pki/cmpv2/initial-registration/input/save-as
                                leaf save-as {
                                    type types-sros:cflash-url;
                                    mandatory true;
                                    description "Full path to save the result certificate";
                                }

                            }
                            output {

                                ///admin/system/security/pki/cmpv2/initial-registration/output/operation-id
                                leaf operation-id {
                                    type types-operation:operation-id;
                                    description "ID assigned to the operation.";
                                }

                                ///admin/system/security/pki/cmpv2/initial-registration/output/start-time
                                leaf start-time {
                                    type types-operation:operation-timestamp;
                                    description "Time when the operation started its execution.";
                                }

                                ///admin/system/security/pki/cmpv2/initial-registration/output/results-path
                                leaf results-path {
                                    type types-operation:operation-path;
                                    description "Path to the results of the operation formatted as xpath.";
                                }

                                ///admin/system/security/pki/cmpv2/initial-registration/output/results
                                container results {
                                    description "Enter the results context";

                                    ///admin/system/security/pki/cmpv2/initial-registration/output/results/request-parameters
                                    container request-parameters {
                                        description "Enter the request-parameters context";

                                        ///admin/system/security/pki/cmpv2/initial-registration/output/results/request-parameters/ca-profile
                                        leaf ca-profile {
                                            type string {
                                                length "1..32";
                                            }
                                            description "The pki ca-profile name";
                                        }

                                        ///admin/system/security/pki/cmpv2/initial-registration/output/results/request-parameters/save-as
                                        leaf save-as {
                                            type types-sros:cflash-url;
                                            description "Path to result certificate file";
                                        }

                                        ///admin/system/security/pki/cmpv2/initial-registration/output/results/request-parameters/key-to-certify
                                        leaf key-to-certify {
                                            type types-security:pki-file-name;
                                        }

                                        ///admin/system/security/pki/cmpv2/initial-registration/output/results/request-parameters/protection-algorithm
                                        choice protection-algorithm {
                                            ///admin/system/security/pki/cmpv2/initial-registration/output/results/request-parameters/protection-algorithm/password
                                            case password {

                                                ///admin/system/security/pki/cmpv2/initial-registration/output/results/request-parameters/protection-algorithm/password/reference
                                                leaf reference {
                                                    type string {
                                                        length "1..64";
                                                    }
                                                }

                                            }
                                            ///admin/system/security/pki/cmpv2/initial-registration/output/results/request-parameters/protection-algorithm/signature
                                            case signature {

                                                ///admin/system/security/pki/cmpv2/initial-registration/output/results/request-parameters/protection-algorithm/signature/certificate
                                                leaf certificate {
                                                    type types-security:pki-file-name;
                                                }

                                                ///admin/system/security/pki/cmpv2/initial-registration/output/results/request-parameters/protection-algorithm/signature/send-chain
                                                leaf send-chain {
                                                    type empty;
                                                }

                                                ///admin/system/security/pki/cmpv2/initial-registration/output/results/request-parameters/protection-algorithm/signature/with-ca
                                                leaf with-ca {
                                                    type string {
                                                        length "1..32";
                                                    }
                                                }

                                                ///admin/system/security/pki/cmpv2/initial-registration/output/results/request-parameters/protection-algorithm/signature/protection-key
                                                leaf protection-key {
                                                    type types-security:pki-file-name;
                                                }

                                                ///admin/system/security/pki/cmpv2/initial-registration/output/results/request-parameters/protection-algorithm/signature/hash-algorithm
                                                leaf hash-algorithm {
                                                    type types-security:hash-algorithm;
                                                    description "Hash algorithm used for the certificate signature";
                                                }

                                            }
                                        }
                                        ///admin/system/security/pki/cmpv2/initial-registration/output/results/request-parameters/subject-dn
                                        leaf subject-dn {
                                            type string {
                                                length "1..256";
                                            }
                                            description "Subject of the requesting certificate";
                                        }

                                        ///admin/system/security/pki/cmpv2/initial-registration/output/results/request-parameters/domain-name
                                        leaf domain-name {
                                            type string {
                                                length "1..512";
                                            }
                                            description "FQDNs for the Subject Alternative Name";
                                        }

                                        ///admin/system/security/pki/cmpv2/initial-registration/output/results/request-parameters/ip-address
                                        leaf ip-address {
                                            type types-sros:ip-address;
                                            description "IP address for the Subject Alternative Name";
                                        }

                                    } // container request-parameters

                                    ///admin/system/security/pki/cmpv2/initial-registration/output/results/ca-profile
                                    leaf ca-profile {
                                        type string {
                                            length "1..32";
                                        }
                                        description "The pki ca-profile name";
                                    }

                                    ///admin/system/security/pki/cmpv2/initial-registration/output/results/save-as
                                    leaf save-as {
                                        type types-sros:cflash-url;
                                        description "Path to result certificate file";
                                    }

                                    ///admin/system/security/pki/cmpv2/initial-registration/output/results/last-ca-response-time
                                    leaf last-ca-response-time {
                                        type yang:date-and-time;
                                        description "Time when CA last response";
                                    }

                                    ///admin/system/security/pki/cmpv2/initial-registration/output/results/transaction-status
                                    leaf transaction-status {
                                        type types-security:cmpv2-transaction-status;
                                        description "CMPv2 transaction status";
                                    }

                                    ///admin/system/security/pki/cmpv2/initial-registration/output/results/transaction-status-code
                                    leaf transaction-status-code {
                                        type types-security:cmpv2-transaction-status-code;
                                        description "CMPv2 transaction status code";
                                    }

                                    ///admin/system/security/pki/cmpv2/initial-registration/output/results/transaction-status-string
                                    leaf transaction-status-string {
                                        type string {
                                            length "1..255";
                                        }
                                        description "CMPv2 transaction extra status info";
                                    }

                                } // container results

                                ///admin/system/security/pki/cmpv2/initial-registration/output/status
                                leaf status {
                                    type types-operation:operation-status;
                                    description "Status of the operation";
                                }

                                ///admin/system/security/pki/cmpv2/initial-registration/output/error-message
                                leaf-list error-message {
                                    type types-operation:operation-message;
                                    description "Error messages reported during execution of the operation.";
                                }

                                ///admin/system/security/pki/cmpv2/initial-registration/output/warning-message
                                leaf-list warning-message {
                                    type types-operation:operation-message;
                                    description "Warning messages reported during execution of the operation.";
                                }

                                ///admin/system/security/pki/cmpv2/initial-registration/output/info-message
                                leaf-list info-message {
                                    type types-operation:operation-message;
                                    description "Info messages reported during execution of the operation.";
                                }

                                ///admin/system/security/pki/cmpv2/initial-registration/output/end-time
                                leaf end-time {
                                    type types-operation:operation-timestamp;
                                    description "Time when the operation ended its execution.";
                                }

                            }
                        } // action initial-registration

                        ///admin/system/security/pki/cmpv2/key-update
                        action key-update {
                            description "Request new certificate to update existing certificate";

                            input {

                                ///admin/system/security/pki/cmpv2/key-update/input/ca-profile
                                leaf ca-profile {
                                    type leafref {
                                        path "/state:state/state:system/state:security/state:pki/state:ca-profile/state:ca-profile-name";
                                    }
                                    mandatory true;
                                    description "PKI CA profile name";
                                }

                                ///admin/system/security/pki/cmpv2/key-update/input/new-key
                                leaf new-key {
                                    type types-security:pki-file-name;
                                    mandatory true;
                                    description "Name of new imported key file used for the key update";
                                }

                                ///admin/system/security/pki/cmpv2/key-update/input/old-key
                                leaf old-key {
                                    type types-security:pki-file-name;
                                    mandatory true;
                                    description "Name of the old key file to be replaced";
                                }

                                ///admin/system/security/pki/cmpv2/key-update/input/old-certificate
                                leaf old-certificate {
                                    type types-security:pki-file-name;
                                    mandatory true;
                                    description "Name of the old certificate file to be replaced";
                                }

                                ///admin/system/security/pki/cmpv2/key-update/input/hash-algorithm
                                leaf hash-algorithm {
                                    type types-security:hash-algorithm;
                                    description "Hash algorithm used for the certificate signature";
                                }

                                ///admin/system/security/pki/cmpv2/key-update/input/save-as
                                leaf save-as {
                                    type types-sros:cflash-url;
                                    mandatory true;
                                    description "Full path to save the result certificate file";
                                }

                            }
                            output {

                                ///admin/system/security/pki/cmpv2/key-update/output/operation-id
                                leaf operation-id {
                                    type types-operation:operation-id;
                                    description "ID assigned to the operation.";
                                }

                                ///admin/system/security/pki/cmpv2/key-update/output/start-time
                                leaf start-time {
                                    type types-operation:operation-timestamp;
                                    description "Time when the operation started its execution.";
                                }

                                ///admin/system/security/pki/cmpv2/key-update/output/results-path
                                leaf results-path {
                                    type types-operation:operation-path;
                                    description "Path to the results of the operation formatted as xpath.";
                                }

                                ///admin/system/security/pki/cmpv2/key-update/output/results
                                container results {
                                    description "Enter the results context";

                                    ///admin/system/security/pki/cmpv2/key-update/output/results/request-parameters
                                    container request-parameters {
                                        description "Enter the request-parameters context";

                                        ///admin/system/security/pki/cmpv2/key-update/output/results/request-parameters/ca-profile
                                        leaf ca-profile {
                                            type string {
                                                length "1..32";
                                            }
                                            description "The pki ca-profile name";
                                        }

                                        ///admin/system/security/pki/cmpv2/key-update/output/results/request-parameters/save-as
                                        leaf save-as {
                                            type types-sros:cflash-url;
                                            description "Path to result certificate file";
                                        }

                                        ///admin/system/security/pki/cmpv2/key-update/output/results/request-parameters/new-key
                                        leaf new-key {
                                            type types-security:pki-file-name;
                                        }

                                        ///admin/system/security/pki/cmpv2/key-update/output/results/request-parameters/old-key
                                        leaf old-key {
                                            type types-security:pki-file-name;
                                        }

                                        ///admin/system/security/pki/cmpv2/key-update/output/results/request-parameters/old-certificate
                                        leaf old-certificate {
                                            type types-security:pki-file-name;
                                        }

                                        ///admin/system/security/pki/cmpv2/key-update/output/results/request-parameters/hash-algorithm
                                        leaf hash-algorithm {
                                            type types-security:hash-algorithm;
                                            description "Hash algorithm used for the certificate signature";
                                        }

                                    } // container request-parameters

                                    ///admin/system/security/pki/cmpv2/key-update/output/results/last-ca-response-time
                                    leaf last-ca-response-time {
                                        type yang:date-and-time;
                                        description "Time when CA last response";
                                    }

                                    ///admin/system/security/pki/cmpv2/key-update/output/results/transaction-status
                                    leaf transaction-status {
                                        type types-security:cmpv2-transaction-status;
                                        description "CMPv2 transaction status";
                                    }

                                    ///admin/system/security/pki/cmpv2/key-update/output/results/transaction-status-code
                                    leaf transaction-status-code {
                                        type types-security:cmpv2-transaction-status-code;
                                        description "CMPv2 transaction status code";
                                    }

                                    ///admin/system/security/pki/cmpv2/key-update/output/results/transaction-status-string
                                    leaf transaction-status-string {
                                        type string {
                                            length "1..255";
                                        }
                                        description "CMPv2 transaction extra status info";
                                    }

                                } // container results

                                ///admin/system/security/pki/cmpv2/key-update/output/status
                                leaf status {
                                    type types-operation:operation-status;
                                    description "Status of the operation";
                                }

                                ///admin/system/security/pki/cmpv2/key-update/output/error-message
                                leaf-list error-message {
                                    type types-operation:operation-message;
                                    description "Error messages reported during execution of the operation.";
                                }

                                ///admin/system/security/pki/cmpv2/key-update/output/warning-message
                                leaf-list warning-message {
                                    type types-operation:operation-message;
                                    description "Warning messages reported during execution of the operation.";
                                }

                                ///admin/system/security/pki/cmpv2/key-update/output/info-message
                                leaf-list info-message {
                                    type types-operation:operation-message;
                                    description "Info messages reported during execution of the operation.";
                                }

                                ///admin/system/security/pki/cmpv2/key-update/output/end-time
                                leaf end-time {
                                    type types-operation:operation-timestamp;
                                    description "Time when the operation ended its execution.";
                                }

                            }
                        } // action key-update

                        ///admin/system/security/pki/cmpv2/poll
                        action poll {
                            description "Poll the CMPv2 server for pending request status";

                            input {

                                ///admin/system/security/pki/cmpv2/poll/input/ca-profile
                                leaf ca-profile {
                                    type leafref {
                                        path "/state:state/state:system/state:security/state:pki/state:ca-profile/state:ca-profile-name";
                                    }
                                    mandatory true;
                                    description "PKI CA profile name";
                                }

                            }
                            output {

                                ///admin/system/security/pki/cmpv2/poll/output/operation-id
                                leaf operation-id {
                                    type types-operation:operation-id;
                                    description "ID assigned to the operation.";
                                }

                                ///admin/system/security/pki/cmpv2/poll/output/start-time
                                leaf start-time {
                                    type types-operation:operation-timestamp;
                                    description "Time when the operation started its execution.";
                                }

                                ///admin/system/security/pki/cmpv2/poll/output/results-path
                                leaf results-path {
                                    type types-operation:operation-path;
                                    description "Path to the results of the operation formatted as xpath.";
                                }

                                ///admin/system/security/pki/cmpv2/poll/output/results
                                container results {
                                    description "Enter the results context";

                                    ///admin/system/security/pki/cmpv2/poll/output/results/request-type
                                    leaf request-type {
                                        type types-security:cmpv2-request-type;
                                        description "CMPv2 request type";
                                    }

                                    ///admin/system/security/pki/cmpv2/poll/output/results/ca-profile
                                    leaf ca-profile {
                                        type string {
                                            length "1..32";
                                        }
                                        description "The pki ca-profile name";
                                    }

                                    ///admin/system/security/pki/cmpv2/poll/output/results/save-as
                                    leaf save-as {
                                        type types-sros:cflash-url;
                                        description "Path to result certificate file";
                                    }

                                    ///admin/system/security/pki/cmpv2/poll/output/results/last-ca-response-time
                                    leaf last-ca-response-time {
                                        type yang:date-and-time;
                                        description "Time when CA last response";
                                    }

                                    ///admin/system/security/pki/cmpv2/poll/output/results/transaction-status
                                    leaf transaction-status {
                                        type types-security:cmpv2-transaction-status;
                                        description "CMPv2 transaction status";
                                    }

                                    ///admin/system/security/pki/cmpv2/poll/output/results/transaction-status-code
                                    leaf transaction-status-code {
                                        type types-security:cmpv2-transaction-status-code;
                                        description "CMPv2 transaction status code";
                                    }

                                    ///admin/system/security/pki/cmpv2/poll/output/results/transaction-status-string
                                    leaf transaction-status-string {
                                        type string {
                                            length "1..255";
                                        }
                                        description "CMPv2 transaction extra status info";
                                    }

                                } // container results

                                ///admin/system/security/pki/cmpv2/poll/output/status
                                leaf status {
                                    type types-operation:operation-status;
                                    description "Status of the operation";
                                }

                                ///admin/system/security/pki/cmpv2/poll/output/error-message
                                leaf-list error-message {
                                    type types-operation:operation-message;
                                    description "Error messages reported during execution of the operation.";
                                }

                                ///admin/system/security/pki/cmpv2/poll/output/warning-message
                                leaf-list warning-message {
                                    type types-operation:operation-message;
                                    description "Warning messages reported during execution of the operation.";
                                }

                                ///admin/system/security/pki/cmpv2/poll/output/info-message
                                leaf-list info-message {
                                    type types-operation:operation-message;
                                    description "Info messages reported during execution of the operation.";
                                }

                                ///admin/system/security/pki/cmpv2/poll/output/end-time
                                leaf end-time {
                                    type types-operation:operation-timestamp;
                                    description "Time when the operation ended its execution.";
                                }

                            }
                        } // action poll

                    } // container cmpv2

                    ///admin/system/security/pki/convert-file
                    action convert-file {
                        description "Convert imported file between secure and legacy format";

                        input {

                            ///admin/system/security/pki/convert-file/input/input-file
                            leaf input-file {
                                type types-security:pki-file-name;
                                mandatory true;
                                description "Name of the file to be converted";
                            }

                            ///admin/system/security/pki/convert-file/input/output-file
                            leaf output-file {
                                type types-security:pki-file-name;
                                mandatory true;
                                description "Output filename";
                            }

                            ///admin/system/security/pki/convert-file/input/format
                            leaf format {
                                type types-security:cert-file-convert-format;
                                mandatory true;
                                description "File format to convert to";
                            }

                            ///admin/system/security/pki/convert-file/input/force
                            leaf force {
                                type empty;
                                description "Force the conversion";
                            }

                        }
                        output {

                            ///admin/system/security/pki/convert-file/output/operation-id
                            leaf operation-id {
                                type types-operation:operation-id;
                                description "ID assigned to the operation.";
                            }

                            ///admin/system/security/pki/convert-file/output/start-time
                            leaf start-time {
                                type types-operation:operation-timestamp;
                                description "Time when the operation started its execution.";
                            }

                            ///admin/system/security/pki/convert-file/output/results-path
                            leaf results-path {
                                type types-operation:operation-path;
                                description "Path to the results of the operation formatted as xpath.";
                            }

                            ///admin/system/security/pki/convert-file/output/status
                            leaf status {
                                type types-operation:operation-status;
                                description "Status of the operation";
                            }

                            ///admin/system/security/pki/convert-file/output/error-message
                            leaf-list error-message {
                                type types-operation:operation-message;
                                description "Error messages reported during execution of the operation.";
                            }

                            ///admin/system/security/pki/convert-file/output/warning-message
                            leaf-list warning-message {
                                type types-operation:operation-message;
                                description "Warning messages reported during execution of the operation.";
                            }

                            ///admin/system/security/pki/convert-file/output/info-message
                            leaf-list info-message {
                                type types-operation:operation-message;
                                description "Info messages reported during execution of the operation.";
                            }

                            ///admin/system/security/pki/convert-file/output/end-time
                            leaf end-time {
                                type types-operation:operation-timestamp;
                                description "Time when the operation ended its execution.";
                            }

                        }
                    } // action convert-file

                    ///admin/system/security/pki/crl-update
                    action crl-update {
                        description "Trigger the CRL update for the CA profile";

                        input {

                            ///admin/system/security/pki/crl-update/input/ca-profile
                            leaf ca-profile {
                                type leafref {
                                    path "/state:state/state:system/state:security/state:pki/state:ca-profile/state:ca-profile-name";
                                }
                                mandatory true;
                                description "PKI CA profile name";
                            }

                        }
                        output {

                            ///admin/system/security/pki/crl-update/output/operation-id
                            leaf operation-id {
                                type types-operation:operation-id;
                                description "ID assigned to the operation.";
                            }

                            ///admin/system/security/pki/crl-update/output/start-time
                            leaf start-time {
                                type types-operation:operation-timestamp;
                                description "Time when the operation started its execution.";
                            }

                            ///admin/system/security/pki/crl-update/output/results-path
                            leaf results-path {
                                type types-operation:operation-path;
                                description "Path to the results of the operation formatted as xpath.";
                            }

                            ///admin/system/security/pki/crl-update/output/status
                            leaf status {
                                type types-operation:operation-status;
                                description "Status of the operation";
                            }

                            ///admin/system/security/pki/crl-update/output/error-message
                            leaf-list error-message {
                                type types-operation:operation-message;
                                description "Error messages reported during execution of the operation.";
                            }

                            ///admin/system/security/pki/crl-update/output/warning-message
                            leaf-list warning-message {
                                type types-operation:operation-message;
                                description "Warning messages reported during execution of the operation.";
                            }

                            ///admin/system/security/pki/crl-update/output/info-message
                            leaf-list info-message {
                                type types-operation:operation-message;
                                description "Info messages reported during execution of the operation.";
                            }

                            ///admin/system/security/pki/crl-update/output/end-time
                            leaf end-time {
                                type types-operation:operation-timestamp;
                                description "Time when the operation ended its execution.";
                            }

                        }
                    } // action crl-update

                    ///admin/system/security/pki/est
                    container est {
                        description "Perform Enrollment over Secure Transport operations";

                        ///admin/system/security/pki/est/ca-certificates
                        action ca-certificates {
                            description "Download CA certificates from the EST server";

                            input {

                                ///admin/system/security/pki/est/ca-certificates/input/est-profile
                                leaf est-profile {
                                    type string {
                                        length "1..32";
                                    }
                                    mandatory true;
                                    description "PKI EST profile name";
                                }

                                ///admin/system/security/pki/est/ca-certificates/input/output-url
                                leaf output-url {
                                    type types-sros:cflash-url;
                                    mandatory true;
                                    description "Path to the result file";
                                }

                                ///admin/system/security/pki/est/ca-certificates/input/force
                                leaf force {
                                    type empty;
                                    description "Force an overwrite of the result file";
                                }

                            }
                            output {

                                ///admin/system/security/pki/est/ca-certificates/output/operation-id
                                leaf operation-id {
                                    type types-operation:operation-id;
                                    description "ID assigned to the operation.";
                                }

                                ///admin/system/security/pki/est/ca-certificates/output/start-time
                                leaf start-time {
                                    type types-operation:operation-timestamp;
                                    description "Time when the operation started its execution.";
                                }

                                ///admin/system/security/pki/est/ca-certificates/output/results-path
                                leaf results-path {
                                    type types-operation:operation-path;
                                    description "Path to the results of the operation formatted as xpath.";
                                }

                                ///admin/system/security/pki/est/ca-certificates/output/status
                                leaf status {
                                    type types-operation:operation-status;
                                    description "Status of the operation";
                                }

                                ///admin/system/security/pki/est/ca-certificates/output/error-message
                                leaf-list error-message {
                                    type types-operation:operation-message;
                                    description "Error messages reported during execution of the operation.";
                                }

                                ///admin/system/security/pki/est/ca-certificates/output/warning-message
                                leaf-list warning-message {
                                    type types-operation:operation-message;
                                    description "Warning messages reported during execution of the operation.";
                                }

                                ///admin/system/security/pki/est/ca-certificates/output/info-message
                                leaf-list info-message {
                                    type types-operation:operation-message;
                                    description "Info messages reported during execution of the operation.";
                                }

                                ///admin/system/security/pki/est/ca-certificates/output/end-time
                                leaf end-time {
                                    type types-operation:operation-timestamp;
                                    description "Time when the operation ended its execution.";
                                }

                            }
                        } // action ca-certificates

                        ///admin/system/security/pki/est/enroll
                        action enroll {
                            description "Enroll a new certificate with CA with the EST protocol";

                            input {

                                ///admin/system/security/pki/est/enroll/input/est-profile
                                leaf est-profile {
                                    type string {
                                        length "1..32";
                                    }
                                    mandatory true;
                                    description "PKI EST profile name";
                                }

                                ///admin/system/security/pki/est/enroll/input/key
                                leaf key {
                                    type types-sros:cflash-url;
                                    mandatory true;
                                    description "Name of the imported the key file to enroll";
                                }

                                ///admin/system/security/pki/est/enroll/input/hash-algorithm
                                leaf hash-algorithm {
                                    type types-security:hash-algorithm;
                                    description "Hash algorithm used for the certificate signature";
                                }

                                ///admin/system/security/pki/est/enroll/input/subject-dn
                                leaf subject-dn {
                                    type string {
                                        length "1..256";
                                    }
                                    description "Subject of the requesting certificate";
                                }

                                ///admin/system/security/pki/est/enroll/input/domain-name
                                leaf domain-name {
                                    type string {
                                        length "1..512";
                                    }
                                    description "FQDNs for the Subject Alternative Name";
                                }

                                ///admin/system/security/pki/est/enroll/input/ip-address
                                leaf ip-address {
                                    type types-sros:ip-address;
                                    description "IP address for the Subject Alternative Name";
                                }

                                ///admin/system/security/pki/est/enroll/input/output-file
                                leaf output-file {
                                    type types-security:pki-file-name;
                                    mandatory true;
                                    description "Name of the result file";
                                }

                                ///admin/system/security/pki/est/enroll/input/force
                                leaf force {
                                    type empty;
                                    description "Force an overwrite of the result file";
                                }

                                ///admin/system/security/pki/est/enroll/input/validate-certificate-chain
                                leaf validate-certificate-chain {
                                    type empty;
                                    description "Validate result certificate chain before importing";
                                }

                            }
                            output {

                                ///admin/system/security/pki/est/enroll/output/operation-id
                                leaf operation-id {
                                    type types-operation:operation-id;
                                    description "ID assigned to the operation.";
                                }

                                ///admin/system/security/pki/est/enroll/output/start-time
                                leaf start-time {
                                    type types-operation:operation-timestamp;
                                    description "Time when the operation started its execution.";
                                }

                                ///admin/system/security/pki/est/enroll/output/results-path
                                leaf results-path {
                                    type types-operation:operation-path;
                                    description "Path to the results of the operation formatted as xpath.";
                                }

                                ///admin/system/security/pki/est/enroll/output/status
                                leaf status {
                                    type types-operation:operation-status;
                                    description "Status of the operation";
                                }

                                ///admin/system/security/pki/est/enroll/output/error-message
                                leaf-list error-message {
                                    type types-operation:operation-message;
                                    description "Error messages reported during execution of the operation.";
                                }

                                ///admin/system/security/pki/est/enroll/output/warning-message
                                leaf-list warning-message {
                                    type types-operation:operation-message;
                                    description "Warning messages reported during execution of the operation.";
                                }

                                ///admin/system/security/pki/est/enroll/output/info-message
                                leaf-list info-message {
                                    type types-operation:operation-message;
                                    description "Info messages reported during execution of the operation.";
                                }

                                ///admin/system/security/pki/est/enroll/output/end-time
                                leaf end-time {
                                    type types-operation:operation-timestamp;
                                    description "Time when the operation ended its execution.";
                                }

                            }
                        } // action enroll

                        ///admin/system/security/pki/est/renew
                        action renew {
                            description "Renew a CA certificate using the EST protocol";

                            input {

                                ///admin/system/security/pki/est/renew/input/est-profile
                                leaf est-profile {
                                    type string {
                                        length "1..32";
                                    }
                                    mandatory true;
                                    description "PKI EST profile name";
                                }

                                ///admin/system/security/pki/est/renew/input/certificate
                                leaf certificate {
                                    type types-sros:cflash-url;
                                    mandatory true;
                                    description "Name of the imported certificate file to renew";
                                }

                                ///admin/system/security/pki/est/renew/input/key
                                leaf key {
                                    type types-sros:cflash-url;
                                    mandatory true;
                                    description "Imported key file of the certificate to renew";
                                }

                                ///admin/system/security/pki/est/renew/input/hash-algorithm
                                leaf hash-algorithm {
                                    type types-security:hash-algorithm;
                                    description "Hash algorithm used for the certificate signature";
                                }

                                ///admin/system/security/pki/est/renew/input/output-file
                                leaf output-file {
                                    type types-security:pki-file-name;
                                    mandatory true;
                                    description "Name of the result file";
                                }

                                ///admin/system/security/pki/est/renew/input/force
                                leaf force {
                                    type empty;
                                    description "Force an overwrite of the result file";
                                }

                                ///admin/system/security/pki/est/renew/input/validate-certificate-chain
                                leaf validate-certificate-chain {
                                    type empty;
                                    description "Validate result certificate chain before importing";
                                }

                            }
                            output {

                                ///admin/system/security/pki/est/renew/output/operation-id
                                leaf operation-id {
                                    type types-operation:operation-id;
                                    description "ID assigned to the operation.";
                                }

                                ///admin/system/security/pki/est/renew/output/start-time
                                leaf start-time {
                                    type types-operation:operation-timestamp;
                                    description "Time when the operation started its execution.";
                                }

                                ///admin/system/security/pki/est/renew/output/results-path
                                leaf results-path {
                                    type types-operation:operation-path;
                                    description "Path to the results of the operation formatted as xpath.";
                                }

                                ///admin/system/security/pki/est/renew/output/status
                                leaf status {
                                    type types-operation:operation-status;
                                    description "Status of the operation";
                                }

                                ///admin/system/security/pki/est/renew/output/error-message
                                leaf-list error-message {
                                    type types-operation:operation-message;
                                    description "Error messages reported during execution of the operation.";
                                }

                                ///admin/system/security/pki/est/renew/output/warning-message
                                leaf-list warning-message {
                                    type types-operation:operation-message;
                                    description "Warning messages reported during execution of the operation.";
                                }

                                ///admin/system/security/pki/est/renew/output/info-message
                                leaf-list info-message {
                                    type types-operation:operation-message;
                                    description "Info messages reported during execution of the operation.";
                                }

                                ///admin/system/security/pki/est/renew/output/end-time
                                leaf end-time {
                                    type types-operation:operation-timestamp;
                                    description "Time when the operation ended its execution.";
                                }

                            }
                        } // action renew

                    } // container est

                    ///admin/system/security/pki/export
                    action export {
                        description "Export an imported file";

                        input {

                            ///admin/system/security/pki/export/input/input-file
                            leaf input-file {
                                type types-security:pki-file-name;
                                mandatory true;
                                description "Name of the file to be exported";
                            }

                            ///admin/system/security/pki/export/input/output-url
                            leaf output-url {
                                type types-sros:cflash-url;
                                mandatory true;
                                description "Full path to export the result file";
                            }

                            ///admin/system/security/pki/export/input/type
                            leaf type {
                                type types-security:cert-export-file-type;
                                mandatory true;
                                description "Type of file to be exported";
                            }

                            ///admin/system/security/pki/export/input/format
                            leaf format {
                                type types-security:cert-export-file-format;
                                mandatory true;
                                description "Output file format";
                            }

                            ///admin/system/security/pki/export/input/password
                            leaf password {
                                type string {
                                    length "1..32";
                                }
                                description "Password used to encrypt the output file";
                            }

                            ///admin/system/security/pki/export/input/key-file
                            leaf key-file {
                                type types-security:pki-file-name;
                                description "Name of the key file to be exported";
                            }

                        }
                        output {

                            ///admin/system/security/pki/export/output/operation-id
                            leaf operation-id {
                                type types-operation:operation-id;
                                description "ID assigned to the operation.";
                            }

                            ///admin/system/security/pki/export/output/start-time
                            leaf start-time {
                                type types-operation:operation-timestamp;
                                description "Time when the operation started its execution.";
                            }

                            ///admin/system/security/pki/export/output/results-path
                            leaf results-path {
                                type types-operation:operation-path;
                                description "Path to the results of the operation formatted as xpath.";
                            }

                            ///admin/system/security/pki/export/output/status
                            leaf status {
                                type types-operation:operation-status;
                                description "Status of the operation";
                            }

                            ///admin/system/security/pki/export/output/error-message
                            leaf-list error-message {
                                type types-operation:operation-message;
                                description "Error messages reported during execution of the operation.";
                            }

                            ///admin/system/security/pki/export/output/warning-message
                            leaf-list warning-message {
                                type types-operation:operation-message;
                                description "Warning messages reported during execution of the operation.";
                            }

                            ///admin/system/security/pki/export/output/info-message
                            leaf-list info-message {
                                type types-operation:operation-message;
                                description "Info messages reported during execution of the operation.";
                            }

                            ///admin/system/security/pki/export/output/end-time
                            leaf end-time {
                                type types-operation:operation-timestamp;
                                description "Time when the operation ended its execution.";
                            }

                        }
                    } // action export

                    ///admin/system/security/pki/generate-keypair
                    action generate-keypair {
                        description "Generate PKI key pair";

                        input {

                            ///admin/system/security/pki/generate-keypair/input/save-path
                            leaf save-path {
                                type types-sros:cflash-url;
                                mandatory true;
                                description "Full path to save the result key file";
                            }

                            ///admin/system/security/pki/generate-keypair/input/key-type
                            choice key-type {
                                mandatory true;
                                ///admin/system/security/pki/generate-keypair/input/key-type/rsa
                                case rsa {

                                    ///admin/system/security/pki/generate-keypair/input/key-type/rsa/rsa-key-size
                                    leaf rsa-key-size {
                                        type uint32 {
                                            range "512..8192";
                                        }
                                        default "2048";
                                        description "Length of the RSA key to be generated";
                                    }

                                }
                                ///admin/system/security/pki/generate-keypair/input/key-type/dsa
                                case dsa {

                                    ///admin/system/security/pki/generate-keypair/input/key-type/dsa/dsa-key-size
                                    leaf dsa-key-size {
                                        type uint32 {
                                            range "512..8192";
                                        }
                                        default "2048";
                                        description "Length of the DSA key to be generated";
                                    }

                                }
                                ///admin/system/security/pki/generate-keypair/input/key-type/ecdsa
                                case ecdsa {

                                    ///admin/system/security/pki/generate-keypair/input/key-type/ecdsa/ecdsa-curve
                                    leaf ecdsa-curve {
                                        type types-security:ecdsa-curve;
                                        default "secp256r1";
                                        description "Elliptic curve of the ECDSA key to be generated";
                                    }

                                }
                            }
                        }
                        output {

                            ///admin/system/security/pki/generate-keypair/output/operation-id
                            leaf operation-id {
                                type types-operation:operation-id;
                                description "ID assigned to the operation.";
                            }

                            ///admin/system/security/pki/generate-keypair/output/start-time
                            leaf start-time {
                                type types-operation:operation-timestamp;
                                description "Time when the operation started its execution.";
                            }

                            ///admin/system/security/pki/generate-keypair/output/results-path
                            leaf results-path {
                                type types-operation:operation-path;
                                description "Path to the results of the operation formatted as xpath.";
                            }

                            ///admin/system/security/pki/generate-keypair/output/status
                            leaf status {
                                type types-operation:operation-status;
                                description "Status of the operation";
                            }

                            ///admin/system/security/pki/generate-keypair/output/error-message
                            leaf-list error-message {
                                type types-operation:operation-message;
                                description "Error messages reported during execution of the operation.";
                            }

                            ///admin/system/security/pki/generate-keypair/output/warning-message
                            leaf-list warning-message {
                                type types-operation:operation-message;
                                description "Warning messages reported during execution of the operation.";
                            }

                            ///admin/system/security/pki/generate-keypair/output/info-message
                            leaf-list info-message {
                                type types-operation:operation-message;
                                description "Info messages reported during execution of the operation.";
                            }

                            ///admin/system/security/pki/generate-keypair/output/end-time
                            leaf end-time {
                                type types-operation:operation-timestamp;
                                description "Time when the operation ended its execution.";
                            }

                        }
                    } // action generate-keypair

                    ///admin/system/security/pki/generate-csr
                    action generate-csr {
                        description "Generate a PKCS#10 certificate signing request file";

                        input {

                            ///admin/system/security/pki/generate-csr/input/key-url
                            leaf key-url {
                                type types-sros:cflash-url;
                                mandatory true;
                                description "Full path to the key file used to generate the request";
                            }

                            ///admin/system/security/pki/generate-csr/input/hash-algorithm
                            leaf hash-algorithm {
                                type types-security:hash-algorithm;
                                description "Hash algorithm used for the certificate signature";
                            }

                            ///admin/system/security/pki/generate-csr/input/subject-dn
                            leaf subject-dn {
                                type string {
                                    length "1..256";
                                }
                                description "Subject of the requesting certificate";
                            }

                            ///admin/system/security/pki/generate-csr/input/domain-name
                            leaf domain-name {
                                type string {
                                    length "1..512";
                                }
                                description "FQDNs for the Subject Alternative Name";
                            }

                            ///admin/system/security/pki/generate-csr/input/ip-address
                            leaf ip-address {
                                type types-sros:ip-address;
                                description "IP address for the Subject Alternative Name";
                            }

                            ///admin/system/security/pki/generate-csr/input/output-url
                            leaf output-url {
                                type types-sros:cflash-url;
                                mandatory true;
                                description "Full path to result certificate signing request file";
                            }

                            ///admin/system/security/pki/generate-csr/input/use-printable
                            leaf use-printable {
                                type empty;
                                description "Force ASCII encoding for input subject DN attributes";
                            }

                        }
                        output {

                            ///admin/system/security/pki/generate-csr/output/operation-id
                            leaf operation-id {
                                type types-operation:operation-id;
                                description "ID assigned to the operation.";
                            }

                            ///admin/system/security/pki/generate-csr/output/start-time
                            leaf start-time {
                                type types-operation:operation-timestamp;
                                description "Time when the operation started its execution.";
                            }

                            ///admin/system/security/pki/generate-csr/output/results-path
                            leaf results-path {
                                type types-operation:operation-path;
                                description "Path to the results of the operation formatted as xpath.";
                            }

                            ///admin/system/security/pki/generate-csr/output/status
                            leaf status {
                                type types-operation:operation-status;
                                description "Status of the operation";
                            }

                            ///admin/system/security/pki/generate-csr/output/error-message
                            leaf-list error-message {
                                type types-operation:operation-message;
                                description "Error messages reported during execution of the operation.";
                            }

                            ///admin/system/security/pki/generate-csr/output/warning-message
                            leaf-list warning-message {
                                type types-operation:operation-message;
                                description "Warning messages reported during execution of the operation.";
                            }

                            ///admin/system/security/pki/generate-csr/output/info-message
                            leaf-list info-message {
                                type types-operation:operation-message;
                                description "Info messages reported during execution of the operation.";
                            }

                            ///admin/system/security/pki/generate-csr/output/end-time
                            leaf end-time {
                                type types-operation:operation-timestamp;
                                description "Time when the operation ended its execution.";
                            }

                        }
                    } // action generate-csr

                    ///admin/system/security/pki/import
                    action import {
                        description "Import a certificate related file";

                        input {

                            ///admin/system/security/pki/import/input/input-url
                            leaf input-url {
                                type types-sros:cflash-url;
                                mandatory true;
                                description "Full path to the file to import";
                            }

                            ///admin/system/security/pki/import/input/output-file
                            leaf output-file {
                                type types-security:pki-file-name;
                                mandatory true;
                                description "Name of the result file";
                            }

                            ///admin/system/security/pki/import/input/type
                            leaf type {
                                type types-security:cert-export-file-type;
                                mandatory true;
                                description "Type of file to be exported";
                            }

                            ///admin/system/security/pki/import/input/format
                            leaf format {
                                type types-security:cert-export-file-format;
                                mandatory true;
                                description "Output file format";
                            }

                            ///admin/system/security/pki/import/input/password
                            leaf password {
                                type string {
                                    length "1..32";
                                }
                                description "Password used to encrypt the output file";
                            }

                            ///admin/system/security/pki/import/input/validate-certificate-chain
                            leaf validate-certificate-chain {
                                type empty;
                                description "Validate the certificate chain";
                            }

                        }
                        output {

                            ///admin/system/security/pki/import/output/operation-id
                            leaf operation-id {
                                type types-operation:operation-id;
                                description "ID assigned to the operation.";
                            }

                            ///admin/system/security/pki/import/output/start-time
                            leaf start-time {
                                type types-operation:operation-timestamp;
                                description "Time when the operation started its execution.";
                            }

                            ///admin/system/security/pki/import/output/results-path
                            leaf results-path {
                                type types-operation:operation-path;
                                description "Path to the results of the operation formatted as xpath.";
                            }

                            ///admin/system/security/pki/import/output/status
                            leaf status {
                                type types-operation:operation-status;
                                description "Status of the operation";
                            }

                            ///admin/system/security/pki/import/output/error-message
                            leaf-list error-message {
                                type types-operation:operation-message;
                                description "Error messages reported during execution of the operation.";
                            }

                            ///admin/system/security/pki/import/output/warning-message
                            leaf-list warning-message {
                                type types-operation:operation-message;
                                description "Warning messages reported during execution of the operation.";
                            }

                            ///admin/system/security/pki/import/output/info-message
                            leaf-list info-message {
                                type types-operation:operation-message;
                                description "Info messages reported during execution of the operation.";
                            }

                            ///admin/system/security/pki/import/output/end-time
                            leaf end-time {
                                type types-operation:operation-timestamp;
                                description "Time when the operation ended its execution.";
                            }

                        }
                    } // action import

                    ///admin/system/security/pki/reload
                    action reload {
                        description "Reload key or certificate files";

                        input {

                            ///admin/system/security/pki/reload/input/application
                            leaf application {
                                type enumeration {
                                    enum ipsec                          { value 0; }
                                }
                                mandatory true;
                                description "Application to be reloaded";
                            }

                            ///admin/system/security/pki/reload/input/certificate
                            leaf certificate {
                                type types-security:pki-file-name;
                                mandatory true;
                                description "Name of the certificate file to reload";
                            }

                            ///admin/system/security/pki/reload/input/key
                            leaf key {
                                type types-security:pki-file-name;
                                mandatory true;
                                description "Name of the key file to reload";
                            }

                        }
                        output {

                            ///admin/system/security/pki/reload/output/operation-id
                            leaf operation-id {
                                type types-operation:operation-id;
                                description "ID assigned to the operation.";
                            }

                            ///admin/system/security/pki/reload/output/start-time
                            leaf start-time {
                                type types-operation:operation-timestamp;
                                description "Time when the operation started its execution.";
                            }

                            ///admin/system/security/pki/reload/output/results-path
                            leaf results-path {
                                type types-operation:operation-path;
                                description "Path to the results of the operation formatted as xpath.";
                            }

                            ///admin/system/security/pki/reload/output/status
                            leaf status {
                                type types-operation:operation-status;
                                description "Status of the operation";
                            }

                            ///admin/system/security/pki/reload/output/error-message
                            leaf-list error-message {
                                type types-operation:operation-message;
                                description "Error messages reported during execution of the operation.";
                            }

                            ///admin/system/security/pki/reload/output/warning-message
                            leaf-list warning-message {
                                type types-operation:operation-message;
                                description "Warning messages reported during execution of the operation.";
                            }

                            ///admin/system/security/pki/reload/output/info-message
                            leaf-list info-message {
                                type types-operation:operation-message;
                                description "Info messages reported during execution of the operation.";
                            }

                            ///admin/system/security/pki/reload/output/end-time
                            leaf end-time {
                                type types-operation:operation-timestamp;
                                description "Time when the operation ended its execution.";
                            }

                        }
                    } // action reload

                    ///admin/system/security/pki/update-certificate
                    action update-certificate {
                        description "Update End Entity certificate";

                        input {

                            ///admin/system/security/pki/update-certificate/input/certificate
                            leaf certificate {
                                type leafref {
                                    path "/state:state/state:system/state:security/state:pki/state:certificate-auto-update/state:certificate-file-name";
                                }
                                mandatory true;
                                description "Name of the certificate file to be updated";
                            }

                        }
                        output {

                            ///admin/system/security/pki/update-certificate/output/operation-id
                            leaf operation-id {
                                type types-operation:operation-id;
                                description "ID assigned to the operation.";
                            }

                            ///admin/system/security/pki/update-certificate/output/start-time
                            leaf start-time {
                                type types-operation:operation-timestamp;
                                description "Time when the operation started its execution.";
                            }

                            ///admin/system/security/pki/update-certificate/output/results-path
                            leaf results-path {
                                type types-operation:operation-path;
                                description "Path to the results of the operation formatted as xpath.";
                            }

                            ///admin/system/security/pki/update-certificate/output/status
                            leaf status {
                                type types-operation:operation-status;
                                description "Status of the operation";
                            }

                            ///admin/system/security/pki/update-certificate/output/error-message
                            leaf-list error-message {
                                type types-operation:operation-message;
                                description "Error messages reported during execution of the operation.";
                            }

                            ///admin/system/security/pki/update-certificate/output/warning-message
                            leaf-list warning-message {
                                type types-operation:operation-message;
                                description "Warning messages reported during execution of the operation.";
                            }

                            ///admin/system/security/pki/update-certificate/output/info-message
                            leaf-list info-message {
                                type types-operation:operation-message;
                                description "Info messages reported during execution of the operation.";
                            }

                            ///admin/system/security/pki/update-certificate/output/end-time
                            leaf end-time {
                                type types-operation:operation-timestamp;
                                description "Time when the operation ended its execution.";
                            }

                        }
                    } // action update-certificate

                } // container pki

            } // container security

            ///admin/system/license
            container license {
                description "Enter the license context";

                ///admin/system/license/activate
                action activate {
                    description "Load and activate a system license";

                    input {

                        ///admin/system/license/activate/input/file-url
                        leaf file-url {
                            type string {
                                length "1..256";
                            }
                            description "Location of the license file to activate";
                        }

                        ///admin/system/license/activate/input/now
                        leaf now {
                            type empty;
                            description "Activate the license immediately";
                        }

                    }
                    output {

                        ///admin/system/license/activate/output/operation-id
                        leaf operation-id {
                            type types-operation:operation-id;
                            description "ID assigned to the operation.";
                        }

                        ///admin/system/license/activate/output/start-time
                        leaf start-time {
                            type types-operation:operation-timestamp;
                            description "Time when the operation started its execution.";
                        }

                        ///admin/system/license/activate/output/results-path
                        leaf results-path {
                            type types-operation:operation-path;
                            description "Path to the results of the operation formatted as xpath.";
                        }

                        ///admin/system/license/activate/output/results
                        container results {
                            description "Enter the results context";

                            ///admin/system/license/activate/output/results/active-sros-version
                            leaf active-sros-version {
                                type types-sros:description;
                                description "The current software version running on the system";
                            }

                            ///admin/system/license/activate/output/results/license-file
                            leaf license-file {
                                type types-sros:url;
                                description "The location of the validated license file";
                            }

                            ///admin/system/license/activate/output/results/license-name
                            leaf license-name {
                                type types-sros:description;
                                description "The name of the license";
                            }

                            ///admin/system/license/activate/output/results/license-uuid
                            leaf license-uuid {
                                type types-sros:description;
                                description "The target UUID of the license";
                            }

                            ///admin/system/license/activate/output/results/license-secondary-uuid
                            leaf license-secondary-uuid {
                                type types-sros:description;
                                description "The target secondary UUID of the license";
                            }

                            ///admin/system/license/activate/output/results/machine-uuid
                            leaf machine-uuid {
                                type types-sros:description;
                                description "The UUID of this machine";
                            }

                            ///admin/system/license/activate/output/results/license-description
                            leaf license-description {
                                type types-sros:description;
                                description "The description of the license";
                            }

                            ///admin/system/license/activate/output/results/license-product
                            leaf license-product {
                                type types-sros:description;
                                description "The product for which the license was issued";
                            }

                            ///admin/system/license/activate/output/results/license-applicable-versions
                            leaf license-applicable-versions {
                                type types-sros:description;
                                description "The software version(s) supported by the license";
                            }

                            ///admin/system/license/activate/output/results/license-issue-time
                            leaf license-issue-time {
                                type yang:date-and-time;
                                description "The date and time at which the license was issued";
                            }

                            ///admin/system/license/activate/output/results/license-start-time
                            leaf license-start-time {
                                type yang:date-and-time;
                                description "The date and time at which the license becomes valid";
                            }

                            ///admin/system/license/activate/output/results/license-end-time
                            leaf license-end-time {
                                type yang:date-and-time;
                                description "The date and time at which the license expires";
                            }

                            ///admin/system/license/activate/output/results/license-validation-status
                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            ///admin/system/license/activate/output/results/validation-error-additional-details
                            leaf validation-error-additional-details {
                                type types-sros:very-long-description-or-empty;
                                description "Additional text explaining a problem preventing license validation";
                            }

                        } // container results

                        ///admin/system/license/activate/output/status
                        leaf status {
                            type types-operation:operation-status;
                            description "Status of the operation";
                        }

                        ///admin/system/license/activate/output/error-message
                        leaf-list error-message {
                            type types-operation:operation-message;
                            description "Error messages reported during execution of the operation.";
                        }

                        ///admin/system/license/activate/output/warning-message
                        leaf-list warning-message {
                            type types-operation:operation-message;
                            description "Warning messages reported during execution of the operation.";
                        }

                        ///admin/system/license/activate/output/info-message
                        leaf-list info-message {
                            type types-operation:operation-message;
                            description "Info messages reported during execution of the operation.";
                        }

                        ///admin/system/license/activate/output/end-time
                        leaf end-time {
                            type types-operation:operation-timestamp;
                            description "Time when the operation ended its execution.";
                        }

                    }
                } // action activate

                ///admin/system/license/clear
                action clear {
                    description "Clear system license";

                    input {

                        ///admin/system/license/clear/input/now
                        leaf now {
                            type empty;
                            description "Clear license entitlements immediately";
                        }

                    }
                    output {

                        ///admin/system/license/clear/output/operation-id
                        leaf operation-id {
                            type types-operation:operation-id;
                            description "ID assigned to the operation.";
                        }

                        ///admin/system/license/clear/output/start-time
                        leaf start-time {
                            type types-operation:operation-timestamp;
                            description "Time when the operation started its execution.";
                        }

                        ///admin/system/license/clear/output/results-path
                        leaf results-path {
                            type types-operation:operation-path;
                            description "Path to the results of the operation formatted as xpath.";
                        }

                        ///admin/system/license/clear/output/results
                        container results {
                            description "Enter the results context";

                            ///admin/system/license/clear/output/results/active-sros-version
                            leaf active-sros-version {
                                type types-sros:description;
                                description "The current software version running on the system";
                            }

                            ///admin/system/license/clear/output/results/license-file
                            leaf license-file {
                                type types-sros:url;
                                description "The location of the validated license file";
                            }

                            ///admin/system/license/clear/output/results/license-name
                            leaf license-name {
                                type types-sros:description;
                                description "The name of the license";
                            }

                            ///admin/system/license/clear/output/results/license-uuid
                            leaf license-uuid {
                                type types-sros:description;
                                description "The target UUID of the license";
                            }

                            ///admin/system/license/clear/output/results/license-secondary-uuid
                            leaf license-secondary-uuid {
                                type types-sros:description;
                                description "The target secondary UUID of the license";
                            }

                            ///admin/system/license/clear/output/results/machine-uuid
                            leaf machine-uuid {
                                type types-sros:description;
                                description "The UUID of this machine";
                            }

                            ///admin/system/license/clear/output/results/license-description
                            leaf license-description {
                                type types-sros:description;
                                description "The description of the license";
                            }

                            ///admin/system/license/clear/output/results/license-product
                            leaf license-product {
                                type types-sros:description;
                                description "The product for which the license was issued";
                            }

                            ///admin/system/license/clear/output/results/license-applicable-versions
                            leaf license-applicable-versions {
                                type types-sros:description;
                                description "The software version(s) supported by the license";
                            }

                            ///admin/system/license/clear/output/results/license-issue-time
                            leaf license-issue-time {
                                type yang:date-and-time;
                                description "The date and time at which the license was issued";
                            }

                            ///admin/system/license/clear/output/results/license-start-time
                            leaf license-start-time {
                                type yang:date-and-time;
                                description "The date and time at which the license becomes valid";
                            }

                            ///admin/system/license/clear/output/results/license-end-time
                            leaf license-end-time {
                                type yang:date-and-time;
                                description "The date and time at which the license expires";
                            }

                            ///admin/system/license/clear/output/results/license-validation-status
                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            ///admin/system/license/clear/output/results/validation-error-additional-details
                            leaf validation-error-additional-details {
                                type types-sros:very-long-description-or-empty;
                                description "Additional text explaining a problem preventing license validation";
                            }

                        } // container results

                        ///admin/system/license/clear/output/status
                        leaf status {
                            type types-operation:operation-status;
                            description "Status of the operation";
                        }

                        ///admin/system/license/clear/output/error-message
                        leaf-list error-message {
                            type types-operation:operation-message;
                            description "Error messages reported during execution of the operation.";
                        }

                        ///admin/system/license/clear/output/warning-message
                        leaf-list warning-message {
                            type types-operation:operation-message;
                            description "Warning messages reported during execution of the operation.";
                        }

                        ///admin/system/license/clear/output/info-message
                        leaf-list info-message {
                            type types-operation:operation-message;
                            description "Info messages reported during execution of the operation.";
                        }

                        ///admin/system/license/clear/output/end-time
                        leaf end-time {
                            type types-operation:operation-timestamp;
                            description "Time when the operation ended its execution.";
                        }

                    }
                } // action clear

                ///admin/system/license/validate
                action validate {
                    description "Load and validate a system license";

                    input {

                        ///admin/system/license/validate/input/file-url
                        leaf file-url {
                            type string {
                                length "1..256";
                            }
                            description "Location of the license file to validate";
                        }

                    }
                    output {

                        ///admin/system/license/validate/output/operation-id
                        leaf operation-id {
                            type types-operation:operation-id;
                            description "ID assigned to the operation.";
                        }

                        ///admin/system/license/validate/output/start-time
                        leaf start-time {
                            type types-operation:operation-timestamp;
                            description "Time when the operation started its execution.";
                        }

                        ///admin/system/license/validate/output/results-path
                        leaf results-path {
                            type types-operation:operation-path;
                            description "Path to the results of the operation formatted as xpath.";
                        }

                        ///admin/system/license/validate/output/results
                        container results {
                            description "Enter the results context";

                            ///admin/system/license/validate/output/results/active-sros-version
                            leaf active-sros-version {
                                type types-sros:description;
                                description "The current software version running on the system";
                            }

                            ///admin/system/license/validate/output/results/license-file
                            leaf license-file {
                                type types-sros:url;
                                description "The location of the validated license file";
                            }

                            ///admin/system/license/validate/output/results/license-name
                            leaf license-name {
                                type types-sros:description;
                                description "The name of the license";
                            }

                            ///admin/system/license/validate/output/results/license-uuid
                            leaf license-uuid {
                                type types-sros:description;
                                description "The target UUID of the license";
                            }

                            ///admin/system/license/validate/output/results/license-secondary-uuid
                            leaf license-secondary-uuid {
                                type types-sros:description;
                                description "The target secondary UUID of the license";
                            }

                            ///admin/system/license/validate/output/results/machine-uuid
                            leaf machine-uuid {
                                type types-sros:description;
                                description "The UUID of this machine";
                            }

                            ///admin/system/license/validate/output/results/license-description
                            leaf license-description {
                                type types-sros:description;
                                description "The description of the license";
                            }

                            ///admin/system/license/validate/output/results/license-product
                            leaf license-product {
                                type types-sros:description;
                                description "The product for which the license was issued";
                            }

                            ///admin/system/license/validate/output/results/license-applicable-versions
                            leaf license-applicable-versions {
                                type types-sros:description;
                                description "The software version(s) supported by the license";
                            }

                            ///admin/system/license/validate/output/results/license-issue-time
                            leaf license-issue-time {
                                type yang:date-and-time;
                                description "The date and time at which the license was issued";
                            }

                            ///admin/system/license/validate/output/results/license-start-time
                            leaf license-start-time {
                                type yang:date-and-time;
                                description "The date and time at which the license becomes valid";
                            }

                            ///admin/system/license/validate/output/results/license-end-time
                            leaf license-end-time {
                                type yang:date-and-time;
                                description "The date and time at which the license expires";
                            }

                            ///admin/system/license/validate/output/results/license-validation-status
                            leaf license-validation-status {
                                type enumeration {
                                    enum incompatible-with-standby-cpm  { value -2; }
                                    enum url-invalid                    { value -1; }
                                    enum ok                             { value 0; }
                                    enum invalid                        { value 1; }
                                    enum reboot-required                { value 2; }
                                    enum incompatible                   { value 3; }
                                    enum update-required                { value 4; }
                                }
                                description "The result of the license valdiation";
                            }

                            ///admin/system/license/validate/output/results/validation-error-additional-details
                            leaf validation-error-additional-details {
                                type types-sros:very-long-description-or-empty;
                                description "Additional text explaining a problem preventing license validation";
                            }

                        } // container results

                        ///admin/system/license/validate/output/status
                        leaf status {
                            type types-operation:operation-status;
                            description "Status of the operation";
                        }

                        ///admin/system/license/validate/output/error-message
                        leaf-list error-message {
                            type types-operation:operation-message;
                            description "Error messages reported during execution of the operation.";
                        }

                        ///admin/system/license/validate/output/warning-message
                        leaf-list warning-message {
                            type types-operation:operation-message;
                            description "Warning messages reported during execution of the operation.";
                        }

                        ///admin/system/license/validate/output/info-message
                        leaf-list info-message {
                            type types-operation:operation-message;
                            description "Info messages reported during execution of the operation.";
                        }

                        ///admin/system/license/validate/output/end-time
                        leaf end-time {
                            type types-operation:operation-timestamp;
                            description "Time when the operation ended its execution.";
                        }

                    }
                } // action validate

            } // container license

            ///admin/system/telemetry
            container telemetry {
                description "Enter the telemetry context";

                ///admin/system/telemetry/grpc
                container grpc {
                    description "Enter the grpc context";

                    ///admin/system/telemetry/grpc/cancel
                    action cancel {
                        description "Cancel the gRPC dynamic telemetry subscription";

                        input {

                            ///admin/system/telemetry/grpc/cancel/input/cancel-options
                            choice cancel-options {
                                mandatory true;
                                ///admin/system/telemetry/grpc/cancel/input/cancel-options/subscription
                                case subscription {

                                    ///admin/system/telemetry/grpc/cancel/input/cancel-options/subscription/subscription-id
                                    leaf subscription-id {
                                        type uint32;
                                        description "ID of the telemetry subscription to cancel";
                                    }

                                }
                                ///admin/system/telemetry/grpc/cancel/input/cancel-options/all
                                case all {

                                    ///admin/system/telemetry/grpc/cancel/input/cancel-options/all/all
                                    leaf all {
                                        type empty;
                                        description "Cancel gRPC dynamic telemetry for all subscriptions";
                                    }

                                }
                            }
                        }
                        output {

                            ///admin/system/telemetry/grpc/cancel/output/operation-id
                            leaf operation-id {
                                type types-operation:operation-id;
                                description "ID assigned to the operation.";
                            }

                            ///admin/system/telemetry/grpc/cancel/output/start-time
                            leaf start-time {
                                type types-operation:operation-timestamp;
                                description "Time when the operation started its execution.";
                            }

                            ///admin/system/telemetry/grpc/cancel/output/results-path
                            leaf results-path {
                                type types-operation:operation-path;
                                description "Path to the results of the operation formatted as xpath.";
                            }

                            ///admin/system/telemetry/grpc/cancel/output/status
                            leaf status {
                                type types-operation:operation-status;
                                description "Status of the operation";
                            }

                            ///admin/system/telemetry/grpc/cancel/output/error-message
                            leaf-list error-message {
                                type types-operation:operation-message;
                                description "Error messages reported during execution of the operation.";
                            }

                            ///admin/system/telemetry/grpc/cancel/output/warning-message
                            leaf-list warning-message {
                                type types-operation:operation-message;
                                description "Warning messages reported during execution of the operation.";
                            }

                            ///admin/system/telemetry/grpc/cancel/output/info-message
                            leaf-list info-message {
                                type types-operation:operation-message;
                                description "Info messages reported during execution of the operation.";
                            }

                            ///admin/system/telemetry/grpc/cancel/output/end-time
                            leaf end-time {
                                type types-operation:operation-timestamp;
                                description "Time when the operation ended its execution.";
                            }

                        }
                    } // action cancel

                } // container grpc

            } // container telemetry

            ///admin/system/management-interface
            container management-interface {
                description "Enter the management-interface context";

                ///admin/system/management-interface/operations
                container operations {
                    description "Enter the operations context";

                    ///admin/system/management-interface/operations/delete-operation
                    action delete-operation {
                        description "Stop and remove an operation";

                        input {

                            ///admin/system/management-interface/operations/delete-operation/input/op-table-bypass
                            leaf op-table-bypass {
                                type types-operation:operation-op-table-bypass;
                                description "Avoid operation ID allocation";
                            }

                            ///admin/system/management-interface/operations/delete-operation/input/delete-id
                            leaf delete-id {
                                type types-operation:operation-id;
                                mandatory true;
                                description "ID of the operation to remove";
                            }

                        }
                        output {

                            ///admin/system/management-interface/operations/delete-operation/output/operation-id
                            leaf operation-id {
                                type types-operation:operation-id;
                                description "ID assigned to the operation.";
                            }

                            ///admin/system/management-interface/operations/delete-operation/output/start-time
                            leaf start-time {
                                type types-operation:operation-timestamp;
                                description "Time when the operation started its execution.";
                            }

                            ///admin/system/management-interface/operations/delete-operation/output/results-path
                            leaf results-path {
                                type types-operation:operation-path;
                                description "Path to the results of the operation formatted as xpath.";
                            }

                            ///admin/system/management-interface/operations/delete-operation/output/status
                            leaf status {
                                type types-operation:operation-status;
                                description "Status of the operation";
                            }

                            ///admin/system/management-interface/operations/delete-operation/output/error-message
                            leaf-list error-message {
                                type types-operation:operation-message;
                                description "Error messages reported during execution of the operation.";
                            }

                            ///admin/system/management-interface/operations/delete-operation/output/warning-message
                            leaf-list warning-message {
                                type types-operation:operation-message;
                                description "Warning messages reported during execution of the operation.";
                            }

                            ///admin/system/management-interface/operations/delete-operation/output/info-message
                            leaf-list info-message {
                                type types-operation:operation-message;
                                description "Info messages reported during execution of the operation.";
                            }

                            ///admin/system/management-interface/operations/delete-operation/output/end-time
                            leaf end-time {
                                type types-operation:operation-timestamp;
                                description "Time when the operation ended its execution.";
                            }

                        }
                    } // action delete-operation

                    ///admin/system/management-interface/operations/stop-operation
                    action stop-operation {
                        description "Stop the execution of an operational command";

                        input {

                            ///admin/system/management-interface/operations/stop-operation/input/op-table-bypass
                            leaf op-table-bypass {
                                type types-operation:operation-op-table-bypass;
                                description "Avoid operation ID allocation";
                            }

                            ///admin/system/management-interface/operations/stop-operation/input/stop-id
                            leaf stop-id {
                                type types-operation:operation-id;
                                mandatory true;
                                description "ID of the operation to stop";
                            }

                        }
                        output {

                            ///admin/system/management-interface/operations/stop-operation/output/operation-id
                            leaf operation-id {
                                type types-operation:operation-id;
                                description "ID assigned to the operation.";
                            }

                            ///admin/system/management-interface/operations/stop-operation/output/start-time
                            leaf start-time {
                                type types-operation:operation-timestamp;
                                description "Time when the operation started its execution.";
                            }

                            ///admin/system/management-interface/operations/stop-operation/output/results-path
                            leaf results-path {
                                type types-operation:operation-path;
                                description "Path to the results of the operation formatted as xpath.";
                            }

                            ///admin/system/management-interface/operations/stop-operation/output/status
                            leaf status {
                                type types-operation:operation-status;
                                description "Status of the operation";
                            }

                            ///admin/system/management-interface/operations/stop-operation/output/error-message
                            leaf-list error-message {
                                type types-operation:operation-message;
                                description "Error messages reported during execution of the operation.";
                            }

                            ///admin/system/management-interface/operations/stop-operation/output/warning-message
                            leaf-list warning-message {
                                type types-operation:operation-message;
                                description "Warning messages reported during execution of the operation.";
                            }

                            ///admin/system/management-interface/operations/stop-operation/output/info-message
                            leaf-list info-message {
                                type types-operation:operation-message;
                                description "Info messages reported during execution of the operation.";
                            }

                            ///admin/system/management-interface/operations/stop-operation/output/end-time
                            leaf end-time {
                                type types-operation:operation-timestamp;
                                description "Time when the operation ended its execution.";
                            }

                        }
                    } // action stop-operation

                } // container operations


            } // container management-interface

        } // container system


    } // container admin

}
