module nokia-types-esa {

    yang-version "1.1";

    namespace "urn:nokia.com:sros:ns:yang:sr:types-esa";

    prefix "types-esa";

    import nokia-sros-yang-extensions     { prefix "sros-ext"; }

    sros-ext:sros-major-release "rel23";
    organization "Nokia";
    contact
        "Nokia SR OS Support
         Web: <http://www.nokia.com>";
    description
        "Common esa types data types used in the SR OS management system.

         Copyright 2016 Nokia. All rights reserved. Reproduction of this document
         is authorized on the condition that the foregoing copyright notice is included.

         This nokia-types-esa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2022-10-12";

    typedef esa-id {
        type int32 {
            range "1..16";
        }
        description "The ID of the ESA.";
    }

    typedef vm-id {
        type int32 {
            range "1..4";
        }
        description "The ID of the VM.";
    }

    typedef esa-device-state {
        type enumeration {
            enum unknown                        { value 1; }
            enum ok                             { value 2; }
            enum degraded                       { value 3; }
            enum failed                         { value 4; }
            enum unsupported                    { value 5; }
        }
        description
            "The esa-device-state indicates the state of the device, as follows:
                - Unknown    : Device status not reported. Esa not connected or not booted yet.
                - Ok         : Device status is functioning normally.
                - Degraded   : Device status is degraded.
                - Failed     : Device status is failed.
                - Unsupported: Device status reporting is unsupported.";
    }

    typedef esa-device-redundancy-state {
        type enumeration {
            enum unknown                        { value 1; }
            enum redundant                      { value 2; }
            enum non-redundant                  { value 3; }
            enum failed-redundant               { value 4; }
            enum unsupported                    { value 5; }
        }
        description
            "The esa-device-redundancy-state indicates the redundancy status of an ESA device,
             as follows:
                - Unknown          : Device redundancy status not reported. Esa not connected or not booted yet.
                - Redundant        : Device is redundant.
                - Non-Redundant    : Device is non-redundant.
                - Failed-Redundant : Device status is failed-redundant.
                - Unsupported      : Device redundancy state reporting is unsupported.";
    }

    typedef esa-device-mismatch-state {
        type enumeration {
            enum unknown                        { value 1; }
            enum no-mismatch                    { value 2; }
            enum mismatch                       { value 3; }
            enum unsupported                    { value 4; }
        }
        description
            "The esa-device-mismatch-state indicates the mismatch status of an ESA device,
             as follows:
                - Unknown     : Device mismatch status not reported. Esa not connected or not booted yet.
                - No-mismatch : Device is in no mismatch state.
                - Mismatch    : Device is in mismatch state.
                - Unsupported : Device mismatch state reporting is unsupported.";
    }

}
