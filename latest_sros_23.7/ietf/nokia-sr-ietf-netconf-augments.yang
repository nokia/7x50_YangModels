module nokia-sr-ietf-netconf-augments {

  yang-version 1.1;

  namespace "urn:nokia.com:sros:ns:yang:sr:ietf-netconf-augments";

  prefix nokia-nc-augs;

  import ietf-netconf { prefix nc; }

  description "This YANG module defines augmentations to the standard NETCONF RPCs.";

  revision "2020-12-23" {
    description "Initial revision.";
  }

  grouping nokia-configuration-region {
    leaf configuration-region {
      type enumeration {
        enum configure {
          description "primary configuration region";
        }
        enum li {
          description "Lawful Intercept (LI) configuration region";
        }
        enum bof {
          description "BOF configuration region";
        }
        enum debug {
          description "debug configuration region";
        }
      }//enumeration

      description "SR OS configuration region";
    }// leaf configuration-region
  } //grouping nokia-configuration-region

  augment /nc:get-config/nc:input/nc:source {
    uses nokia-configuration-region;
  }

  augment /nc:validate/nc:input/nc:source {
    uses nokia-configuration-region;
  }

  augment /nc:copy-config/nc:input/nc:source {
    uses nokia-configuration-region;
  }

  augment /nc:copy-config/nc:input/nc:target {
    uses nokia-configuration-region;
  }

  augment /nc:edit-config/nc:input/nc:target {
    uses nokia-configuration-region;
  }

  augment /nc:lock/nc:input/nc:target {
    uses nokia-configuration-region;
  }

  augment /nc:unlock/nc:input/nc:target {
    uses nokia-configuration-region;
  }

  augment /nc:get/nc:input {
    uses nokia-configuration-region;
  }

  augment /nc:discard-changes/nc:input {
    uses nokia-configuration-region;
  }

  grouping nokia-commit-augments {
    leaf comment {
      type string {
        length "1..2048";
      } // string
      description "Comment associated with the commit";
    } // leaf comment
  } // grouping nokia-commit-augments

  augment /nc:commit/nc:input {
    uses nokia-configuration-region;
    uses nokia-commit-augments;
  }

  augment /nc:get-config/nc:input/nc:source/nc:config-source {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:validate/nc:input/nc:source/nc:config-source {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:copy-config/nc:input/nc:source/nc:config-source {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:copy-config/nc:input/nc:target/nc:config-target {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:edit-config/nc:input/nc:target/nc:config-target {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:lock/nc:input/nc:target/nc:config-target {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  augment /nc:unlock/nc:input/nc:target/nc:config-target {
    leaf li-candidate {
      type empty;
      description
        "The li candidate datastore is the config source";
    }

    leaf li-running {
      type empty;
      description
        "The li running datastore is the config source";
    }

    leaf li-startup {
      type empty;
      description
        "The li startup datastore is the config source";
    }

    leaf bof-candidate {
      type empty;
      description
        "The bof candidate datastore is the config source";
    }

    leaf bof-running {
      type empty;
      description
        "The bof running datastore is the config source";
    }

    leaf bof-startup {
      type empty;
      description
        "The bof startup datastore is the config source";
    }

    leaf debug-candidate {
      type empty;
      description
        "The debug candidate datastore is the config source";
    }

    leaf debug-running {
      type empty;
      description
        "The debug running datastore is the config source";
    }

    leaf debug-startup {
      type empty;
      description
        "The debug startup datastore is the config source";
    }
  }

  grouping nokia-output-formats {
    leaf format {
      description "Output format of data";
      type enumeration {
        enum "xml" {
          description "XML output format";
        }
        enum "json" {
          description "JSON IETF output format";
        }
        enum "md-cli" {
          description "MD-CLI output format";
        }
      } // enumeration
    } // leaf format
  } // grouping nokia-output-formats

  augment /nc:get-config/nc:input {
    uses nokia-output-formats;
  }

  augment /nc:get/nc:input {
    uses nokia-output-formats;
  }

}
