module nokia-sr-ietf-interfaces-deviations {
    yang-version "1.1";

    namespace "urn:nokia.com:sros:ns:yang:sr:ietf-interfaces-deviations";
    prefix nokia-if-devs;

    import ietf-interfaces { prefix if; }

    organization "Nokia";

    contact
        "Nokia SR OS Support
         Web: <http://www.nokia.com>";

    description
        "YANG Data model for Nokia NETCONF Interfaces deviations.

        Copyright 2022 Nokia. All rights reserved.
        Reproduction of this document is authorized on the condition
        that the foregoing copyright notice is included.

        This nokia-sr-ietf-interfaces-deviations YANG module embodies Nokia's
        proprietary intellectual property.  Nokia retains all title
        and ownership in the Specification, including any revisions.

        Nokia grants all interested parties a non-exclusive license
        to use and distribute an unmodified copy of this Specification
        in connection with management of Nokia products, and without
        fee, provided this copyright notice and license appear on all
        copies.

        This Specification is supplied `as is', and Nokia makes no
        warranty, either express or implied, as to the use, operation,
        condition, or performance of the Specification.";

    revision 2022-07-01;

    //Deviations

    deviation /if:interfaces {
        description
            "interfaces tree is not supported.";
        deviate not-supported;
    }

    deviation /if:interfaces-state {
        description
            "interfaces-state tree is not supported.";
        deviate not-supported;
    }
}
