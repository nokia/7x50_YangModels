module nokia-oper-global {

    yang-version "1.1";

    namespace "urn:nokia.com:sros:ns:yang:sr:oper-global";

    prefix "oper-global";

    import nokia-conf                     { prefix "conf"; }
    import nokia-sros-yang-extensions     { prefix "sros-ext"; }
    import nokia-state                    { prefix "state"; }
    import nokia-types-eth-cfm            { prefix "types-eth-cfm"; }
    import nokia-types-oam                { prefix "types-oam"; }
    import nokia-types-operation          { prefix "types-operation"; }
    import nokia-types-qos                { prefix "types-qos"; }
    import nokia-types-sros               { prefix "types-sros"; }
    import nokia-types-subscriber-mgmt    { prefix "types-subscriber-mgmt"; }

    sros-ext:sros-major-release "rel23";
    organization "Nokia";
    contact
        "Nokia SR OS Support
         Web: <http://www.nokia.com>";
    description
        "Nokia YANG Data model for Nokia global operations on SR OS based routers.

         Copyright 2016 Nokia. All rights reserved. Reproduction of this document
         is authorized on the condition that the foregoing copyright notice is included.

         This nokia-oper-global YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2020-10-15";

    ///global-operations
    container global-operations {
        config false;
        description "Global operations";

        ///global-operations/md-cli-raw-command
        action md-cli-raw-command {
            description "Trigger MD-CLI command.";

            input {

                ///global-operations/md-cli-raw-command/input/md-cli-input-line
                leaf md-cli-input-line {
                    type string;
                    mandatory true;
                    description "MD-CLI command to be executed..";
                }

            }
            output {

                ///global-operations/md-cli-raw-command/output/operation-id
                leaf operation-id {
                    type types-operation:operation-id;
                    description "ID assigned to the operation.";
                }

                ///global-operations/md-cli-raw-command/output/start-time
                leaf start-time {
                    type types-operation:operation-timestamp;
                    description "Time when the operation started its execution.";
                }

                ///global-operations/md-cli-raw-command/output/results-path
                leaf results-path {
                    type types-operation:operation-path;
                    description "Path to the results of the operation formatted as xpath.";
                }

                ///global-operations/md-cli-raw-command/output/results
                container results {
                    description "Enter the results context";

                    ///global-operations/md-cli-raw-command/output/results/md-cli-output-block
                    leaf md-cli-output-block {
                        type string;
                        description "Output of executed MD-CLI command.";
                    }

                } // container results

                ///global-operations/md-cli-raw-command/output/status
                leaf status {
                    type types-operation:operation-status;
                    description "Status of the operation";
                }

                ///global-operations/md-cli-raw-command/output/error-message
                leaf-list error-message {
                    type types-operation:operation-message;
                    description "Error messages reported during execution of the operation.";
                }

                ///global-operations/md-cli-raw-command/output/warning-message
                leaf-list warning-message {
                    type types-operation:operation-message;
                    description "Warning messages reported during execution of the operation.";
                }

                ///global-operations/md-cli-raw-command/output/info-message
                leaf-list info-message {
                    type types-operation:operation-message;
                    description "Info messages reported during execution of the operation.";
                }

                ///global-operations/md-cli-raw-command/output/end-time
                leaf end-time {
                    type types-operation:operation-timestamp;
                    description "Time when the operation ended its execution.";
                }

            }
        } // action md-cli-raw-command

        ///global-operations/md-compare
        action md-compare {
            description "Trigger md-compare command.";

            input {

                ///global-operations/md-compare/input/path
                container path {
                    description "This parameter contains the path to the target node to compare.";

                    ///global-operations/md-compare/input/path/path-type
                    choice path-type {
                        ///global-operations/md-compare/input/path/path-type/subtree-path
                        case subtree-path {

                            ///global-operations/md-compare/input/path/path-type/subtree-path/subtree-path
                            anyxml subtree-path {
                                description " The source datastore for the compare operation.";

                            } // anyxml subtree-path

                        }
                    }
                } // container path

                ///global-operations/md-compare/input/configuration-region
                leaf configuration-region {
                    type types-sros:configuration-region;
                    description "This parameter contains the configuration region to operate on.";
                }

                ///global-operations/md-compare/input/source
                container source {
                    description " The source datastore for the compare operation.";

                    ///global-operations/md-compare/input/source/destination-type
                    choice destination-type {
                        ///global-operations/md-compare/input/source/destination-type/candidate
                        case candidate {

                            ///global-operations/md-compare/input/source/destination-type/candidate/candidate
                            leaf candidate {
                                type empty;
                            }

                        }
                        ///global-operations/md-compare/input/source/destination-type/baseline
                        case baseline {

                            ///global-operations/md-compare/input/source/destination-type/baseline/baseline
                            leaf baseline {
                                type empty;
                            }

                        }
                        ///global-operations/md-compare/input/source/destination-type/url
                        case url {

                            ///global-operations/md-compare/input/source/destination-type/url/url
                            leaf url {
                                type string;
                            }

                        }
                        ///global-operations/md-compare/input/source/destination-type/running
                        case running {

                            ///global-operations/md-compare/input/source/destination-type/running/running
                            leaf running {
                                type empty;
                            }

                        }
                        ///global-operations/md-compare/input/source/destination-type/startup
                        case startup {

                            ///global-operations/md-compare/input/source/destination-type/startup/startup
                            leaf startup {
                                type empty;
                            }

                        }
                        ///global-operations/md-compare/input/source/destination-type/booted
                        case booted {

                            ///global-operations/md-compare/input/source/destination-type/booted/booted
                            leaf booted {
                                type empty;
                            }

                        }
                        ///global-operations/md-compare/input/source/destination-type/rollback
                        case rollback {
                            status obsolete;

                            ///global-operations/md-compare/input/source/destination-type/rollback/rollback
                            container rollback {
                                status obsolete;
                                description "Enter the rollback context";

                                ///global-operations/md-compare/input/source/destination-type/rollback/rollback/checkpoint-id
                                leaf checkpoint-id {
                                    status obsolete;
                                    type uint32;
                                }

                            } // container rollback

                        }
                        ///global-operations/md-compare/input/source/destination-type/rollback-id
                        case rollback-id {

                            ///global-operations/md-compare/input/source/destination-type/rollback-id/rollback-id
                            leaf rollback-id {
                                type uint32 {
                                    range "0..200";
                                }
                            }

                        }
                        ///global-operations/md-compare/input/source/destination-type/commit-id
                        case commit-id {

                            ///global-operations/md-compare/input/source/destination-type/commit-id/commit-id
                            leaf commit-id {
                                type uint32 {
                                    range "1..max";
                                }
                            }

                        }
                    }
                } // container source

                ///global-operations/md-compare/input/destination
                container destination {
                    description "The destination datastore for the compare operation.";

                    ///global-operations/md-compare/input/destination/destination-type
                    choice destination-type {
                        ///global-operations/md-compare/input/destination/destination-type/candidate
                        case candidate {

                            ///global-operations/md-compare/input/destination/destination-type/candidate/candidate
                            leaf candidate {
                                type empty;
                            }

                        }
                        ///global-operations/md-compare/input/destination/destination-type/baseline
                        case baseline {

                            ///global-operations/md-compare/input/destination/destination-type/baseline/baseline
                            leaf baseline {
                                type empty;
                            }

                        }
                        ///global-operations/md-compare/input/destination/destination-type/url
                        case url {

                            ///global-operations/md-compare/input/destination/destination-type/url/url
                            leaf url {
                                type string;
                            }

                        }
                        ///global-operations/md-compare/input/destination/destination-type/running
                        case running {

                            ///global-operations/md-compare/input/destination/destination-type/running/running
                            leaf running {
                                type empty;
                            }

                        }
                        ///global-operations/md-compare/input/destination/destination-type/startup
                        case startup {

                            ///global-operations/md-compare/input/destination/destination-type/startup/startup
                            leaf startup {
                                type empty;
                            }

                        }
                        ///global-operations/md-compare/input/destination/destination-type/booted
                        case booted {

                            ///global-operations/md-compare/input/destination/destination-type/booted/booted
                            leaf booted {
                                type empty;
                            }

                        }
                        ///global-operations/md-compare/input/destination/destination-type/rollback
                        case rollback {
                            status obsolete;

                            ///global-operations/md-compare/input/destination/destination-type/rollback/rollback
                            container rollback {
                                status obsolete;
                                description "Enter the rollback context";

                                ///global-operations/md-compare/input/destination/destination-type/rollback/rollback/checkpoint-id
                                leaf checkpoint-id {
                                    status obsolete;
                                    type uint32;
                                }

                            } // container rollback

                        }
                        ///global-operations/md-compare/input/destination/destination-type/rollback-id
                        case rollback-id {

                            ///global-operations/md-compare/input/destination/destination-type/rollback-id/rollback-id
                            leaf rollback-id {
                                type uint32 {
                                    range "0..200";
                                }
                            }

                        }
                        ///global-operations/md-compare/input/destination/destination-type/commit-id
                        case commit-id {

                            ///global-operations/md-compare/input/destination/destination-type/commit-id/commit-id
                            leaf commit-id {
                                type uint32 {
                                    range "1..max";
                                }
                            }

                        }
                    }
                } // container destination

                ///global-operations/md-compare/input/format
                leaf format {
                    type enumeration {
                        enum xml                            { value 0; }
                        enum md-cli                         { value 1; }
                    }
                    default "xml";
                    description "RPC output format tag.";
                }

            }
            output {

                ///global-operations/md-compare/output/operation-id
                leaf operation-id {
                    type types-operation:operation-id;
                    description "ID assigned to the operation.";
                }

                ///global-operations/md-compare/output/start-time
                leaf start-time {
                    type types-operation:operation-timestamp;
                    description "Time when the operation started its execution.";
                }

                ///global-operations/md-compare/output/results-path
                leaf results-path {
                    type types-operation:operation-path;
                    description "Path to the results of the operation formatted as xpath.";
                }

                ///global-operations/md-compare/output/results
                container results {
                    description "Enter the results context";

                    ///global-operations/md-compare/output/results/md-compare-output
                    leaf md-compare-output {
                        type string;
                        description "Output of executed md-compare command.";
                    }

                } // container results

                ///global-operations/md-compare/output/status
                leaf status {
                    type types-operation:operation-status;
                    description "Status of the operation";
                }

                ///global-operations/md-compare/output/error-message
                leaf-list error-message {
                    type types-operation:operation-message;
                    description "Error messages reported during execution of the operation.";
                }

                ///global-operations/md-compare/output/warning-message
                leaf-list warning-message {
                    type types-operation:operation-message;
                    description "Warning messages reported during execution of the operation.";
                }

                ///global-operations/md-compare/output/info-message
                leaf-list info-message {
                    type types-operation:operation-message;
                    description "Info messages reported during execution of the operation.";
                }

                ///global-operations/md-compare/output/end-time
                leaf end-time {
                    type types-operation:operation-timestamp;
                    description "Time when the operation ended its execution.";
                }

            }
        } // action md-compare

        ///global-operations/oam
        container oam {
            description "Enter the oam context for operations, administration and maintenance";

            ///global-operations/oam/eth-cfm
            container eth-cfm {
                description "Enter the Eth-CFM context";

                ///global-operations/oam/eth-cfm/linktrace
                action linktrace {
                    description "Initiate a linktrace test";

                    input {

                        ///global-operations/oam/eth-cfm/linktrace/input/asynchronous
                        leaf asynchronous {
                            type types-operation:operation-asynchronous;
                            description "Controls execution type of the operation.";
                        }

                        ///global-operations/oam/eth-cfm/linktrace/input/retention-timeout
                        leaf retention-timeout {
                            type types-operation:operation-timeout;
                            description "Timeout for operation data retention in global operation table.";
                        }

                        ///global-operations/oam/eth-cfm/linktrace/input/destination
                        leaf destination {
                            type union {
                                type types-sros:mac-unicast-address-no-zero;
                                type types-eth-cfm:mep-id-type;
                            }
                            mandatory true;
                            description "Destination MAC address or remote MEP ID of the peer";
                        }

                        ///global-operations/oam/eth-cfm/linktrace/input/md-admin-name
                        leaf md-admin-name {
                            type leafref {
                                path "/state:state/state:eth-cfm/state:domain/state:md-admin-name";
                            }
                            mandatory true;
                            description "Domain name";
                        }

                        ///global-operations/oam/eth-cfm/linktrace/input/ma-admin-name
                        leaf ma-admin-name {
                            type leafref {
                                path "/state:state/state:eth-cfm/state:domain[state:md-admin-name=current()/../md-admin-name]/state:association/state:ma-admin-name";
                            }
                            mandatory true;
                            description "Association name";
                        }

                        ///global-operations/oam/eth-cfm/linktrace/input/mep-id
                        leaf mep-id {
                            type types-eth-cfm:mep-id-type;
                            mandatory true;
                            description "Local Maintenance Association Endpoint (MEP) ID";
                        }

                        ///global-operations/oam/eth-cfm/linktrace/input/ttl
                        leaf ttl {
                            type uint32 {
                                range "0..255";
                            }
                            default "64";
                            description "Time to live for a returned linktrace";
                        }

                    }
                    output {

                        ///global-operations/oam/eth-cfm/linktrace/output/operation-id
                        leaf operation-id {
                            type types-operation:operation-id;
                            description "ID assigned to the operation.";
                        }

                        ///global-operations/oam/eth-cfm/linktrace/output/start-time
                        leaf start-time {
                            type types-operation:operation-timestamp;
                            description "Time when the operation started its execution.";
                        }

                        ///global-operations/oam/eth-cfm/linktrace/output/results-path
                        leaf results-path {
                            type types-operation:operation-path;
                            description "Path to the results of the operation formatted as xpath.";
                        }

                        ///global-operations/oam/eth-cfm/linktrace/output/status
                        leaf status {
                            type types-operation:operation-status;
                            description "Status of the operation";
                        }

                        ///global-operations/oam/eth-cfm/linktrace/output/error-message
                        leaf-list error-message {
                            type types-operation:operation-message;
                            description "Error messages reported during execution of the operation.";
                        }

                        ///global-operations/oam/eth-cfm/linktrace/output/warning-message
                        leaf-list warning-message {
                            type types-operation:operation-message;
                            description "Warning messages reported during execution of the operation.";
                        }

                        ///global-operations/oam/eth-cfm/linktrace/output/info-message
                        leaf-list info-message {
                            type types-operation:operation-message;
                            description "Info messages reported during execution of the operation.";
                        }

                        ///global-operations/oam/eth-cfm/linktrace/output/end-time
                        leaf end-time {
                            type types-operation:operation-timestamp;
                            description "Time when the operation ended its execution.";
                        }

                    }
                } // action linktrace

                ///global-operations/oam/eth-cfm/loopback
                action loopback {
                    description "Initiate a loopback test";

                    input {

                        ///global-operations/oam/eth-cfm/loopback/input/asynchronous
                        leaf asynchronous {
                            type types-operation:operation-asynchronous;
                            description "Controls execution type of the operation.";
                        }

                        ///global-operations/oam/eth-cfm/loopback/input/execution-timeout
                        leaf execution-timeout {
                            type types-operation:operation-timeout;
                            description "Timeout for operation execution.";
                        }

                        ///global-operations/oam/eth-cfm/loopback/input/retention-timeout
                        leaf retention-timeout {
                            type types-operation:operation-timeout;
                            description "Timeout for operation data retention in global operation table.";
                        }

                        ///global-operations/oam/eth-cfm/loopback/input/destination
                        leaf destination {
                            type union {
                                type types-sros:mac-unicast-address-no-zero;
                                type enumeration {
                                    enum multicast {
                                        value 0;
                                        description "Class one destination multicast address based on the level of the local MEP";
                                    }
                                }
                                type types-eth-cfm:mep-id-type;
                            }
                            mandatory true;
                            description "Destination MAC address or remote MEP ID of the peer";
                        }

                        ///global-operations/oam/eth-cfm/loopback/input/md-admin-name
                        leaf md-admin-name {
                            type leafref {
                                path "/state:state/state:eth-cfm/state:domain/state:md-admin-name";
                            }
                            mandatory true;
                            description "Domain name";
                        }

                        ///global-operations/oam/eth-cfm/loopback/input/ma-admin-name
                        leaf ma-admin-name {
                            type leafref {
                                path "/state:state/state:eth-cfm/state:domain[state:md-admin-name=current()/../md-admin-name]/state:association/state:ma-admin-name";
                            }
                            mandatory true;
                            description "Association name";
                        }

                        ///global-operations/oam/eth-cfm/loopback/input/mep-id
                        leaf mep-id {
                            type types-eth-cfm:mep-id-type;
                            mandatory true;
                            description "Local Maintenance Association Endpoint (MEP) ID";
                        }

                        ///global-operations/oam/eth-cfm/loopback/input/send-count
                        leaf send-count {
                            type int32 {
                                range "1..1024";
                            }
                            default "1";
                            description "Number of loopback messages to send";
                        }

                        ///global-operations/oam/eth-cfm/loopback/input/size
                        leaf size {
                            type uint32 {
                                range "0..1500";
                            }
                            units "bytes";
                            default "0";
                            description "Data portion size of the data TLV, octet string allowed";
                        }

                        ///global-operations/oam/eth-cfm/loopback/input/priority
                        leaf priority {
                            type int32 {
                                range "0..7";
                            }
                            description "Frame priority that can be manipulated by QoS policies";
                        }

                        ///global-operations/oam/eth-cfm/loopback/input/lbm-padding
                        leaf lbm-padding {
                            type uint32 {
                                range "0|3..9778";
                            }
                            default "0";
                            description "Data portion size of the data TLV, no octet string";
                        }

                        ///global-operations/oam/eth-cfm/loopback/input/timeout
                        leaf timeout {
                            type uint32 {
                                range "1..10";
                            }
                            units "seconds";
                            default "5";
                            description "Wait time for a reply to a sent message request";
                        }

                        ///global-operations/oam/eth-cfm/loopback/input/interval
                        leaf interval {
                            type uint32 {
                                range "0..600";
                            }
                            units "deciseconds";
                            default "0";
                            description "Time between probes within the test run";
                        }

                    }
                    output {

                        ///global-operations/oam/eth-cfm/loopback/output/operation-id
                        leaf operation-id {
                            type types-operation:operation-id;
                            description "ID assigned to the operation.";
                        }

                        ///global-operations/oam/eth-cfm/loopback/output/start-time
                        leaf start-time {
                            type types-operation:operation-timestamp;
                            description "Time when the operation started its execution.";
                        }

                        ///global-operations/oam/eth-cfm/loopback/output/results-path
                        leaf results-path {
                            type types-operation:operation-path;
                            description "Path to the results of the operation formatted as xpath.";
                        }

                        ///global-operations/oam/eth-cfm/loopback/output/status
                        leaf status {
                            type types-operation:operation-status;
                            description "Status of the operation";
                        }

                        ///global-operations/oam/eth-cfm/loopback/output/error-message
                        leaf-list error-message {
                            type types-operation:operation-message;
                            description "Error messages reported during execution of the operation.";
                        }

                        ///global-operations/oam/eth-cfm/loopback/output/warning-message
                        leaf-list warning-message {
                            type types-operation:operation-message;
                            description "Warning messages reported during execution of the operation.";
                        }

                        ///global-operations/oam/eth-cfm/loopback/output/info-message
                        leaf-list info-message {
                            type types-operation:operation-message;
                            description "Info messages reported during execution of the operation.";
                        }

                        ///global-operations/oam/eth-cfm/loopback/output/end-time
                        leaf end-time {
                            type types-operation:operation-timestamp;
                            description "Time when the operation ended its execution.";
                        }

                    }
                } // action loopback

            } // container eth-cfm

            ///global-operations/oam/lsp-ping
            container lsp-ping {
                description "Perform a Label Switched Path (LSP) ping test";

                ///global-operations/oam/lsp-ping/bgp-label
                action bgp-label {
                    description "Perform a BGP-label LSP trace test";

                    input {

                        ///global-operations/oam/lsp-ping/bgp-label/input/prefix
                        leaf prefix {
                            type types-sros:ip-prefix;
                            mandatory true;
                            description "Destination IP prefix for the test";
                        }

                        ///global-operations/oam/lsp-ping/bgp-label/input/path-destination
                        leaf path-destination {
                            type types-sros:ip-address;
                            description "IP address of the path destination";
                        }

                        ///global-operations/oam/lsp-ping/bgp-label/input/path-destination-egress
                        choice path-destination-egress {
                            ///global-operations/oam/lsp-ping/bgp-label/input/path-destination-egress/case-interface
                            case case-interface {

                                ///global-operations/oam/lsp-ping/bgp-label/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/bgp-label/input/path-destination-egress/case-next-hop
                            case case-next-hop {

                                ///global-operations/oam/lsp-ping/bgp-label/input/path-destination-egress/case-next-hop/next-hop
                                leaf next-hop {
                                    type types-sros:ip-address;
                                    description "Egress IP next hop address to use with path destination";
                                }

                            }
                        }
                        ///global-operations/oam/lsp-ping/bgp-label/input/source-ip-address
                        leaf source-ip-address {
                            type types-sros:ip-address;
                            description "Source IP address";
                        }

                        ///global-operations/oam/lsp-ping/bgp-label/input/interval
                        leaf interval {
                            type uint32 {
                                range "1..10";
                            }
                            units "seconds";
                            default "1";
                            description "Minimum time to expire before next echo request is sent";
                        }

                        ///global-operations/oam/lsp-ping/bgp-label/input/size
                        leaf size {
                            type uint32 {
                                range "1..9786";
                            }
                            units "bytes";
                            default "1";
                            description "Echo request packet pad size";
                        }

                        ///global-operations/oam/lsp-ping/bgp-label/input/fc
                        leaf fc {
                            type types-sros:fc-name;
                            default "be";
                            description "QoS forwarding class for the sent echo request packet";
                        }

                        ///global-operations/oam/lsp-ping/bgp-label/input/profile
                        leaf profile {
                            type types-qos:profile-in-out;
                            default "out";
                            description "QoS profile for the transmitted echo request packets";
                        }

                        ///global-operations/oam/lsp-ping/bgp-label/input/timeout
                        leaf timeout {
                            type uint32 {
                                range "1..10";
                            }
                            units "seconds";
                            default "5";
                            description "Time to wait for a reply after sending an echo request";
                        }

                        ///global-operations/oam/lsp-ping/bgp-label/input/ttl
                        leaf ttl {
                            type uint32 {
                                range "1..255";
                            }
                            default "255";
                            description "TTL value for the MPLS label of the echo request";
                        }

                        ///global-operations/oam/lsp-ping/bgp-label/input/send-count
                        leaf send-count {
                            type uint32 {
                                range "1..100";
                            }
                            units "packets";
                            default "1";
                            description "Number of echo request packets to send";
                        }

                    }
                    output {

                        ///global-operations/oam/lsp-ping/bgp-label/output/operation-id
                        leaf operation-id {
                            type types-operation:operation-id;
                            description "ID assigned to the operation.";
                        }

                        ///global-operations/oam/lsp-ping/bgp-label/output/start-time
                        leaf start-time {
                            type types-operation:operation-timestamp;
                            description "Time when the operation started its execution.";
                        }

                        ///global-operations/oam/lsp-ping/bgp-label/output/results-path
                        leaf results-path {
                            type types-operation:operation-path;
                            description "Path to the results of the operation formatted as xpath.";
                        }

                        ///global-operations/oam/lsp-ping/bgp-label/output/results
                        container results {
                            description "Enter the results context";

                            ///global-operations/oam/lsp-ping/bgp-label/output/results/test-parameters
                            container test-parameters {
                                description "Enter the test-parameters context";

                                ///global-operations/oam/lsp-ping/bgp-label/output/results/test-parameters/prefix
                                leaf prefix {
                                    type types-sros:ip-prefix;
                                    description "The destination IP prefix for the test";
                                }

                                ///global-operations/oam/lsp-ping/bgp-label/output/results/test-parameters/path-destination
                                leaf path-destination {
                                    type types-sros:ip-address;
                                    description "The IP address of the path destination";
                                }

                                ///global-operations/oam/lsp-ping/bgp-label/output/results/test-parameters/path-destination-egress
                                choice path-destination-egress {
                                    ///global-operations/oam/lsp-ping/bgp-label/output/results/test-parameters/path-destination-egress/case-interface
                                    case case-interface {

                                        ///global-operations/oam/lsp-ping/bgp-label/output/results/test-parameters/path-destination-egress/case-interface/interface
                                        leaf interface {
                                            type types-sros:interface-name;
                                            description "The egress router interface, used in conjunction with path-destination";
                                        }

                                    }
                                    ///global-operations/oam/lsp-ping/bgp-label/output/results/test-parameters/path-destination-egress/case-next-hop
                                    case case-next-hop {

                                        ///global-operations/oam/lsp-ping/bgp-label/output/results/test-parameters/path-destination-egress/case-next-hop/next-hop
                                        leaf next-hop {
                                            type types-sros:ip-address;
                                            description "The egress IP next hop address, used in conjunction with path-destination";
                                        }

                                    }
                                }
                                ///global-operations/oam/lsp-ping/bgp-label/output/results/test-parameters/source-ip-address
                                leaf source-ip-address {
                                    type types-sros:ip-address;
                                    description "Source IP address";
                                }

                                ///global-operations/oam/lsp-ping/bgp-label/output/results/test-parameters/interval
                                leaf interval {
                                    type uint32 {
                                        range "1..10";
                                    }
                                    units "seconds";
                                    description "Minimum time to expire before the next request is sent";
                                }

                                ///global-operations/oam/lsp-ping/bgp-label/output/results/test-parameters/size
                                leaf size {
                                    type uint32 {
                                        range "1..9786";
                                    }
                                    units "bytes";
                                    description "Packet pad size of request";
                                }

                                ///global-operations/oam/lsp-ping/bgp-label/output/results/test-parameters/fc
                                leaf fc {
                                    type types-sros:fc-name;
                                    description "QoS Forwarding Class for the transmitted request packet(s)";
                                }

                                ///global-operations/oam/lsp-ping/bgp-label/output/results/test-parameters/profile
                                leaf profile {
                                    type types-qos:profile-in-out;
                                    description "QoS profile for the transmitted request packet(s)";
                                }

                                ///global-operations/oam/lsp-ping/bgp-label/output/results/test-parameters/timeout
                                leaf timeout {
                                    type uint32 {
                                        range "1..10";
                                    }
                                    units "seconds";
                                    description "Time router waits for a reply after sending a request";
                                }

                                ///global-operations/oam/lsp-ping/bgp-label/output/results/test-parameters/ttl
                                leaf ttl {
                                    type uint32 {
                                        range "1..255";
                                    }
                                    description "TTL value for the request's MPLS label";
                                }

                                ///global-operations/oam/lsp-ping/bgp-label/output/results/test-parameters/send-count
                                leaf send-count {
                                    type uint32 {
                                        range "1..100";
                                    }
                                    units "packets";
                                    description "Number of request packets to send";
                                }

                            } // container test-parameters

                            ///global-operations/oam/lsp-ping/bgp-label/output/results/probe
                            list probe {
                                key "probe-index";
                                description "Probe data for the specified test run";

                                ///global-operations/oam/lsp-ping/bgp-label/output/results/probe/probe-index
                                leaf probe-index {
                                    type uint32 {
                                        range "1..max";
                                    }
                                    description "Probe index number";
                                }

                                ///global-operations/oam/lsp-ping/bgp-label/output/results/probe/egress-interface
                                leaf egress-interface {
                                    type types-sros:interface-name;
                                    description "Indicates the interface name this probe was transmitted from";
                                }

                                ///global-operations/oam/lsp-ping/bgp-label/output/results/probe/round-trip-time
                                leaf round-trip-time {
                                    type uint32;
                                    units "microseconds";
                                    description "Indicates the round trip time for the probe";
                                }

                                ///global-operations/oam/lsp-ping/bgp-label/output/results/probe/status
                                leaf status {
                                    type types-oam:response-status;
                                    description "Indicates the OAM response status code for the probe";
                                }

                                ///global-operations/oam/lsp-ping/bgp-label/output/results/probe/response-packet
                                container response-packet {
                                    description "Data from packet received as a response to the transmitted probe";

                                    ///global-operations/oam/lsp-ping/bgp-label/output/results/probe/response-packet/size
                                    leaf size {
                                        type uint32;
                                        units "bytes";
                                        description "Indicates the number of bytes in the response packet for the specified probe";
                                    }

                                    ///global-operations/oam/lsp-ping/bgp-label/output/results/probe/response-packet/source-address
                                    leaf source-address {
                                        type types-sros:ip-address;
                                        description "Indicates the source address in the response packet for the specified probe";
                                    }

                                    ///global-operations/oam/lsp-ping/bgp-label/output/results/probe/response-packet/sequence-number
                                    leaf sequence-number {
                                        type uint32;
                                        description
                                            "Indicates the sequence number in the response packet for the
                                             specified probe";
                                    }

                                    ///global-operations/oam/lsp-ping/bgp-label/output/results/probe/response-packet/return-code
                                    leaf return-code {
                                        type int32;
                                        description "Indicates the OAM return code received in the probe response";
                                    }

                                    ///global-operations/oam/lsp-ping/bgp-label/output/results/probe/response-packet/return-code-string
                                    leaf return-code-string {
                                        type types-oam:lsp-ping-trace-return-code;
                                        description "Description of the OAM return code";
                                    }

                                } // container response-packet

                            } // list probe

                            ///global-operations/oam/lsp-ping/bgp-label/output/results/summary
                            container summary {
                                description "Test run summary data";

                                ///global-operations/oam/lsp-ping/bgp-label/output/results/summary/statistics
                                container statistics {
                                    description "Test run summary statistics";

                                    ///global-operations/oam/lsp-ping/bgp-label/output/results/summary/statistics/packets
                                    container packets {
                                        description "Packet statistics for the specified test run";

                                        ///global-operations/oam/lsp-ping/bgp-label/output/results/summary/statistics/packets/sent
                                        leaf sent {
                                            type uint32;
                                            units "packets";
                                            description "Indicates the number of packets sent for the specified test run";
                                        }

                                        ///global-operations/oam/lsp-ping/bgp-label/output/results/summary/statistics/packets/received
                                        leaf received {
                                            type uint32;
                                            units "packets";
                                            description "Indicates the number of packets received for the specified test run";
                                        }

                                        ///global-operations/oam/lsp-ping/bgp-label/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/bgp-label/output/results/summary/statistics/round-trip-time
                                    container round-trip-time {
                                        description "Test run round trip time statistics";

                                        ///global-operations/oam/lsp-ping/bgp-label/output/results/summary/statistics/round-trip-time/minimum
                                        leaf minimum {
                                            type uint32;
                                            units "microseconds";
                                            description "Indicates the minimum round trip time for the specified test run";
                                        }

                                        ///global-operations/oam/lsp-ping/bgp-label/output/results/summary/statistics/round-trip-time/average
                                        leaf average {
                                            type uint32;
                                            units "microseconds";
                                            description "Indicates the average round trip time for the specified test run";
                                        }

                                        ///global-operations/oam/lsp-ping/bgp-label/output/results/summary/statistics/round-trip-time/maximum
                                        leaf maximum {
                                            type uint32;
                                            units "microseconds";
                                            description "Indicates the maximum round trip time for the specified test run";
                                        }

                                        ///global-operations/oam/lsp-ping/bgp-label/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/bgp-label/output/status
                        leaf status {
                            type types-operation:operation-status;
                            description "Status of the operation";
                        }

                        ///global-operations/oam/lsp-ping/bgp-label/output/error-message
                        leaf-list error-message {
                            type types-operation:operation-message;
                            description "Error messages reported during execution of the operation.";
                        }

                        ///global-operations/oam/lsp-ping/bgp-label/output/warning-message
                        leaf-list warning-message {
                            type types-operation:operation-message;
                            description "Warning messages reported during execution of the operation.";
                        }

                        ///global-operations/oam/lsp-ping/bgp-label/output/info-message
                        leaf-list info-message {
                            type types-operation:operation-message;
                            description "Info messages reported during execution of the operation.";
                        }

                        ///global-operations/oam/lsp-ping/bgp-label/output/end-time
                        leaf end-time {
                            type types-operation:operation-timestamp;
                            description "Time when the operation ended its execution.";
                        }

                    }
                } // action bgp-label

                ///global-operations/oam/lsp-ping/ldp
                action ldp {
                    description "Perform Label Distribution Protocal (LDP) LSP ping test";

                    input {

                        ///global-operations/oam/lsp-ping/ldp/input/prefix
                        leaf prefix {
                            type types-sros:ip-prefix;
                            mandatory true;
                            description "Destination IP prefix for the test";
                        }

                        ///global-operations/oam/lsp-ping/ldp/input/path-destination
                        leaf path-destination {
                            type types-sros:ip-address;
                            description "IP address of the path destination";
                        }

                        ///global-operations/oam/lsp-ping/ldp/input/path-destination-egress
                        choice path-destination-egress {
                            ///global-operations/oam/lsp-ping/ldp/input/path-destination-egress/case-interface
                            case case-interface {

                                ///global-operations/oam/lsp-ping/ldp/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/ldp/input/path-destination-egress/case-next-hop
                            case case-next-hop {

                                ///global-operations/oam/lsp-ping/ldp/input/path-destination-egress/case-next-hop/next-hop
                                leaf next-hop {
                                    type types-sros:ip-address;
                                    description "Egress IP next hop address to use with path destination";
                                }

                            }
                        }
                        ///global-operations/oam/lsp-ping/ldp/input/source-ip-address
                        leaf source-ip-address {
                            type types-sros:ip-address;
                            description "Source IP address";
                        }

                        ///global-operations/oam/lsp-ping/ldp/input/interval
                        leaf interval {
                            type uint32 {
                                range "1..10";
                            }
                            units "seconds";
                            default "1";
                            description "Minimum time to expire before next echo request is sent";
                        }

                        ///global-operations/oam/lsp-ping/ldp/input/size
                        leaf size {
                            type uint32 {
                                range "1..9786";
                            }
                            units "bytes";
                            default "1";
                            description "Echo request packet pad size";
                        }

                        ///global-operations/oam/lsp-ping/ldp/input/fc
                        leaf fc {
                            type types-sros:fc-name;
                            default "be";
                            description "QoS forwarding class for the sent echo request packet";
                        }

                        ///global-operations/oam/lsp-ping/ldp/input/profile
                        leaf profile {
                            type types-qos:profile-in-out;
                            default "out";
                            description "QoS profile for the transmitted echo request packets";
                        }

                        ///global-operations/oam/lsp-ping/ldp/input/timeout
                        leaf timeout {
                            type uint32 {
                                range "1..10";
                            }
                            units "seconds";
                            default "5";
                            description "Time to wait for a reply after sending an echo request";
                        }

                        ///global-operations/oam/lsp-ping/ldp/input/ttl
                        leaf ttl {
                            type uint32 {
                                range "1..255";
                            }
                            default "255";
                            description "TTL value for the MPLS label of the echo request";
                        }

                        ///global-operations/oam/lsp-ping/ldp/input/send-count
                        leaf send-count {
                            type uint32 {
                                range "1..100";
                            }
                            units "packets";
                            default "1";
                            description "Number of echo request packets to send";
                        }

                    }
                    output {

                        ///global-operations/oam/lsp-ping/ldp/output/operation-id
                        leaf operation-id {
                            type types-operation:operation-id;
                            description "ID assigned to the operation.";
                        }

                        ///global-operations/oam/lsp-ping/ldp/output/start-time
                        leaf start-time {
                            type types-operation:operation-timestamp;
                            description "Time when the operation started its execution.";
                        }

                        ///global-operations/oam/lsp-ping/ldp/output/results-path
                        leaf results-path {
                            type types-operation:operation-path;
                            description "Path to the results of the operation formatted as xpath.";
                        }

                        ///global-operations/oam/lsp-ping/ldp/output/results
                        container results {
                            description "Enter the results context";

                            ///global-operations/oam/lsp-ping/ldp/output/results/test-parameters
                            container test-parameters {
                                description "Enter the test-parameters context";

                                ///global-operations/oam/lsp-ping/ldp/output/results/test-parameters/prefix
                                leaf prefix {
                                    type types-sros:ip-prefix;
                                    description "The destination IP prefix for the test";
                                }

                                ///global-operations/oam/lsp-ping/ldp/output/results/test-parameters/path-destination
                                leaf path-destination {
                                    type types-sros:ip-address;
                                    description "The IP address of the path destination";
                                }

                                ///global-operations/oam/lsp-ping/ldp/output/results/test-parameters/path-destination-egress
                                choice path-destination-egress {
                                    ///global-operations/oam/lsp-ping/ldp/output/results/test-parameters/path-destination-egress/case-interface
                                    case case-interface {

                                        ///global-operations/oam/lsp-ping/ldp/output/results/test-parameters/path-destination-egress/case-interface/interface
                                        leaf interface {
                                            type types-sros:interface-name;
                                            description "The egress router interface, used in conjunction with path-destination";
                                        }

                                    }
                                    ///global-operations/oam/lsp-ping/ldp/output/results/test-parameters/path-destination-egress/case-next-hop
                                    case case-next-hop {

                                        ///global-operations/oam/lsp-ping/ldp/output/results/test-parameters/path-destination-egress/case-next-hop/next-hop
                                        leaf next-hop {
                                            type types-sros:ip-address;
                                            description "The egress IP next hop address, used in conjunction with path-destination";
                                        }

                                    }
                                }
                                ///global-operations/oam/lsp-ping/ldp/output/results/test-parameters/source-ip-address
                                leaf source-ip-address {
                                    type types-sros:ip-address;
                                    description "Source IP address";
                                }

                                ///global-operations/oam/lsp-ping/ldp/output/results/test-parameters/interval
                                leaf interval {
                                    type uint32 {
                                        range "1..10";
                                    }
                                    units "seconds";
                                    description "Minimum time to expire before the next request is sent";
                                }

                                ///global-operations/oam/lsp-ping/ldp/output/results/test-parameters/size
                                leaf size {
                                    type uint32 {
                                        range "1..9786";
                                    }
                                    units "bytes";
                                    description "Packet pad size of request";
                                }

                                ///global-operations/oam/lsp-ping/ldp/output/results/test-parameters/fc
                                leaf fc {
                                    type types-sros:fc-name;
                                    description "QoS Forwarding Class for the transmitted request packet(s)";
                                }

                                ///global-operations/oam/lsp-ping/ldp/output/results/test-parameters/profile
                                leaf profile {
                                    type types-qos:profile-in-out;
                                    description "QoS profile for the transmitted request packet(s)";
                                }

                                ///global-operations/oam/lsp-ping/ldp/output/results/test-parameters/timeout
                                leaf timeout {
                                    type uint32 {
                                        range "1..10";
                                    }
                                    units "seconds";
                                    description "Time router waits for a reply after sending a request";
                                }

                                ///global-operations/oam/lsp-ping/ldp/output/results/test-parameters/ttl
                                leaf ttl {
                                    type uint32 {
                                        range "1..255";
                                    }
                                    description "TTL value for the request's MPLS label";
                                }

                                ///global-operations/oam/lsp-ping/ldp/output/results/test-parameters/send-count
                                leaf send-count {
                                    type uint32 {
                                        range "1..100";
                                    }
                                    units "packets";
                                    description "Number of request packets to send";
                                }

                            } // container test-parameters

                            ///global-operations/oam/lsp-ping/ldp/output/results/probe
                            list probe {
                                key "probe-index";
                                description "Probe data for the specified test run";

                                ///global-operations/oam/lsp-ping/ldp/output/results/probe/probe-index
                                leaf probe-index {
                                    type uint32 {
                                        range "1..max";
                                    }
                                    description "Probe index number";
                                }

                                ///global-operations/oam/lsp-ping/ldp/output/results/probe/egress-interface
                                leaf egress-interface {
                                    type types-sros:interface-name;
                                    description "Indicates the interface name this probe was transmitted from";
                                }

                                ///global-operations/oam/lsp-ping/ldp/output/results/probe/round-trip-time
                                leaf round-trip-time {
                                    type uint32;
                                    units "microseconds";
                                    description "Indicates the round trip time for the probe";
                                }

                                ///global-operations/oam/lsp-ping/ldp/output/results/probe/status
                                leaf status {
                                    type types-oam:response-status;
                                    description "Indicates the OAM response status code for the probe";
                                }

                                ///global-operations/oam/lsp-ping/ldp/output/results/probe/response-packet
                                container response-packet {
                                    description "Data from packet received as a response to the transmitted probe";

                                    ///global-operations/oam/lsp-ping/ldp/output/results/probe/response-packet/size
                                    leaf size {
                                        type uint32;
                                        units "bytes";
                                        description "Indicates the number of bytes in the response packet for the specified probe";
                                    }

                                    ///global-operations/oam/lsp-ping/ldp/output/results/probe/response-packet/source-address
                                    leaf source-address {
                                        type types-sros:ip-address;
                                        description "Indicates the source address in the response packet for the specified probe";
                                    }

                                    ///global-operations/oam/lsp-ping/ldp/output/results/probe/response-packet/sequence-number
                                    leaf sequence-number {
                                        type uint32;
                                        description
                                            "Indicates the sequence number in the response packet for the
                                             specified probe";
                                    }

                                    ///global-operations/oam/lsp-ping/ldp/output/results/probe/response-packet/return-code
                                    leaf return-code {
                                        type int32;
                                        description "Indicates the OAM return code received in the probe response";
                                    }

                                    ///global-operations/oam/lsp-ping/ldp/output/results/probe/response-packet/return-code-string
                                    leaf return-code-string {
                                        type types-oam:lsp-ping-trace-return-code;
                                        description "Description of the OAM return code";
                                    }

                                } // container response-packet

                            } // list probe

                            ///global-operations/oam/lsp-ping/ldp/output/results/summary
                            container summary {
                                description "Test run summary data";

                                ///global-operations/oam/lsp-ping/ldp/output/results/summary/statistics
                                container statistics {
                                    description "Test run summary statistics";

                                    ///global-operations/oam/lsp-ping/ldp/output/results/summary/statistics/packets
                                    container packets {
                                        description "Packet statistics for the specified test run";

                                        ///global-operations/oam/lsp-ping/ldp/output/results/summary/statistics/packets/sent
                                        leaf sent {
                                            type uint32;
                                            units "packets";
                                            description "Indicates the number of packets sent for the specified test run";
                                        }

                                        ///global-operations/oam/lsp-ping/ldp/output/results/summary/statistics/packets/received
                                        leaf received {
                                            type uint32;
                                            units "packets";
                                            description "Indicates the number of packets received for the specified test run";
                                        }

                                        ///global-operations/oam/lsp-ping/ldp/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/ldp/output/results/summary/statistics/round-trip-time
                                    container round-trip-time {
                                        description "Test run round trip time statistics";

                                        ///global-operations/oam/lsp-ping/ldp/output/results/summary/statistics/round-trip-time/minimum
                                        leaf minimum {
                                            type uint32;
                                            units "microseconds";
                                            description "Indicates the minimum round trip time for the specified test run";
                                        }

                                        ///global-operations/oam/lsp-ping/ldp/output/results/summary/statistics/round-trip-time/average
                                        leaf average {
                                            type uint32;
                                            units "microseconds";
                                            description "Indicates the average round trip time for the specified test run";
                                        }

                                        ///global-operations/oam/lsp-ping/ldp/output/results/summary/statistics/round-trip-time/maximum
                                        leaf maximum {
                                            type uint32;
                                            units "microseconds";
                                            description "Indicates the maximum round trip time for the specified test run";
                                        }

                                        ///global-operations/oam/lsp-ping/ldp/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/ldp/output/status
                        leaf status {
                            type types-operation:operation-status;
                            description "Status of the operation";
                        }

                        ///global-operations/oam/lsp-ping/ldp/output/error-message
                        leaf-list error-message {
                            type types-operation:operation-message;
                            description "Error messages reported during execution of the operation.";
                        }

                        ///global-operations/oam/lsp-ping/ldp/output/warning-message
                        leaf-list warning-message {
                            type types-operation:operation-message;
                            description "Warning messages reported during execution of the operation.";
                        }

                        ///global-operations/oam/lsp-ping/ldp/output/info-message
                        leaf-list info-message {
                            type types-operation:operation-message;
                            description "Info messages reported during execution of the operation.";
                        }

                        ///global-operations/oam/lsp-ping/ldp/output/end-time
                        leaf end-time {
                            type types-operation:operation-timestamp;
                            description "Time when the operation ended its execution.";
                        }

                    }
                } // action ldp

                ///global-operations/oam/lsp-ping/rsvp-te
                action rsvp-te {
                    description "Perform an RSVP-TE LSP ping test";

                    input {

                        ///global-operations/oam/lsp-ping/rsvp-te/input/lsp-name
                        leaf lsp-name {
                            type leafref {
                                path "/state:state/state:router/state:mpls/state:lsp/state:lsp-name";
                                require-instance "false";
                            }
                            mandatory true;
                            description "Name of the LSP to test";
                        }

                        ///global-operations/oam/lsp-ping/rsvp-te/input/path
                        leaf path {
                            type leafref {
                                path "/state:state/state:router/state:mpls/state:path/state:path-name";
                                require-instance "false";
                            }
                            description "Name of the MPLS path to test";
                        }

                        ///global-operations/oam/lsp-ping/rsvp-te/input/source-ip-address
                        leaf source-ip-address {
                            type types-sros:ip-address;
                            description "Source IP address";
                        }

                        ///global-operations/oam/lsp-ping/rsvp-te/input/interval
                        leaf interval {
                            type uint32 {
                                range "1..10";
                            }
                            units "seconds";
                            default "1";
                            description "Minimum time to expire before next echo request is sent";
                        }

                        ///global-operations/oam/lsp-ping/rsvp-te/input/size
                        leaf size {
                            type uint32 {
                                range "1..9786";
                            }
                            units "bytes";
                            default "1";
                            description "Echo request packet pad size";
                        }

                        ///global-operations/oam/lsp-ping/rsvp-te/input/fc
                        leaf fc {
                            type types-sros:fc-name;
                            default "be";
                            description "QoS forwarding class for the sent echo request packet";
                        }

                        ///global-operations/oam/lsp-ping/rsvp-te/input/profile
                        leaf profile {
                            type types-qos:profile-in-out;
                            default "out";
                            description "QoS profile for the transmitted echo request packets";
                        }

                        ///global-operations/oam/lsp-ping/rsvp-te/input/timeout
                        leaf timeout {
                            type uint32 {
                                range "1..10";
                            }
                            units "seconds";
                            default "5";
                            description "Time to wait for a reply after sending an echo request";
                        }

                        ///global-operations/oam/lsp-ping/rsvp-te/input/ttl
                        leaf ttl {
                            type uint32 {
                                range "1..255";
                            }
                            default "255";
                            description "TTL value for the MPLS label of the echo request";
                        }

                        ///global-operations/oam/lsp-ping/rsvp-te/input/send-count
                        leaf send-count {
                            type uint32 {
                                range "1..100";
                            }
                            units "packets";
                            default "1";
                            description "Number of echo request packets to send";
                        }

                    }
                    output {

                        ///global-operations/oam/lsp-ping/rsvp-te/output/operation-id
                        leaf operation-id {
                            type types-operation:operation-id;
                            description "ID assigned to the operation.";
                        }

                        ///global-operations/oam/lsp-ping/rsvp-te/output/start-time
                        leaf start-time {
                            type types-operation:operation-timestamp;
                            description "Time when the operation started its execution.";
                        }

                        ///global-operations/oam/lsp-ping/rsvp-te/output/results-path
                        leaf results-path {
                            type types-operation:operation-path;
                            description "Path to the results of the operation formatted as xpath.";
                        }

                        ///global-operations/oam/lsp-ping/rsvp-te/output/results
                        container results {
                            description "Enter the results context";

                            ///global-operations/oam/lsp-ping/rsvp-te/output/results/test-parameters
                            container test-parameters {
                                description "Enter the test-parameters context";

                                ///global-operations/oam/lsp-ping/rsvp-te/output/results/test-parameters/lsp-name
                                leaf lsp-name {
                                    type types-sros:named-item-64;
                                    description "The name of the LSP to be tested";
                                }

                                ///global-operations/oam/lsp-ping/rsvp-te/output/results/test-parameters/path
                                leaf path {
                                    type types-sros:named-item-64;
                                    description "The name of the MPLS path to be tested";
                                }

                                ///global-operations/oam/lsp-ping/rsvp-te/output/results/test-parameters/source-ip-address
                                leaf source-ip-address {
                                    type types-sros:ip-address;
                                    description "Source IP address";
                                }

                                ///global-operations/oam/lsp-ping/rsvp-te/output/results/test-parameters/interval
                                leaf interval {
                                    type uint32 {
                                        range "1..10";
                                    }
                                    units "seconds";
                                    description "Minimum time to expire before the next request is sent";
                                }

                                ///global-operations/oam/lsp-ping/rsvp-te/output/results/test-parameters/size
                                leaf size {
                                    type uint32 {
                                        range "1..9786";
                                    }
                                    units "bytes";
                                    description "Packet pad size of request";
                                }

                                ///global-operations/oam/lsp-ping/rsvp-te/output/results/test-parameters/fc
                                leaf fc {
                                    type types-sros:fc-name;
                                    description "QoS Forwarding Class for the transmitted request packet(s)";
                                }

                                ///global-operations/oam/lsp-ping/rsvp-te/output/results/test-parameters/profile
                                leaf profile {
                                    type types-qos:profile-in-out;
                                    description "QoS profile for the transmitted request packet(s)";
                                }

                                ///global-operations/oam/lsp-ping/rsvp-te/output/results/test-parameters/timeout
                                leaf timeout {
                                    type uint32 {
                                        range "1..10";
                                    }
                                    units "seconds";
                                    description "Time router waits for a reply after sending a request";
                                }

                                ///global-operations/oam/lsp-ping/rsvp-te/output/results/test-parameters/ttl
                                leaf ttl {
                                    type uint32 {
                                        range "1..255";
                                    }
                                    description "TTL value for the request's MPLS label";
                                }

                                ///global-operations/oam/lsp-ping/rsvp-te/output/results/test-parameters/send-count
                                leaf send-count {
                                    type uint32 {
                                        range "1..100";
                                    }
                                    units "packets";
                                    description "Number of request packets to send";
                                }

                            } // container test-parameters

                            ///global-operations/oam/lsp-ping/rsvp-te/output/results/probe
                            list probe {
                                key "probe-index";
                                description "Probe data for the specified test run";

                                ///global-operations/oam/lsp-ping/rsvp-te/output/results/probe/probe-index
                                leaf probe-index {
                                    type uint32 {
                                        range "1..max";
                                    }
                                    description "Probe index number";
                                }

                                ///global-operations/oam/lsp-ping/rsvp-te/output/results/probe/egress-interface
                                leaf egress-interface {
                                    type types-sros:interface-name;
                                    description "Indicates the interface name this probe was transmitted from";
                                }

                                ///global-operations/oam/lsp-ping/rsvp-te/output/results/probe/round-trip-time
                                leaf round-trip-time {
                                    type uint32;
                                    units "microseconds";
                                    description "Indicates the round trip time for the probe";
                                }

                                ///global-operations/oam/lsp-ping/rsvp-te/output/results/probe/status
                                leaf status {
                                    type types-oam:response-status;
                                    description "Indicates the OAM response status code for the probe";
                                }

                                ///global-operations/oam/lsp-ping/rsvp-te/output/results/probe/response-packet
                                container response-packet {
                                    description "Data from packet received as a response to the transmitted probe";

                                    ///global-operations/oam/lsp-ping/rsvp-te/output/results/probe/response-packet/size
                                    leaf size {
                                        type uint32;
                                        units "bytes";
                                        description "Indicates the number of bytes in the response packet for the specified probe";
                                    }

                                    ///global-operations/oam/lsp-ping/rsvp-te/output/results/probe/response-packet/source-address
                                    leaf source-address {
                                        type types-sros:ip-address;
                                        description "Indicates the source address in the response packet for the specified probe";
                                    }

                                    ///global-operations/oam/lsp-ping/rsvp-te/output/results/probe/response-packet/sequence-number
                                    leaf sequence-number {
                                        type uint32;
                                        description
                                            "Indicates the sequence number in the response packet for the
                                             specified probe";
                                    }

                                    ///global-operations/oam/lsp-ping/rsvp-te/output/results/probe/response-packet/return-code
                                    leaf return-code {
                                        type int32;
                                        description "Indicates the OAM return code received in the probe response";
                                    }

                                    ///global-operations/oam/lsp-ping/rsvp-te/output/results/probe/response-packet/return-code-string
                                    leaf return-code-string {
                                        type types-oam:lsp-ping-trace-return-code;
                                        description "Description of the OAM return code";
                                    }

                                } // container response-packet

                            } // list probe

                            ///global-operations/oam/lsp-ping/rsvp-te/output/results/summary
                            container summary {
                                description "Test run summary data";

                                ///global-operations/oam/lsp-ping/rsvp-te/output/results/summary/statistics
                                container statistics {
                                    description "Test run summary statistics";

                                    ///global-operations/oam/lsp-ping/rsvp-te/output/results/summary/statistics/packets
                                    container packets {
                                        description "Packet statistics for the specified test run";

                                        ///global-operations/oam/lsp-ping/rsvp-te/output/results/summary/statistics/packets/sent
                                        leaf sent {
                                            type uint32;
                                            units "packets";
                                            description "Indicates the number of packets sent for the specified test run";
                                        }

                                        ///global-operations/oam/lsp-ping/rsvp-te/output/results/summary/statistics/packets/received
                                        leaf received {
                                            type uint32;
                                            units "packets";
                                            description "Indicates the number of packets received for the specified test run";
                                        }

                                        ///global-operations/oam/lsp-ping/rsvp-te/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/rsvp-te/output/results/summary/statistics/round-trip-time
                                    container round-trip-time {
                                        description "Test run round trip time statistics";

                                        ///global-operations/oam/lsp-ping/rsvp-te/output/results/summary/statistics/round-trip-time/minimum
                                        leaf minimum {
                                            type uint32;
                                            units "microseconds";
                                            description "Indicates the minimum round trip time for the specified test run";
                                        }

                                        ///global-operations/oam/lsp-ping/rsvp-te/output/results/summary/statistics/round-trip-time/average
                                        leaf average {
                                            type uint32;
                                            units "microseconds";
                                            description "Indicates the average round trip time for the specified test run";
                                        }

                                        ///global-operations/oam/lsp-ping/rsvp-te/output/results/summary/statistics/round-trip-time/maximum
                                        leaf maximum {
                                            type uint32;
                                            units "microseconds";
                                            description "Indicates the maximum round trip time for the specified test run";
                                        }

                                        ///global-operations/oam/lsp-ping/rsvp-te/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/rsvp-te/output/status
                        leaf status {
                            type types-operation:operation-status;
                            description "Status of the operation";
                        }

                        ///global-operations/oam/lsp-ping/rsvp-te/output/error-message
                        leaf-list error-message {
                            type types-operation:operation-message;
                            description "Error messages reported during execution of the operation.";
                        }

                        ///global-operations/oam/lsp-ping/rsvp-te/output/warning-message
                        leaf-list warning-message {
                            type types-operation:operation-message;
                            description "Warning messages reported during execution of the operation.";
                        }

                        ///global-operations/oam/lsp-ping/rsvp-te/output/info-message
                        leaf-list info-message {
                            type types-operation:operation-message;
                            description "Info messages reported during execution of the operation.";
                        }

                        ///global-operations/oam/lsp-ping/rsvp-te/output/end-time
                        leaf end-time {
                            type types-operation:operation-timestamp;
                            description "Time when the operation ended its execution.";
                        }

                    }
                } // action rsvp-te

                ///global-operations/oam/lsp-ping/sr-isis
                action sr-isis {
                    description "Perform an SR-ISIS LSP ping test";

                    input {

                        ///global-operations/oam/lsp-ping/sr-isis/input/prefix
                        leaf prefix {
                            type types-sros:ip-prefix;
                            mandatory true;
                            description "Destination IP prefix for the test";
                        }

                        ///global-operations/oam/lsp-ping/sr-isis/input/igp-instance
                        leaf igp-instance {
                            type uint32 {
                                range "0..127";
                            }
                            default "0";
                            description "IGP instance for the SR-ISIS test";
                        }

                        ///global-operations/oam/lsp-ping/sr-isis/input/flex-algo
                        leaf flex-algo {
                            type uint32 {
                                range "128..255";
                            }
                            description "Segment Routing Flexible Algorithm for the test";
                        }

                        ///global-operations/oam/lsp-ping/sr-isis/input/path-destination
                        leaf path-destination {
                            type types-sros:ip-address;
                            description "IP address of the path destination";
                        }

                        ///global-operations/oam/lsp-ping/sr-isis/input/path-destination-egress
                        choice path-destination-egress {
                            ///global-operations/oam/lsp-ping/sr-isis/input/path-destination-egress/case-interface
                            case case-interface {

                                ///global-operations/oam/lsp-ping/sr-isis/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/sr-isis/input/path-destination-egress/case-next-hop
                            case case-next-hop {

                                ///global-operations/oam/lsp-ping/sr-isis/input/path-destination-egress/case-next-hop/next-hop
                                leaf next-hop {
                                    type types-sros:ip-address;
                                    description "Egress IP next hop address to use with path destination";
                                }

                            }
                        }
                        ///global-operations/oam/lsp-ping/sr-isis/input/source-ip-address
                        leaf source-ip-address {
                            type types-sros:ip-address;
                            description "Source IP address";
                        }

                        ///global-operations/oam/lsp-ping/sr-isis/input/interval
                        leaf interval {
                            type uint32 {
                                range "1..10";
                            }
                            units "seconds";
                            default "1";
                            description "Minimum time to expire before next echo request is sent";
                        }

                        ///global-operations/oam/lsp-ping/sr-isis/input/size
                        leaf size {
                            type uint32 {
                                range "1..9786";
                            }
                            units "bytes";
                            default "1";
                            description "Echo request packet pad size";
                        }

                        ///global-operations/oam/lsp-ping/sr-isis/input/fc
                        leaf fc {
                            type types-sros:fc-name;
                            default "be";
                            description "QoS forwarding class for the sent echo request packet";
                        }

                        ///global-operations/oam/lsp-ping/sr-isis/input/profile
                        leaf profile {
                            type types-qos:profile-in-out;
                            default "out";
                            description "QoS profile for the transmitted echo request packets";
                        }

                        ///global-operations/oam/lsp-ping/sr-isis/input/timeout
                        leaf timeout {
                            type uint32 {
                                range "1..10";
                            }
                            units "seconds";
                            default "5";
                            description "Time to wait for a reply after sending an echo request";
                        }

                        ///global-operations/oam/lsp-ping/sr-isis/input/ttl
                        leaf ttl {
                            type uint32 {
                                range "1..255";
                            }
                            default "255";
                            description "TTL value for the MPLS label of the echo request";
                        }

                        ///global-operations/oam/lsp-ping/sr-isis/input/send-count
                        leaf send-count {
                            type uint32 {
                                range "1..100";
                            }
                            units "packets";
                            default "1";
                            description "Number of echo request packets to send";
                        }

                    }
                    output {

                        ///global-operations/oam/lsp-ping/sr-isis/output/operation-id
                        leaf operation-id {
                            type types-operation:operation-id;
                            description "ID assigned to the operation.";
                        }

                        ///global-operations/oam/lsp-ping/sr-isis/output/start-time
                        leaf start-time {
                            type types-operation:operation-timestamp;
                            description "Time when the operation started its execution.";
                        }

                        ///global-operations/oam/lsp-ping/sr-isis/output/results-path
                        leaf results-path {
                            type types-operation:operation-path;
                            description "Path to the results of the operation formatted as xpath.";
                        }

                        ///global-operations/oam/lsp-ping/sr-isis/output/results
                        container results {
                            description "Enter the results context";

                            ///global-operations/oam/lsp-ping/sr-isis/output/results/test-parameters
                            container test-parameters {
                                description "Enter the test-parameters context";

                                ///global-operations/oam/lsp-ping/sr-isis/output/results/test-parameters/prefix
                                leaf prefix {
                                    type types-sros:ip-prefix;
                                    description "The destination IP prefix for the test";
                                }

                                ///global-operations/oam/lsp-ping/sr-isis/output/results/test-parameters/igp-instance
                                leaf igp-instance {
                                    type uint32 {
                                        range "0..127";
                                    }
                                    description "The IGP instance for the test";
                                }

                                ///global-operations/oam/lsp-ping/sr-isis/output/results/test-parameters/flex-algo
                                leaf flex-algo {
                                    type uint32 {
                                        range "128..255";
                                    }
                                    description "Segment Routing Flexible Algorithm for the test";
                                }

                                ///global-operations/oam/lsp-ping/sr-isis/output/results/test-parameters/path-destination
                                leaf path-destination {
                                    type types-sros:ip-address;
                                    description "The IP address of the path destination";
                                }

                                ///global-operations/oam/lsp-ping/sr-isis/output/results/test-parameters/path-destination-egress
                                choice path-destination-egress {
                                    ///global-operations/oam/lsp-ping/sr-isis/output/results/test-parameters/path-destination-egress/case-interface
                                    case case-interface {

                                        ///global-operations/oam/lsp-ping/sr-isis/output/results/test-parameters/path-destination-egress/case-interface/interface
                                        leaf interface {
                                            type types-sros:interface-name;
                                            description "The egress router interface, used in conjunction with path-destination";
                                        }

                                    }
                                    ///global-operations/oam/lsp-ping/sr-isis/output/results/test-parameters/path-destination-egress/case-next-hop
                                    case case-next-hop {

                                        ///global-operations/oam/lsp-ping/sr-isis/output/results/test-parameters/path-destination-egress/case-next-hop/next-hop
                                        leaf next-hop {
                                            type types-sros:ip-address;
                                            description "The egress IP next hop address, used in conjunction with path-destination";
                                        }

                                    }
                                }
                                ///global-operations/oam/lsp-ping/sr-isis/output/results/test-parameters/source-ip-address
                                leaf source-ip-address {
                                    type types-sros:ip-address;
                                    description "Source IP address";
                                }

                                ///global-operations/oam/lsp-ping/sr-isis/output/results/test-parameters/interval
                                leaf interval {
                                    type uint32 {
                                        range "1..10";
                                    }
                                    units "seconds";
                                    description "Minimum time to expire before the next request is sent";
                                }

                                ///global-operations/oam/lsp-ping/sr-isis/output/results/test-parameters/size
                                leaf size {
                                    type uint32 {
                                        range "1..9786";
                                    }
                                    units "bytes";
                                    description "Packet pad size of request";
                                }

                                ///global-operations/oam/lsp-ping/sr-isis/output/results/test-parameters/fc
                                leaf fc {
                                    type types-sros:fc-name;
                                    description "QoS Forwarding Class for the transmitted request packet(s)";
                                }

                                ///global-operations/oam/lsp-ping/sr-isis/output/results/test-parameters/profile
                                leaf profile {
                                    type types-qos:profile-in-out;
                                    description "QoS profile for the transmitted request packet(s)";
                                }

                                ///global-operations/oam/lsp-ping/sr-isis/output/results/test-parameters/timeout
                                leaf timeout {
                                    type uint32 {
                                        range "1..10";
                                    }
                                    units "seconds";
                                    description "Time router waits for a reply after sending a request";
                                }

                                ///global-operations/oam/lsp-ping/sr-isis/output/results/test-parameters/ttl
                                leaf ttl {
                                    type uint32 {
                                        range "1..255";
                                    }
                                    description "TTL value for the request's MPLS label";
                                }

                                ///global-operations/oam/lsp-ping/sr-isis/output/results/test-parameters/send-count
                                leaf send-count {
                                    type uint32 {
                                        range "1..100";
                                    }
                                    units "packets";
                                    description "Number of request packets to send";
                                }

                            } // container test-parameters

                            ///global-operations/oam/lsp-ping/sr-isis/output/results/probe
                            list probe {
                                key "probe-index";
                                description "Probe data for the specified test run";

                                ///global-operations/oam/lsp-ping/sr-isis/output/results/probe/probe-index
                                leaf probe-index {
                                    type uint32 {
                                        range "1..max";
                                    }
                                    description "Probe index number";
                                }

                                ///global-operations/oam/lsp-ping/sr-isis/output/results/probe/egress-interface
                                leaf egress-interface {
                                    type types-sros:interface-name;
                                    description "Indicates the interface name this probe was transmitted from";
                                }

                                ///global-operations/oam/lsp-ping/sr-isis/output/results/probe/round-trip-time
                                leaf round-trip-time {
                                    type uint32;
                                    units "microseconds";
                                    description "Indicates the round trip time for the probe";
                                }

                                ///global-operations/oam/lsp-ping/sr-isis/output/results/probe/status
                                leaf status {
                                    type types-oam:response-status;
                                    description "Indicates the OAM response status code for the probe";
                                }

                                ///global-operations/oam/lsp-ping/sr-isis/output/results/probe/response-packet
                                container response-packet {
                                    description "Data from packet received as a response to the transmitted probe";

                                    ///global-operations/oam/lsp-ping/sr-isis/output/results/probe/response-packet/size
                                    leaf size {
                                        type uint32;
                                        units "bytes";
                                        description "Indicates the number of bytes in the response packet for the specified probe";
                                    }

                                    ///global-operations/oam/lsp-ping/sr-isis/output/results/probe/response-packet/source-address
                                    leaf source-address {
                                        type types-sros:ip-address;
                                        description "Indicates the source address in the response packet for the specified probe";
                                    }

                                    ///global-operations/oam/lsp-ping/sr-isis/output/results/probe/response-packet/sequence-number
                                    leaf sequence-number {
                                        type uint32;
                                        description
                                            "Indicates the sequence number in the response packet for the
                                             specified probe";
                                    }

                                    ///global-operations/oam/lsp-ping/sr-isis/output/results/probe/response-packet/return-code
                                    leaf return-code {
                                        type int32;
                                        description "Indicates the OAM return code received in the probe response";
                                    }

                                    ///global-operations/oam/lsp-ping/sr-isis/output/results/probe/response-packet/return-code-string
                                    leaf return-code-string {
                                        type types-oam:lsp-ping-trace-return-code;
                                        description "Description of the OAM return code";
                                    }

                                } // container response-packet

                            } // list probe

                            ///global-operations/oam/lsp-ping/sr-isis/output/results/summary
                            container summary {
                                description "Test run summary data";

                                ///global-operations/oam/lsp-ping/sr-isis/output/results/summary/statistics
                                container statistics {
                                    description "Test run summary statistics";

                                    ///global-operations/oam/lsp-ping/sr-isis/output/results/summary/statistics/packets
                                    container packets {
                                        description "Packet statistics for the specified test run";

                                        ///global-operations/oam/lsp-ping/sr-isis/output/results/summary/statistics/packets/sent
                                        leaf sent {
                                            type uint32;
                                            units "packets";
                                            description "Indicates the number of packets sent for the specified test run";
                                        }

                                        ///global-operations/oam/lsp-ping/sr-isis/output/results/summary/statistics/packets/received
                                        leaf received {
                                            type uint32;
                                            units "packets";
                                            description "Indicates the number of packets received for the specified test run";
                                        }

                                        ///global-operations/oam/lsp-ping/sr-isis/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/sr-isis/output/results/summary/statistics/round-trip-time
                                    container round-trip-time {
                                        description "Test run round trip time statistics";

                                        ///global-operations/oam/lsp-ping/sr-isis/output/results/summary/statistics/round-trip-time/minimum
                                        leaf minimum {
                                            type uint32;
                                            units "microseconds";
                                            description "Indicates the minimum round trip time for the specified test run";
                                        }

                                        ///global-operations/oam/lsp-ping/sr-isis/output/results/summary/statistics/round-trip-time/average
                                        leaf average {
                                            type uint32;
                                            units "microseconds";
                                            description "Indicates the average round trip time for the specified test run";
                                        }

                                        ///global-operations/oam/lsp-ping/sr-isis/output/results/summary/statistics/round-trip-time/maximum
                                        leaf maximum {
                                            type uint32;
                                            units "microseconds";
                                            description "Indicates the maximum round trip time for the specified test run";
                                        }

                                        ///global-operations/oam/lsp-ping/sr-isis/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/sr-isis/output/status
                        leaf status {
                            type types-operation:operation-status;
                            description "Status of the operation";
                        }

                        ///global-operations/oam/lsp-ping/sr-isis/output/error-message
                        leaf-list error-message {
                            type types-operation:operation-message;
                            description "Error messages reported during execution of the operation.";
                        }

                        ///global-operations/oam/lsp-ping/sr-isis/output/warning-message
                        leaf-list warning-message {
                            type types-operation:operation-message;
                            description "Warning messages reported during execution of the operation.";
                        }

                        ///global-operations/oam/lsp-ping/sr-isis/output/info-message
                        leaf-list info-message {
                            type types-operation:operation-message;
                            description "Info messages reported during execution of the operation.";
                        }

                        ///global-operations/oam/lsp-ping/sr-isis/output/end-time
                        leaf end-time {
                            type types-operation:operation-timestamp;
                            description "Time when the operation ended its execution.";
                        }

                    }
                } // action sr-isis

                ///global-operations/oam/lsp-ping/sr-ospf
                action sr-ospf {
                    description "Perform an SR-OSPF LSP ping test";

                    input {

                        ///global-operations/oam/lsp-ping/sr-ospf/input/prefix
                        leaf prefix {
                            type types-sros:ip-prefix;
                            mandatory true;
                            description "Destination IP prefix for the test";
                        }

                        ///global-operations/oam/lsp-ping/sr-ospf/input/igp-instance
                        leaf igp-instance {
                            type uint32 {
                                range "0..31";
                            }
                            default "0";
                            description "IGP instance for the SR-OSPF test";
                        }

                        ///global-operations/oam/lsp-ping/sr-ospf/input/flex-algo
                        leaf flex-algo {
                            type uint32 {
                                range "128..255";
                            }
                            description "Segment Routing Flexible Algorithm for the test";
                        }

                        ///global-operations/oam/lsp-ping/sr-ospf/input/path-destination
                        leaf path-destination {
                            type types-sros:ipv4-address;
                            description "IP address of the path destination";
                        }

                        ///global-operations/oam/lsp-ping/sr-ospf/input/path-destination-egress
                        choice path-destination-egress {
                            ///global-operations/oam/lsp-ping/sr-ospf/input/path-destination-egress/case-interface
                            case case-interface {

                                ///global-operations/oam/lsp-ping/sr-ospf/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/sr-ospf/input/path-destination-egress/case-next-hop
                            case case-next-hop {

                                ///global-operations/oam/lsp-ping/sr-ospf/input/path-destination-egress/case-next-hop/next-hop
                                leaf next-hop {
                                    type types-sros:ipv4-address;
                                    description "Egress IP next hop address to use with path destination";
                                }

                            }
                        }
                        ///global-operations/oam/lsp-ping/sr-ospf/input/source-ip-address
                        leaf source-ip-address {
                            type types-sros:ipv4-address;
                            description "Source IP address";
                        }

                        ///global-operations/oam/lsp-ping/sr-ospf/input/interval
                        leaf interval {
                            type uint32 {
                                range "1..10";
                            }
                            units "seconds";
                            default "1";
                            description "Minimum time to expire before next echo request is sent";
                        }

                        ///global-operations/oam/lsp-ping/sr-ospf/input/size
                        leaf size {
                            type uint32 {
                                range "1..9786";
                            }
                            units "bytes";
                            default "1";
                            description "Echo request packet pad size";
                        }

                        ///global-operations/oam/lsp-ping/sr-ospf/input/fc
                        leaf fc {
                            type types-sros:fc-name;
                            default "be";
                            description "QoS forwarding class for the sent echo request packet";
                        }

                        ///global-operations/oam/lsp-ping/sr-ospf/input/profile
                        leaf profile {
                            type types-qos:profile-in-out;
                            default "out";
                            description "QoS profile for the transmitted echo request packets";
                        }

                        ///global-operations/oam/lsp-ping/sr-ospf/input/timeout
                        leaf timeout {
                            type uint32 {
                                range "1..10";
                            }
                            units "seconds";
                            default "5";
                            description "Time to wait for a reply after sending an echo request";
                        }

                        ///global-operations/oam/lsp-ping/sr-ospf/input/ttl
                        leaf ttl {
                            type uint32 {
                                range "1..255";
                            }
                            default "255";
                            description "TTL value for the MPLS label of the echo request";
                        }

                        ///global-operations/oam/lsp-ping/sr-ospf/input/send-count
                        leaf send-count {
                            type uint32 {
                                range "1..100";
                            }
                            units "packets";
                            default "1";
                            description "Number of echo request packets to send";
                        }

                    }
                    output {

                        ///global-operations/oam/lsp-ping/sr-ospf/output/operation-id
                        leaf operation-id {
                            type types-operation:operation-id;
                            description "ID assigned to the operation.";
                        }

                        ///global-operations/oam/lsp-ping/sr-ospf/output/start-time
                        leaf start-time {
                            type types-operation:operation-timestamp;
                            description "Time when the operation started its execution.";
                        }

                        ///global-operations/oam/lsp-ping/sr-ospf/output/results-path
                        leaf results-path {
                            type types-operation:operation-path;
                            description "Path to the results of the operation formatted as xpath.";
                        }

                        ///global-operations/oam/lsp-ping/sr-ospf/output/results
                        container results {
                            description "Enter the results context";

                            ///global-operations/oam/lsp-ping/sr-ospf/output/results/test-parameters
                            container test-parameters {
                                description "Enter the test-parameters context";

                                ///global-operations/oam/lsp-ping/sr-ospf/output/results/test-parameters/prefix
                                leaf prefix {
                                    type types-sros:ip-prefix;
                                    description "The destination IP prefix for the test";
                                }

                                ///global-operations/oam/lsp-ping/sr-ospf/output/results/test-parameters/igp-instance
                                leaf igp-instance {
                                    type uint32 {
                                        range "0..127";
                                    }
                                    description "The IGP instance for the test";
                                }

                                ///global-operations/oam/lsp-ping/sr-ospf/output/results/test-parameters/flex-algo
                                leaf flex-algo {
                                    type uint32 {
                                        range "128..255";
                                    }
                                    description "Segment Routing Flexible Algorithm for the test";
                                }

                                ///global-operations/oam/lsp-ping/sr-ospf/output/results/test-parameters/path-destination
                                leaf path-destination {
                                    type types-sros:ip-address;
                                    description "The IP address of the path destination";
                                }

                                ///global-operations/oam/lsp-ping/sr-ospf/output/results/test-parameters/path-destination-egress
                                choice path-destination-egress {
                                    ///global-operations/oam/lsp-ping/sr-ospf/output/results/test-parameters/path-destination-egress/case-interface
                                    case case-interface {

                                        ///global-operations/oam/lsp-ping/sr-ospf/output/results/test-parameters/path-destination-egress/case-interface/interface
                                        leaf interface {
                                            type types-sros:interface-name;
                                            description "The egress router interface, used in conjunction with path-destination";
                                        }

                                    }
                                    ///global-operations/oam/lsp-ping/sr-ospf/output/results/test-parameters/path-destination-egress/case-next-hop
                                    case case-next-hop {

                                        ///global-operations/oam/lsp-ping/sr-ospf/output/results/test-parameters/path-destination-egress/case-next-hop/next-hop
                                        leaf next-hop {
                                            type types-sros:ip-address;
                                            description "The egress IP next hop address, used in conjunction with path-destination";
                                        }

                                    }
                                }
                                ///global-operations/oam/lsp-ping/sr-ospf/output/results/test-parameters/source-ip-address
                                leaf source-ip-address {
                                    type types-sros:ipv4-address;
                                    description "Source IP address";
                                }

                                ///global-operations/oam/lsp-ping/sr-ospf/output/results/test-parameters/interval
                                leaf interval {
                                    type uint32 {
                                        range "1..10";
                                    }
                                    units "seconds";
                                    description "Minimum time to expire before the next request is sent";
                                }

                                ///global-operations/oam/lsp-ping/sr-ospf/output/results/test-parameters/size
                                leaf size {
                                    type uint32 {
                                        range "1..9786";
                                    }
                                    units "bytes";
                                    description "Packet pad size of request";
                                }

                                ///global-operations/oam/lsp-ping/sr-ospf/output/results/test-parameters/fc
                                leaf fc {
                                    type types-sros:fc-name;
                                    description "QoS Forwarding Class for the transmitted request packet(s)";
                                }

                                ///global-operations/oam/lsp-ping/sr-ospf/output/results/test-parameters/profile
                                leaf profile {
                                    type types-qos:profile-in-out;
                                    description "QoS profile for the transmitted request packet(s)";
                                }

                                ///global-operations/oam/lsp-ping/sr-ospf/output/results/test-parameters/timeout
                                leaf timeout {
                                    type uint32 {
                                        range "1..10";
                                    }
                                    units "seconds";
                                    description "Time router waits for a reply after sending a request";
                                }

                                ///global-operations/oam/lsp-ping/sr-ospf/output/results/test-parameters/ttl
                                leaf ttl {
                                    type uint32 {
                                        range "1..255";
                                    }
                                    description "TTL value for the request's MPLS label";
                                }

                                ///global-operations/oam/lsp-ping/sr-ospf/output/results/test-parameters/send-count
                                leaf send-count {
                                    type uint32 {
                                        range "1..100";
                                    }
                                    units "packets";
                                    description "Number of request packets to send";
                                }

                            } // container test-parameters

                            ///global-operations/oam/lsp-ping/sr-ospf/output/results/probe
                            list probe {
                                key "probe-index";
                                description "Probe data for the specified test run";

                                ///global-operations/oam/lsp-ping/sr-ospf/output/results/probe/probe-index
                                leaf probe-index {
                                    type uint32 {
                                        range "1..max";
                                    }
                                    description "Probe index number";
                                }

                                ///global-operations/oam/lsp-ping/sr-ospf/output/results/probe/egress-interface
                                leaf egress-interface {
                                    type types-sros:interface-name;
                                    description "Indicates the interface name this probe was transmitted from";
                                }

                                ///global-operations/oam/lsp-ping/sr-ospf/output/results/probe/round-trip-time
                                leaf round-trip-time {
                                    type uint32;
                                    units "microseconds";
                                    description "Indicates the round trip time for the probe";
                                }

                                ///global-operations/oam/lsp-ping/sr-ospf/output/results/probe/status
                                leaf status {
                                    type types-oam:response-status;
                                    description "Indicates the OAM response status code for the probe";
                                }

                                ///global-operations/oam/lsp-ping/sr-ospf/output/results/probe/response-packet
                                container response-packet {
                                    description "Data from packet received as a response to the transmitted probe";

                                    ///global-operations/oam/lsp-ping/sr-ospf/output/results/probe/response-packet/size
                                    leaf size {
                                        type uint32;
                                        units "bytes";
                                        description "Indicates the number of bytes in the response packet for the specified probe";
                                    }

                                    ///global-operations/oam/lsp-ping/sr-ospf/output/results/probe/response-packet/source-address
                                    leaf source-address {
                                        type types-sros:ip-address;
                                        description "Indicates the source address in the response packet for the specified probe";
                                    }

                                    ///global-operations/oam/lsp-ping/sr-ospf/output/results/probe/response-packet/sequence-number
                                    leaf sequence-number {
                                        type uint32;
                                        description
                                            "Indicates the sequence number in the response packet for the
                                             specified probe";
                                    }

                                    ///global-operations/oam/lsp-ping/sr-ospf/output/results/probe/response-packet/return-code
                                    leaf return-code {
                                        type int32;
                                        description "Indicates the OAM return code received in the probe response";
                                    }

                                    ///global-operations/oam/lsp-ping/sr-ospf/output/results/probe/response-packet/return-code-string
                                    leaf return-code-string {
                                        type types-oam:lsp-ping-trace-return-code;
                                        description "Description of the OAM return code";
                                    }

                                } // container response-packet

                            } // list probe

                            ///global-operations/oam/lsp-ping/sr-ospf/output/results/summary
                            container summary {
                                description "Test run summary data";

                                ///global-operations/oam/lsp-ping/sr-ospf/output/results/summary/statistics
                                container statistics {
                                    description "Test run summary statistics";

                                    ///global-operations/oam/lsp-ping/sr-ospf/output/results/summary/statistics/packets
                                    container packets {
                                        description "Packet statistics for the specified test run";

                                        ///global-operations/oam/lsp-ping/sr-ospf/output/results/summary/statistics/packets/sent
                                        leaf sent {
                                            type uint32;
                                            units "packets";
                                            description "Indicates the number of packets sent for the specified test run";
                                        }

                                        ///global-operations/oam/lsp-ping/sr-ospf/output/results/summary/statistics/packets/received
                                        leaf received {
                                            type uint32;
                                            units "packets";
                                            description "Indicates the number of packets received for the specified test run";
                                        }

                                        ///global-operations/oam/lsp-ping/sr-ospf/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/sr-ospf/output/results/summary/statistics/round-trip-time
                                    container round-trip-time {
                                        description "Test run round trip time statistics";

                                        ///global-operations/oam/lsp-ping/sr-ospf/output/results/summary/statistics/round-trip-time/minimum
                                        leaf minimum {
                                            type uint32;
                                            units "microseconds";
                                            description "Indicates the minimum round trip time for the specified test run";
                                        }

                                        ///global-operations/oam/lsp-ping/sr-ospf/output/results/summary/statistics/round-trip-time/average
                                        leaf average {
                                            type uint32;
                                            units "microseconds";
                                            description "Indicates the average round trip time for the specified test run";
                                        }

                                        ///global-operations/oam/lsp-ping/sr-ospf/output/results/summary/statistics/round-trip-time/maximum
                                        leaf maximum {
                                            type uint32;
                                            units "microseconds";
                                            description "Indicates the maximum round trip time for the specified test run";
                                        }

                                        ///global-operations/oam/lsp-ping/sr-ospf/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/sr-ospf/output/status
                        leaf status {
                            type types-operation:operation-status;
                            description "Status of the operation";
                        }

                        ///global-operations/oam/lsp-ping/sr-ospf/output/error-message
                        leaf-list error-message {
                            type types-operation:operation-message;
                            description "Error messages reported during execution of the operation.";
                        }

                        ///global-operations/oam/lsp-ping/sr-ospf/output/warning-message
                        leaf-list warning-message {
                            type types-operation:operation-message;
                            description "Warning messages reported during execution of the operation.";
                        }

                        ///global-operations/oam/lsp-ping/sr-ospf/output/info-message
                        leaf-list info-message {
                            type types-operation:operation-message;
                            description "Info messages reported during execution of the operation.";
                        }

                        ///global-operations/oam/lsp-ping/sr-ospf/output/end-time
                        leaf end-time {
                            type types-operation:operation-timestamp;
                            description "Time when the operation ended its execution.";
                        }

                    }
                } // action sr-ospf

                ///global-operations/oam/lsp-ping/sr-ospf3
                action sr-ospf3 {
                    description "Perform an SR-OSPFv3 LSP ping test";

                    input {

                        ///global-operations/oam/lsp-ping/sr-ospf3/input/prefix
                        leaf prefix {
                            type types-sros:ip-prefix;
                            mandatory true;
                            description "Destination IP prefix for the test";
                        }

                        ///global-operations/oam/lsp-ping/sr-ospf3/input/igp-instance
                        leaf igp-instance {
                            type uint32 {
                                range "0..31|64..95";
                            }
                            default "0";
                            description "IGP instance for the SR-OSPFv3 test";
                        }

                        ///global-operations/oam/lsp-ping/sr-ospf3/input/path-destination
                        leaf path-destination {
                            type types-sros:ip-address;
                            description "IP address of the path destination";
                        }

                        ///global-operations/oam/lsp-ping/sr-ospf3/input/path-destination-egress
                        choice path-destination-egress {
                            ///global-operations/oam/lsp-ping/sr-ospf3/input/path-destination-egress/case-interface
                            case case-interface {

                                ///global-operations/oam/lsp-ping/sr-ospf3/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/sr-ospf3/input/path-destination-egress/case-next-hop
                            case case-next-hop {

                                ///global-operations/oam/lsp-ping/sr-ospf3/input/path-destination-egress/case-next-hop/next-hop
                                leaf next-hop {
                                    type types-sros:ip-address;
                                    description "Egress IP next hop address to use with path destination";
                                }

                            }
                        }
                        ///global-operations/oam/lsp-ping/sr-ospf3/input/source-ip-address
                        leaf source-ip-address {
                            type types-sros:ip-address;
                            description "Source IP address";
                        }

                        ///global-operations/oam/lsp-ping/sr-ospf3/input/interval
                        leaf interval {
                            type uint32 {
                                range "1..10";
                            }
                            units "seconds";
                            default "1";
                            description "Minimum time to expire before next echo request is sent";
                        }

                        ///global-operations/oam/lsp-ping/sr-ospf3/input/size
                        leaf size {
                            type uint32 {
                                range "1..9786";
                            }
                            units "bytes";
                            default "1";
                            description "Echo request packet pad size";
                        }

                        ///global-operations/oam/lsp-ping/sr-ospf3/input/fc
                        leaf fc {
                            type types-sros:fc-name;
                            default "be";
                            description "QoS forwarding class for the sent echo request packet";
                        }

                        ///global-operations/oam/lsp-ping/sr-ospf3/input/profile
                        leaf profile {
                            type types-qos:profile-in-out;
                            default "out";
                            description "QoS profile for the transmitted echo request packets";
                        }

                        ///global-operations/oam/lsp-ping/sr-ospf3/input/timeout
                        leaf timeout {
                            type uint32 {
                                range "1..10";
                            }
                            units "seconds";
                            default "5";
                            description "Time to wait for a reply after sending an echo request";
                        }

                        ///global-operations/oam/lsp-ping/sr-ospf3/input/ttl
                        leaf ttl {
                            type uint32 {
                                range "1..255";
                            }
                            default "255";
                            description "TTL value for the MPLS label of the echo request";
                        }

                        ///global-operations/oam/lsp-ping/sr-ospf3/input/send-count
                        leaf send-count {
                            type uint32 {
                                range "1..100";
                            }
                            units "packets";
                            default "1";
                            description "Number of echo request packets to send";
                        }

                    }
                    output {

                        ///global-operations/oam/lsp-ping/sr-ospf3/output/operation-id
                        leaf operation-id {
                            type types-operation:operation-id;
                            description "ID assigned to the operation.";
                        }

                        ///global-operations/oam/lsp-ping/sr-ospf3/output/start-time
                        leaf start-time {
                            type types-operation:operation-timestamp;
                            description "Time when the operation started its execution.";
                        }

                        ///global-operations/oam/lsp-ping/sr-ospf3/output/results-path
                        leaf results-path {
                            type types-operation:operation-path;
                            description "Path to the results of the operation formatted as xpath.";
                        }

                        ///global-operations/oam/lsp-ping/sr-ospf3/output/results
                        container results {
                            description "Enter the results context";

                            ///global-operations/oam/lsp-ping/sr-ospf3/output/results/test-parameters
                            container test-parameters {
                                description "Enter the test-parameters context";

                                ///global-operations/oam/lsp-ping/sr-ospf3/output/results/test-parameters/prefix
                                leaf prefix {
                                    type types-sros:ip-prefix;
                                    description "The destination IP prefix for the test";
                                }

                                ///global-operations/oam/lsp-ping/sr-ospf3/output/results/test-parameters/igp-instance
                                leaf igp-instance {
                                    type uint32 {
                                        range "0..127";
                                    }
                                    description "The IGP instance for the test";
                                }

                                ///global-operations/oam/lsp-ping/sr-ospf3/output/results/test-parameters/path-destination
                                leaf path-destination {
                                    type types-sros:ip-address;
                                    description "The IP address of the path destination";
                                }

                                ///global-operations/oam/lsp-ping/sr-ospf3/output/results/test-parameters/path-destination-egress
                                choice path-destination-egress {
                                    ///global-operations/oam/lsp-ping/sr-ospf3/output/results/test-parameters/path-destination-egress/case-interface
                                    case case-interface {

                                        ///global-operations/oam/lsp-ping/sr-ospf3/output/results/test-parameters/path-destination-egress/case-interface/interface
                                        leaf interface {
                                            type types-sros:interface-name;
                                            description "The egress router interface, used in conjunction with path-destination";
                                        }

                                    }
                                    ///global-operations/oam/lsp-ping/sr-ospf3/output/results/test-parameters/path-destination-egress/case-next-hop
                                    case case-next-hop {

                                        ///global-operations/oam/lsp-ping/sr-ospf3/output/results/test-parameters/path-destination-egress/case-next-hop/next-hop
                                        leaf next-hop {
                                            type types-sros:ip-address;
                                            description "The egress IP next hop address, used in conjunction with path-destination";
                                        }

                                    }
                                }
                                ///global-operations/oam/lsp-ping/sr-ospf3/output/results/test-parameters/source-ip-address
                                leaf source-ip-address {
                                    type types-sros:ip-address;
                                    description "Source IP address";
                                }

                                ///global-operations/oam/lsp-ping/sr-ospf3/output/results/test-parameters/interval
                                leaf interval {
                                    type uint32 {
                                        range "1..10";
                                    }
                                    units "seconds";
                                    description "Minimum time to expire before the next request is sent";
                                }

                                ///global-operations/oam/lsp-ping/sr-ospf3/output/results/test-parameters/size
                                leaf size {
                                    type uint32 {
                                        range "1..9786";
                                    }
                                    units "bytes";
                                    description "Packet pad size of request";
                                }

                                ///global-operations/oam/lsp-ping/sr-ospf3/output/results/test-parameters/fc
                                leaf fc {
                                    type types-sros:fc-name;
                                    description "QoS Forwarding Class for the transmitted request packet(s)";
                                }

                                ///global-operations/oam/lsp-ping/sr-ospf3/output/results/test-parameters/profile
                                leaf profile {
                                    type types-qos:profile-in-out;
                                    description "QoS profile for the transmitted request packet(s)";
                                }

                                ///global-operations/oam/lsp-ping/sr-ospf3/output/results/test-parameters/timeout
                                leaf timeout {
                                    type uint32 {
                                        range "1..10";
                                    }
                                    units "seconds";
                                    description "Time router waits for a reply after sending a request";
                                }

                                ///global-operations/oam/lsp-ping/sr-ospf3/output/results/test-parameters/ttl
                                leaf ttl {
                                    type uint32 {
                                        range "1..255";
                                    }
                                    description "TTL value for the request's MPLS label";
                                }

                                ///global-operations/oam/lsp-ping/sr-ospf3/output/results/test-parameters/send-count
                                leaf send-count {
                                    type uint32 {
                                        range "1..100";
                                    }
                                    units "packets";
                                    description "Number of request packets to send";
                                }

                            } // container test-parameters

                            ///global-operations/oam/lsp-ping/sr-ospf3/output/results/probe
                            list probe {
                                key "probe-index";
                                description "Probe data for the specified test run";

                                ///global-operations/oam/lsp-ping/sr-ospf3/output/results/probe/probe-index
                                leaf probe-index {
                                    type uint32 {
                                        range "1..max";
                                    }
                                    description "Probe index number";
                                }

                                ///global-operations/oam/lsp-ping/sr-ospf3/output/results/probe/egress-interface
                                leaf egress-interface {
                                    type types-sros:interface-name;
                                    description "Indicates the interface name this probe was transmitted from";
                                }

                                ///global-operations/oam/lsp-ping/sr-ospf3/output/results/probe/round-trip-time
                                leaf round-trip-time {
                                    type uint32;
                                    units "microseconds";
                                    description "Indicates the round trip time for the probe";
                                }

                                ///global-operations/oam/lsp-ping/sr-ospf3/output/results/probe/status
                                leaf status {
                                    type types-oam:response-status;
                                    description "Indicates the OAM response status code for the probe";
                                }

                                ///global-operations/oam/lsp-ping/sr-ospf3/output/results/probe/response-packet
                                container response-packet {
                                    description "Data from packet received as a response to the transmitted probe";

                                    ///global-operations/oam/lsp-ping/sr-ospf3/output/results/probe/response-packet/size
                                    leaf size {
                                        type uint32;
                                        units "bytes";
                                        description "Indicates the number of bytes in the response packet for the specified probe";
                                    }

                                    ///global-operations/oam/lsp-ping/sr-ospf3/output/results/probe/response-packet/source-address
                                    leaf source-address {
                                        type types-sros:ip-address;
                                        description "Indicates the source address in the response packet for the specified probe";
                                    }

                                    ///global-operations/oam/lsp-ping/sr-ospf3/output/results/probe/response-packet/sequence-number
                                    leaf sequence-number {
                                        type uint32;
                                        description
                                            "Indicates the sequence number in the response packet for the
                                             specified probe";
                                    }

                                    ///global-operations/oam/lsp-ping/sr-ospf3/output/results/probe/response-packet/return-code
                                    leaf return-code {
                                        type int32;
                                        description "Indicates the OAM return code received in the probe response";
                                    }

                                    ///global-operations/oam/lsp-ping/sr-ospf3/output/results/probe/response-packet/return-code-string
                                    leaf return-code-string {
                                        type types-oam:lsp-ping-trace-return-code;
                                        description "Description of the OAM return code";
                                    }

                                } // container response-packet

                            } // list probe

                            ///global-operations/oam/lsp-ping/sr-ospf3/output/results/summary
                            container summary {
                                description "Test run summary data";

                                ///global-operations/oam/lsp-ping/sr-ospf3/output/results/summary/statistics
                                container statistics {
                                    description "Test run summary statistics";

                                    ///global-operations/oam/lsp-ping/sr-ospf3/output/results/summary/statistics/packets
                                    container packets {
                                        description "Packet statistics for the specified test run";

                                        ///global-operations/oam/lsp-ping/sr-ospf3/output/results/summary/statistics/packets/sent
                                        leaf sent {
                                            type uint32;
                                            units "packets";
                                            description "Indicates the number of packets sent for the specified test run";
                                        }

                                        ///global-operations/oam/lsp-ping/sr-ospf3/output/results/summary/statistics/packets/received
                                        leaf received {
                                            type uint32;
                                            units "packets";
                                            description "Indicates the number of packets received for the specified test run";
                                        }

                                        ///global-operations/oam/lsp-ping/sr-ospf3/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/sr-ospf3/output/results/summary/statistics/round-trip-time
                                    container round-trip-time {
                                        description "Test run round trip time statistics";

                                        ///global-operations/oam/lsp-ping/sr-ospf3/output/results/summary/statistics/round-trip-time/minimum
                                        leaf minimum {
                                            type uint32;
                                            units "microseconds";
                                            description "Indicates the minimum round trip time for the specified test run";
                                        }

                                        ///global-operations/oam/lsp-ping/sr-ospf3/output/results/summary/statistics/round-trip-time/average
                                        leaf average {
                                            type uint32;
                                            units "microseconds";
                                            description "Indicates the average round trip time for the specified test run";
                                        }

                                        ///global-operations/oam/lsp-ping/sr-ospf3/output/results/summary/statistics/round-trip-time/maximum
                                        leaf maximum {
                                            type uint32;
                                            units "microseconds";
                                            description "Indicates the maximum round trip time for the specified test run";
                                        }

                                        ///global-operations/oam/lsp-ping/sr-ospf3/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/sr-ospf3/output/status
                        leaf status {
                            type types-operation:operation-status;
                            description "Status of the operation";
                        }

                        ///global-operations/oam/lsp-ping/sr-ospf3/output/error-message
                        leaf-list error-message {
                            type types-operation:operation-message;
                            description "Error messages reported during execution of the operation.";
                        }

                        ///global-operations/oam/lsp-ping/sr-ospf3/output/warning-message
                        leaf-list warning-message {
                            type types-operation:operation-message;
                            description "Warning messages reported during execution of the operation.";
                        }

                        ///global-operations/oam/lsp-ping/sr-ospf3/output/info-message
                        leaf-list info-message {
                            type types-operation:operation-message;
                            description "Info messages reported during execution of the operation.";
                        }

                        ///global-operations/oam/lsp-ping/sr-ospf3/output/end-time
                        leaf end-time {
                            type types-operation:operation-timestamp;
                            description "Time when the operation ended its execution.";
                        }

                    }
                } // action sr-ospf3

                ///global-operations/oam/lsp-ping/sr-policy
                action sr-policy {
                    description "Perform an SR policy LSP ping test";

                    input {

                        ///global-operations/oam/lsp-ping/sr-policy/input/color
                        leaf color {
                            type uint32;
                            mandatory true;
                            description "Segment Routing color for the test";
                        }

                        ///global-operations/oam/lsp-ping/sr-policy/input/endpoint
                        leaf endpoint {
                            type types-sros:ip-address;
                            mandatory true;
                            description "Segment Routing endpoint for the test";
                        }

                        ///global-operations/oam/lsp-ping/sr-policy/input/segment-list
                        leaf segment-list {
                            type uint32 {
                                range "1..32";
                            }
                            description "Segment Routing segment list for the test";
                        }

                        ///global-operations/oam/lsp-ping/sr-policy/input/path-destination
                        leaf path-destination {
                            type types-sros:ip-address;
                            description "IP address of the path destination";
                        }

                        ///global-operations/oam/lsp-ping/sr-policy/input/path-destination-egress
                        choice path-destination-egress {
                            ///global-operations/oam/lsp-ping/sr-policy/input/path-destination-egress/case-interface
                            case case-interface {

                                ///global-operations/oam/lsp-ping/sr-policy/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/sr-policy/input/path-destination-egress/case-next-hop
                            case case-next-hop {

                                ///global-operations/oam/lsp-ping/sr-policy/input/path-destination-egress/case-next-hop/next-hop
                                leaf next-hop {
                                    type types-sros:ip-address;
                                    description "Egress IP next hop address to use with path destination";
                                }

                            }
                        }
                        ///global-operations/oam/lsp-ping/sr-policy/input/source-ip-address
                        leaf source-ip-address {
                            type types-sros:ip-address;
                            description "Source IP address";
                        }

                        ///global-operations/oam/lsp-ping/sr-policy/input/interval
                        leaf interval {
                            type uint32 {
                                range "1..10";
                            }
                            units "seconds";
                            default "1";
                            description "Minimum time to expire before next echo request is sent";
                        }

                        ///global-operations/oam/lsp-ping/sr-policy/input/size
                        leaf size {
                            type uint32 {
                                range "1..9786";
                            }
                            units "bytes";
                            default "1";
                            description "Echo request packet pad size";
                        }

                        ///global-operations/oam/lsp-ping/sr-policy/input/fc
                        leaf fc {
                            type types-sros:fc-name;
                            default "be";
                            description "QoS forwarding class for the sent echo request packet";
                        }

                        ///global-operations/oam/lsp-ping/sr-policy/input/profile
                        leaf profile {
                            type types-qos:profile-in-out;
                            default "out";
                            description "QoS profile for the transmitted echo request packets";
                        }

                        ///global-operations/oam/lsp-ping/sr-policy/input/timeout
                        leaf timeout {
                            type uint32 {
                                range "1..10";
                            }
                            units "seconds";
                            default "5";
                            description "Time to wait for a reply after sending an echo request";
                        }

                        ///global-operations/oam/lsp-ping/sr-policy/input/ttl
                        leaf ttl {
                            type uint32 {
                                range "1..255";
                            }
                            default "255";
                            description "TTL value for the MPLS label of the echo request";
                        }

                        ///global-operations/oam/lsp-ping/sr-policy/input/send-count
                        leaf send-count {
                            type uint32 {
                                range "1..100";
                            }
                            units "packets";
                            default "1";
                            description "Number of echo request packets to send";
                        }

                    }
                    output {

                        ///global-operations/oam/lsp-ping/sr-policy/output/operation-id
                        leaf operation-id {
                            type types-operation:operation-id;
                            description "ID assigned to the operation.";
                        }

                        ///global-operations/oam/lsp-ping/sr-policy/output/start-time
                        leaf start-time {
                            type types-operation:operation-timestamp;
                            description "Time when the operation started its execution.";
                        }

                        ///global-operations/oam/lsp-ping/sr-policy/output/results-path
                        leaf results-path {
                            type types-operation:operation-path;
                            description "Path to the results of the operation formatted as xpath.";
                        }

                        ///global-operations/oam/lsp-ping/sr-policy/output/results
                        container results {
                            description "Enter the results context";

                            ///global-operations/oam/lsp-ping/sr-policy/output/results/test-parameters
                            container test-parameters {
                                description "Enter the test-parameters context";

                                ///global-operations/oam/lsp-ping/sr-policy/output/results/test-parameters/color
                                leaf color {
                                    type uint32;
                                    description "The Segment Routing color for the test";
                                }

                                ///global-operations/oam/lsp-ping/sr-policy/output/results/test-parameters/endpoint
                                leaf endpoint {
                                    type types-sros:ip-address;
                                    description "The Segment Routing endpoint for the test";
                                }

                                ///global-operations/oam/lsp-ping/sr-policy/output/results/test-parameters/segment-list
                                leaf segment-list {
                                    type uint32 {
                                        range "0..32";
                                    }
                                    description "The Segment Routing segment list for the test";
                                }

                                ///global-operations/oam/lsp-ping/sr-policy/output/results/test-parameters/path-destination
                                leaf path-destination {
                                    type types-sros:ip-address;
                                    description "The IP address of the path destination";
                                }

                                ///global-operations/oam/lsp-ping/sr-policy/output/results/test-parameters/path-destination-egress
                                choice path-destination-egress {
                                    ///global-operations/oam/lsp-ping/sr-policy/output/results/test-parameters/path-destination-egress/case-interface
                                    case case-interface {

                                        ///global-operations/oam/lsp-ping/sr-policy/output/results/test-parameters/path-destination-egress/case-interface/interface
                                        leaf interface {
                                            type types-sros:interface-name;
                                            description "The egress router interface, used in conjunction with path-destination";
                                        }

                                    }
                                    ///global-operations/oam/lsp-ping/sr-policy/output/results/test-parameters/path-destination-egress/case-next-hop
                                    case case-next-hop {

                                        ///global-operations/oam/lsp-ping/sr-policy/output/results/test-parameters/path-destination-egress/case-next-hop/next-hop
                                        leaf next-hop {
                                            type types-sros:ip-address;
                                            description "The egress IP next hop address, used in conjunction with path-destination";
                                        }

                                    }
                                }
                                ///global-operations/oam/lsp-ping/sr-policy/output/results/test-parameters/source-ip-address
                                leaf source-ip-address {
                                    type types-sros:ip-address;
                                    description "Source IP address";
                                }

                                ///global-operations/oam/lsp-ping/sr-policy/output/results/test-parameters/interval
                                leaf interval {
                                    type uint32 {
                                        range "1..10";
                                    }
                                    units "seconds";
                                    description "Minimum time to expire before the next request is sent";
                                }

                                ///global-operations/oam/lsp-ping/sr-policy/output/results/test-parameters/size
                                leaf size {
                                    type uint32 {
                                        range "1..9786";
                                    }
                                    units "bytes";
                                    description "Packet pad size of request";
                                }

                                ///global-operations/oam/lsp-ping/sr-policy/output/results/test-parameters/fc
                                leaf fc {
                                    type types-sros:fc-name;
                                    description "QoS Forwarding Class for the transmitted request packet(s)";
                                }

                                ///global-operations/oam/lsp-ping/sr-policy/output/results/test-parameters/profile
                                leaf profile {
                                    type types-qos:profile-in-out;
                                    description "QoS profile for the transmitted request packet(s)";
                                }

                                ///global-operations/oam/lsp-ping/sr-policy/output/results/test-parameters/timeout
                                leaf timeout {
                                    type uint32 {
                                        range "1..10";
                                    }
                                    units "seconds";
                                    description "Time router waits for a reply after sending a request";
                                }

                                ///global-operations/oam/lsp-ping/sr-policy/output/results/test-parameters/ttl
                                leaf ttl {
                                    type uint32 {
                                        range "1..255";
                                    }
                                    description "TTL value for the request's MPLS label";
                                }

                                ///global-operations/oam/lsp-ping/sr-policy/output/results/test-parameters/send-count
                                leaf send-count {
                                    type uint32 {
                                        range "1..100";
                                    }
                                    units "packets";
                                    description "Number of request packets to send";
                                }

                            } // container test-parameters

                            ///global-operations/oam/lsp-ping/sr-policy/output/results/probe
                            list probe {
                                key "probe-index";
                                description "Probe data for the specified test run";

                                ///global-operations/oam/lsp-ping/sr-policy/output/results/probe/probe-index
                                leaf probe-index {
                                    type uint32 {
                                        range "1..max";
                                    }
                                    description "Probe index number";
                                }

                                ///global-operations/oam/lsp-ping/sr-policy/output/results/probe/egress-interface
                                leaf egress-interface {
                                    type types-sros:interface-name;
                                    description "Indicates the interface name this probe was transmitted from";
                                }

                                ///global-operations/oam/lsp-ping/sr-policy/output/results/probe/round-trip-time
                                leaf round-trip-time {
                                    type uint32;
                                    units "microseconds";
                                    description "Indicates the round trip time for the probe";
                                }

                                ///global-operations/oam/lsp-ping/sr-policy/output/results/probe/status
                                leaf status {
                                    type types-oam:response-status;
                                    description "Indicates the OAM response status code for the probe";
                                }

                                ///global-operations/oam/lsp-ping/sr-policy/output/results/probe/response-packet
                                container response-packet {
                                    description "Data from packet received as a response to the transmitted probe";

                                    ///global-operations/oam/lsp-ping/sr-policy/output/results/probe/response-packet/size
                                    leaf size {
                                        type uint32;
                                        units "bytes";
                                        description "Indicates the number of bytes in the response packet for the specified probe";
                                    }

                                    ///global-operations/oam/lsp-ping/sr-policy/output/results/probe/response-packet/source-address
                                    leaf source-address {
                                        type types-sros:ip-address;
                                        description "Indicates the source address in the response packet for the specified probe";
                                    }

                                    ///global-operations/oam/lsp-ping/sr-policy/output/results/probe/response-packet/sequence-number
                                    leaf sequence-number {
                                        type uint32;
                                        description
                                            "Indicates the sequence number in the response packet for the
                                             specified probe";
                                    }

                                    ///global-operations/oam/lsp-ping/sr-policy/output/results/probe/response-packet/return-code
                                    leaf return-code {
                                        type int32;
                                        description "Indicates the OAM return code received in the probe response";
                                    }

                                    ///global-operations/oam/lsp-ping/sr-policy/output/results/probe/response-packet/return-code-string
                                    leaf return-code-string {
                                        type types-oam:lsp-ping-trace-return-code;
                                        description "Description of the OAM return code";
                                    }

                                } // container response-packet

                            } // list probe

                            ///global-operations/oam/lsp-ping/sr-policy/output/results/summary
                            container summary {
                                description "Test run summary data";

                                ///global-operations/oam/lsp-ping/sr-policy/output/results/summary/statistics
                                container statistics {
                                    description "Test run summary statistics";

                                    ///global-operations/oam/lsp-ping/sr-policy/output/results/summary/statistics/packets
                                    container packets {
                                        description "Packet statistics for the specified test run";

                                        ///global-operations/oam/lsp-ping/sr-policy/output/results/summary/statistics/packets/sent
                                        leaf sent {
                                            type uint32;
                                            units "packets";
                                            description "Indicates the number of packets sent for the specified test run";
                                        }

                                        ///global-operations/oam/lsp-ping/sr-policy/output/results/summary/statistics/packets/received
                                        leaf received {
                                            type uint32;
                                            units "packets";
                                            description "Indicates the number of packets received for the specified test run";
                                        }

                                        ///global-operations/oam/lsp-ping/sr-policy/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/sr-policy/output/results/summary/statistics/round-trip-time
                                    container round-trip-time {
                                        description "Test run round trip time statistics";

                                        ///global-operations/oam/lsp-ping/sr-policy/output/results/summary/statistics/round-trip-time/minimum
                                        leaf minimum {
                                            type uint32;
                                            units "microseconds";
                                            description "Indicates the minimum round trip time for the specified test run";
                                        }

                                        ///global-operations/oam/lsp-ping/sr-policy/output/results/summary/statistics/round-trip-time/average
                                        leaf average {
                                            type uint32;
                                            units "microseconds";
                                            description "Indicates the average round trip time for the specified test run";
                                        }

                                        ///global-operations/oam/lsp-ping/sr-policy/output/results/summary/statistics/round-trip-time/maximum
                                        leaf maximum {
                                            type uint32;
                                            units "microseconds";
                                            description "Indicates the maximum round trip time for the specified test run";
                                        }

                                        ///global-operations/oam/lsp-ping/sr-policy/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/sr-policy/output/status
                        leaf status {
                            type types-operation:operation-status;
                            description "Status of the operation";
                        }

                        ///global-operations/oam/lsp-ping/sr-policy/output/error-message
                        leaf-list error-message {
                            type types-operation:operation-message;
                            description "Error messages reported during execution of the operation.";
                        }

                        ///global-operations/oam/lsp-ping/sr-policy/output/warning-message
                        leaf-list warning-message {
                            type types-operation:operation-message;
                            description "Warning messages reported during execution of the operation.";
                        }

                        ///global-operations/oam/lsp-ping/sr-policy/output/info-message
                        leaf-list info-message {
                            type types-operation:operation-message;
                            description "Info messages reported during execution of the operation.";
                        }

                        ///global-operations/oam/lsp-ping/sr-policy/output/end-time
                        leaf end-time {
                            type types-operation:operation-timestamp;
                            description "Time when the operation ended its execution.";
                        }

                    }
                } // action sr-policy

                ///global-operations/oam/lsp-ping/sr-te
                action sr-te {
                    description "Perform an SR-TE LSP ping test";

                    input {

                        ///global-operations/oam/lsp-ping/sr-te/input/lsp-name
                        leaf lsp-name {
                            type leafref {
                                path "/state:state/state:router/state:mpls/state:lsp/state:lsp-name";
                                require-instance "false";
                            }
                            mandatory true;
                            description "Name of the LSP to test";
                        }

                        ///global-operations/oam/lsp-ping/sr-te/input/path
                        leaf path {
                            type leafref {
                                path "/state:state/state:router/state:mpls/state:path/state:path-name";
                                require-instance "false";
                            }
                            description "Name of the MPLS path to test";
                        }

                        ///global-operations/oam/lsp-ping/sr-te/input/path-destination
                        leaf path-destination {
                            type types-sros:ip-address;
                            description "IP address of the path destination";
                        }

                        ///global-operations/oam/lsp-ping/sr-te/input/path-destination-egress
                        choice path-destination-egress {
                            ///global-operations/oam/lsp-ping/sr-te/input/path-destination-egress/case-interface
                            case case-interface {

                                ///global-operations/oam/lsp-ping/sr-te/input/path-destination-egress/case-interface/interface
                                leaf interface {
                                    type leafref {
                                        path "/state:state/state:router/state:interface/state:interface-name";
                                        require-instance "false";
                                    }
                                    description "Egress router interface to use with path destination";
                                }

                            }
                            ///global-operations/oam/lsp-ping/sr-te/input/path-destination-egress/case-next-hop
                            case case-next-hop {

                                ///global-operations/oam/lsp-ping/sr-te/input/path-destination-egress/case-next-hop/next-hop
                                leaf next-hop {
                                    type types-sros:ip-address;
                                    description "Egress IP next hop address to use with path destination";
                                }

                            }
                        }
                        ///global-operations/oam/lsp-ping/sr-te/input/source-ip-address
                        leaf source-ip-address {
                            type types-sros:ip-address;
                            description "Source IP address";
                        }

                        ///global-operations/oam/lsp-ping/sr-te/input/interval
                        leaf interval {
                            type uint32 {
                                range "1..10";
                            }
                            units "seconds";
                            default "1";
                            description "Minimum time to expire before next echo request is sent";
                        }

                        ///global-operations/oam/lsp-ping/sr-te/input/size
                        leaf size {
                            type uint32 {
                                range "1..9786";
                            }
                            units "bytes";
                            default "1";
                            description "Echo request packet pad size";
                        }

                        ///global-operations/oam/lsp-ping/sr-te/input/fc
                        leaf fc {
                            type types-sros:fc-name;
                            default "be";
                            description "QoS forwarding class for the sent echo request packet";
                        }

                        ///global-operations/oam/lsp-ping/sr-te/input/profile
                        leaf profile {
                            type types-qos:profile-in-out;
                            default "out";
                            description "QoS profile for the transmitted echo request packets";
                        }

                        ///global-operations/oam/lsp-ping/sr-te/input/timeout
                        leaf timeout {
                            type uint32 {
                                range "1..10";
                            }
                            units "seconds";
                            default "5";
                            description "Time to wait for a reply after sending an echo request";
                        }

                        ///global-operations/oam/lsp-ping/sr-te/input/ttl
                        leaf ttl {
                            type uint32 {
                                range "1..255";
                            }
                            default "255";
                            description "TTL value for the MPLS label of the echo request";
                        }

                        ///global-operations/oam/lsp-ping/sr-te/input/send-count
                        leaf send-count {
                            type uint32 {
                                range "1..100";
                            }
                            units "packets";
                            default "1";
                            description "Number of echo request packets to send";
                        }

                    }
                    output {

                        ///global-operations/oam/lsp-ping/sr-te/output/operation-id
                        leaf operation-id {
                            type types-operation:operation-id;
                            description "ID assigned to the operation.";
                        }

                        ///global-operations/oam/lsp-ping/sr-te/output/start-time
                        leaf start-time {
                            type types-operation:operation-timestamp;
                            description "Time when the operation started its execution.";
                        }

                        ///global-operations/oam/lsp-ping/sr-te/output/results-path
                        leaf results-path {
                            type types-operation:operation-path;
                            description "Path to the results of the operation formatted as xpath.";
                        }

                        ///global-operations/oam/lsp-ping/sr-te/output/results
                        container results {
                            description "Enter the results context";

                            ///global-operations/oam/lsp-ping/sr-te/output/results/test-parameters
                            container test-parameters {
                                description "Enter the test-parameters context";

                                ///global-operations/oam/lsp-ping/sr-te/output/results/test-parameters/lsp-name
                                leaf lsp-name {
                                    type types-sros:named-item-64;
                                    description "The name of the LSP to be tested";
                                }

                                ///global-operations/oam/lsp-ping/sr-te/output/results/test-parameters/path
                                leaf path {
                                    type types-sros:named-item-64;
                                    description "The name of the MPLS path to be tested";
                                }

                                ///global-operations/oam/lsp-ping/sr-te/output/results/test-parameters/path-destination
                                leaf path-destination {
                                    type types-sros:ip-address;
                                    description "The IP address of the path destination";
                                }

                                ///global-operations/oam/lsp-ping/sr-te/output/results/test-parameters/path-destination-egress
                                choice path-destination-egress {
                                    ///global-operations/oam/lsp-ping/sr-te/output/results/test-parameters/path-destination-egress/case-interface
                                    case case-interface {

                                        ///global-operations/oam/lsp-ping/sr-te/output/results/test-parameters/path-destination-egress/case-interface/interface
                                        leaf interface {
                                            type types-sros:interface-name;
                                            description "The egress router interface, used in conjunction with path-destination";
                                        }

                                    }
                                    ///global-operations/oam/lsp-ping/sr-te/output/results/test-parameters/path-destination-egress/case-next-hop
                                    case case-next-hop {

                                        ///global-operations/oam/lsp-ping/sr-te/output/results/test-parameters/path-destination-egress/case-next-hop/next-hop
                                        leaf next-hop {
                                            type types-sros:ip-address;
                                            description "The egress IP next hop address, used in conjunction with path-destination";
                                        }

                                    }
                                }
                                ///global-operations/oam/lsp-ping/sr-te/output/results/test-parameters/source-ip-address
                                leaf source-ip-address {
                                    type types-sros:ip-address;
                                    description "Source IP address";
                                }

                                ///global-operations/oam/lsp-ping/sr-te/output/results/test-parameters/interval
                                leaf interval {
                                    type uint32 {
                                        range "1..10";
                                    }
                                    units "seconds";
                                    description "Minimum time to expire before the next request is sent";
                                }

                                ///global-operations/oam/lsp-ping/sr-te/output/results/test-parameters/size
                                leaf size {
                                    type uint32 {
                                        range "1..9786";
                                    }
                                    units "bytes";
                                    description "Packet pad size of request";
                                }

                                ///global-operations/oam/lsp-ping/sr-te/output/results/test-parameters/fc
                                leaf fc {
                                    type types-sros:fc-name;
                                    description "QoS Forwarding Class for the transmitted request packet(s)";
                                }

                                ///global-operations/oam/lsp-ping/sr-te/output/results/test-parameters/profile
                                leaf profile {
                                    type types-qos:profile-in-out;
                                    description "QoS profile for the transmitted request packet(s)";
                                }

                                ///global-operations/oam/lsp-ping/sr-te/output/results/test-parameters/timeout
                                leaf timeout {
                                    type uint32 {
                                        range "1..10";
                                    }
                                    units "seconds";
                                    description "Time router waits for a reply after sending a request";
                                }

                                ///global-operations/oam/lsp-ping/sr-te/output/results/test-parameters/ttl
                                leaf ttl {
                                    type uint32 {
                                        range "1..255";
                                    }
                                    description "TTL value for the request's MPLS label";
                                }

                                ///global-operations/oam/lsp-ping/sr-te/output/results/test-parameters/send-count
                                leaf send-count {
                                    type uint32 {
                                        range "1..100";
                                    }
                                    units "packets";
                                    description "Number of request packets to send";
                                }

                            } // container test-parameters

                            ///global-operations/oam/lsp-ping/sr-te/output/results/probe
                            list probe {
                                key "probe-index";
                                description "Probe data for the specified test run";

                                ///global-operations/oam/lsp-ping/sr-te/output/results/probe/probe-index
                                leaf probe-index {
                                    type uint32 {
                                        range "1..max";
                                    }
                                    description "Probe index number";
                                }

                                ///global-operations/oam/lsp-ping/sr-te/output/results/probe/egress-interface
                                leaf egress-interface {
                                    type types-sros:interface-name;
                                    description "Indicates the interface name this probe was transmitted from";
                                }

                                ///global-operations/oam/lsp-ping/sr-te/output/results/probe/round-trip-time
                                leaf round-trip-time {
                                    type uint32;
                                    units "microseconds";
                                    description "Indicates the round trip time for the probe";
                                }

                                ///global-operations/oam/lsp-ping/sr-te/output/results/probe/status
                                leaf status {
                                    type types-oam:response-status;
                                    description "Indicates the OAM response status code for the probe";
                                }

                                ///global-operations/oam/lsp-ping/sr-te/output/results/probe/response-packet
                                container response-packet {
                                    description "Data from packet received as a response to the transmitted probe";

                                    ///global-operations/oam/lsp-ping/sr-te/output/results/probe/response-packet/size
                                    leaf size {
                                        type uint32;
                                        units "bytes";
                                        description "Indicates the number of bytes in the response packet for the specified probe";
                                    }

                                    ///global-operations/oam/lsp-ping/sr-te/output/results/probe/response-packet/source-address
                                    leaf source-address {
                                        type types-sros:ip-address;
                                        description "Indicates the source address in the response packet for the specified probe";
                                    }

                                    ///global-operations/oam/lsp-ping/sr-te/output/results/probe/response-packet/sequence-number
                                    leaf sequence-number {
                                        type uint32;
                                        description
                                            "Indicates the sequence number in the response packet for the
                                             specified probe";
                                    }

                                    ///global-operations/oam/lsp-ping/sr-te/output/results/probe/response-packet/return-code
                                    leaf return-code {
                                        type int32;
                                        description "Indicates the OAM return code received in the probe response";
                                    }

                                    ///global-operations/oam/lsp-ping/sr-te/output/results/probe/response-packet/return-code-string
                                    leaf return-code-string {
                                        type types-oam:lsp-ping-trace-return-code;
                                        description "Description of the OAM return code";
                                    }

                                } // container response-packet

                            } // list probe

                            ///global-operations/oam/lsp-ping/sr-te/output/results/summary
                            container summary {
                                description "Test run summary data";

                                ///global-operations/oam/lsp-ping/sr-te/output/results/summary/statistics
                                container statistics {
                                    description "Test run summary statistics";

                                    ///global-operations/oam/lsp-ping/sr-te/output/results/summary/statistics/packets
                                    container packets {
                                        description "Packet statistics for the specified test run";

                                        ///global-operations/oam/lsp-ping/sr-te/output/results/summary/statistics/packets/sent
                                        leaf sent {
                                            type uint32;
                                            units "packets";
                                            description "Indicates the number of packets sent for the specified test run";
                                        }

                                        ///global-operations/oam/lsp-ping/sr-te/output/results/summary/statistics/packets/received
                                        leaf received {
                                            type uint32;
                                            units "packets";
                                            description "Indicates the number of packets received for the specified test run";
                                        }

                                        ///global-operations/oam/lsp-ping/sr-te/output/results/summary/statistics/packets/loss
                                        leaf loss {
                                            type decimal64 {
                                                range "0.00..100.00";
                                                fraction-digits 2;
                                            }
                                            units "percent";
                                            description "Indicates the number of packet loss percentage for the specified test run";
                                        }

                                    } // container packets

                                    ///global-operations/oam/lsp-ping/sr-te/output/results/summary/statistics/round-trip-time
                                    container round-trip-time {
                                        description "Test run round trip time statistics";

                                        ///global-operations/oam/lsp-ping/sr-te/output/results/summary/statistics/round-trip-time/minimum
                                        leaf minimum {
                                            type uint32;
                                            units "microseconds";
                                            description "Indicates the minimum round trip time for the specified test run";
                                        }

                                        ///global-operations/oam/lsp-ping/sr-te/output/results/summary/statistics/round-trip-time/average
                                        leaf average {
                                            type uint32;
                                            units "microseconds";
                                            description "Indicates the average round trip time for the specified test run";
                                        }

                                        ///global-operations/oam/lsp-ping/sr-te/output/results/summary/statistics/round-trip-time/maximum
                                        leaf maximum {
                                            type uint32;
                                            units "microseconds";
                                            description "Indicates the maximum round trip time for the specified test run";
                                        }

                                        ///global-operations/oam/lsp-ping/sr-te/output/results/summary/statistics/round-trip-time/standard-deviation
                                        leaf standard-deviation {
                                            type uint32;
                                            units "microseconds";
                                            description
                                                "Indicates the standard deviation for the round trip times for the
                                                 specified test run";
                                        }

                                    } // container round-trip-time

                                } // container statistics

                            } // container summary

                        } // container results

                        ///global-operations/oam/lsp-ping/sr-te/output/status
                        leaf status {
                            type types-operation:operation-status;
                            description "Status of the operation";
                        }

                        ///global-operations/oam/lsp-ping/sr-te/output/error-message
                        leaf-list error-message {
                            type types-operation:operation-message;
                            description "Error messages reported during execution of the operation.";
                        }

                        ///global-operations/oam/lsp-ping/sr-te/output/warning-message
                        leaf-list warning-message {
                            type types-operation:operation-message;
                            description "Warning messages reported during execution of the operation.";
                        }

                        ///global-operations/oam/lsp-ping/sr-te/output/info-message
                        leaf-list info-message {
                            type types-operation:operation-message;
                            description "Info messages reported during execution of the operation.";
                        }

                        ///global-operations/oam/lsp-ping/sr-te/output/end-time
                        leaf end-time {
                            type types-operation:operation-timestamp;
                            description "Time when the operation ended its execution.";
                        }

                    }
                } // action sr-te

            } // container lsp-ping

            ///global-operations/oam/lsp-trace
            container lsp-trace {
                description "Perform a Label Switched Path (LSP) trace test";

                ///global-operations/oam/lsp-trace/bgp-label
                action bgp-label {
                    description "Perform a BGP-label LSP trace test";

                    input {

                        ///global-operations/oam/lsp-trace/bgp-label/input/prefix
                        leaf prefix {
                            type types-sros:ip-prefix;
                            mandatory true;
                            description "Destination IP prefix for the test";
                        }

                        ///global-operations/oam/lsp-trace/bgp-label/input/path-destination
                        leaf path-destination {
                            type types-sros:ip-address;
                            description "IP address of the path destination";
                        }

                        ///global-operations/oam/lsp-trace/bgp-label/input/path-destination-egress
                        choice path-destination-egress {
                            ///global-operations/oam/lsp-trace/bgp-label/input/path-destination-egress/case-interface
                            case case-interface {

                                ///global-operations/oam/lsp-trace/bgp-label/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/bgp-label/input/path-destination-egress/case-next-hop
                            case case-next-hop {

                                ///global-operations/oam/lsp-trace/bgp-label/input/path-destination-egress/case-next-hop/next-hop
                                leaf next-hop {
                                    type types-sros:ip-address;
                                    description "Egress IP next hop address to use with path destination";
                                }

                            }
                        }
                        ///global-operations/oam/lsp-trace/bgp-label/input/source-ip-address
                        leaf source-ip-address {
                            type types-sros:ip-address;
                            description "Source IP address";
                        }

                        ///global-operations/oam/lsp-trace/bgp-label/input/interval
                        leaf interval {
                            type uint32 {
                                range "1..10";
                            }
                            units "seconds";
                            default "1";
                            description "Minimum time to expire before next echo request is sent";
                        }

                        ///global-operations/oam/lsp-trace/bgp-label/input/size
                        leaf size {
                            type uint32 {
                                range "1..9786";
                            }
                            units "bytes";
                            default "1";
                            description "Echo request packet pad size";
                        }

                        ///global-operations/oam/lsp-trace/bgp-label/input/fc
                        leaf fc {
                            type types-sros:fc-name;
                            default "be";
                            description "QoS forwarding class for the sent echo request packet";
                        }

                        ///global-operations/oam/lsp-trace/bgp-label/input/profile
                        leaf profile {
                            type types-qos:profile-in-out;
                            default "out";
                            description "QoS profile for the transmitted echo request packets";
                        }

                        ///global-operations/oam/lsp-trace/bgp-label/input/timeout
                        leaf timeout {
                            type uint32 {
                                range "1..10";
                            }
                            units "seconds";
                            default "5";
                            description "Time to wait for a reply after sending an echo request";
                        }

                        ///global-operations/oam/lsp-trace/bgp-label/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/bgp-label/input/min-ttl
                        leaf min-ttl {
                            type uint32 {
                                range "1..255";
                            }
                            default "1";
                            description "Initial TTL for the test";
                        }

                        ///global-operations/oam/lsp-trace/bgp-label/input/max-ttl
                        leaf max-ttl {
                            type uint32 {
                                range "1..255";
                            }
                            default "30";
                            description "Maximum TTL";
                        }

                        ///global-operations/oam/lsp-trace/bgp-label/input/max-fail
                        leaf max-fail {
                            type uint32 {
                                range "1..255";
                            }
                            default "5";
                            description "Maximum consecutive timeouts before terminating test";
                        }

                        ///global-operations/oam/lsp-trace/bgp-label/input/probe-count
                        leaf probe-count {
                            type uint32 {
                                range "1..10";
                            }
                            default "1";
                            description "Number of OAM trace probes to send per TTL";
                        }

                    }
                    output {

                        ///global-operations/oam/lsp-trace/bgp-label/output/operation-id
                        leaf operation-id {
                            type types-operation:operation-id;
                            description "ID assigned to the operation.";
                        }

                        ///global-operations/oam/lsp-trace/bgp-label/output/start-time
                        leaf start-time {
                            type types-operation:operation-timestamp;
                            description "Time when the operation started its execution.";
                        }

                        ///global-operations/oam/lsp-trace/bgp-label/output/results-path
                        leaf results-path {
                            type types-operation:operation-path;
                            description "Path to the results of the operation formatted as xpath.";
                        }

                        ///global-operations/oam/lsp-trace/bgp-label/output/results
                        container results {
                            description "Enter the results context";

                            ///global-operations/oam/lsp-trace/bgp-label/output/results/test-parameters
                            container test-parameters {
                                description "Enter the test-parameters context";

                                ///global-operations/oam/lsp-trace/bgp-label/output/results/test-parameters/prefix
                                leaf prefix {
                                    type types-sros:ip-prefix;
                                    description "The destination IP prefix for the test";
                                }

                                ///global-operations/oam/lsp-trace/bgp-label/output/results/test-parameters/path-destination
                                leaf path-destination {
                                    type types-sros:ip-address;
                                    description "The IP address of the path destination";
                                }

                                ///global-operations/oam/lsp-trace/bgp-label/output/results/test-parameters/path-destination-egress
                                choice path-destination-egress {
                                    ///global-operations/oam/lsp-trace/bgp-label/output/results/test-parameters/path-destination-egress/case-interface
                                    case case-interface {

                                        ///global-operations/oam/lsp-trace/bgp-label/output/results/test-parameters/path-destination-egress/case-interface/interface
                                        leaf interface {
                                            type types-sros:interface-name;
                                            description "The egress router interface, used in conjunction with path-destination";
                                        }

                                    }
                                    ///global-operations/oam/lsp-trace/bgp-label/output/results/test-parameters/path-destination-egress/case-next-hop
                                    case case-next-hop {

                                        ///global-operations/oam/lsp-trace/bgp-label/output/results/test-parameters/path-destination-egress/case-next-hop/next-hop
                                        leaf next-hop {
                                            type types-sros:ip-address;
                                            description "The egress IP next hop address, used in conjunction with path-destination";
                                        }

                                    }
                                }
                                ///global-operations/oam/lsp-trace/bgp-label/output/results/test-parameters/source-ip-address
                                leaf source-ip-address {
                                    type types-sros:ip-address;
                                    description "Source IP address";
                                }

                                ///global-operations/oam/lsp-trace/bgp-label/output/results/test-parameters/interval
                                leaf interval {
                                    type uint32 {
                                        range "1..10";
                                    }
                                    units "seconds";
                                    description "Minimum time to expire before the next request is sent";
                                }

                                ///global-operations/oam/lsp-trace/bgp-label/output/results/test-parameters/size
                                leaf size {
                                    type uint32 {
                                        range "1..9786";
                                    }
                                    units "bytes";
                                    description "Packet pad size of request";
                                }

                                ///global-operations/oam/lsp-trace/bgp-label/output/results/test-parameters/fc
                                leaf fc {
                                    type types-sros:fc-name;
                                    description "QoS Forwarding Class for the transmitted request packet(s)";
                                }

                                ///global-operations/oam/lsp-trace/bgp-label/output/results/test-parameters/profile
                                leaf profile {
                                    type types-qos:profile-in-out;
                                    description "QoS profile for the transmitted request packet(s)";
                                }

                                ///global-operations/oam/lsp-trace/bgp-label/output/results/test-parameters/timeout
                                leaf timeout {
                                    type uint32 {
                                        range "1..10";
                                    }
                                    units "seconds";
                                    description "Time router waits for a reply after sending a request";
                                }

                                ///global-operations/oam/lsp-trace/bgp-label/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/bgp-label/output/results/test-parameters/min-ttl
                                leaf min-ttl {
                                    type uint32 {
                                        range "1..255";
                                    }
                                    description "The initial time-to-live value for the test";
                                }

                                ///global-operations/oam/lsp-trace/bgp-label/output/results/test-parameters/max-ttl
                                leaf max-ttl {
                                    type uint32 {
                                        range "1..255";
                                    }
                                    description "The maximum time-to-live value for the test";
                                }

                                ///global-operations/oam/lsp-trace/bgp-label/output/results/test-parameters/max-fail
                                leaf max-fail {
                                    type uint32 {
                                        range "1..255";
                                    }
                                    description "The maximum number of consecutive timeouts allowed before terminating test";
                                }

                                ///global-operations/oam/lsp-trace/bgp-label/output/results/test-parameters/probe-count
                                leaf probe-count {
                                    type uint32 {
                                        range "1..10";
                                    }
                                    description "The number of OAM trace probes to send per TTL";
                                }

                            } // container test-parameters

                            ///global-operations/oam/lsp-trace/bgp-label/output/results/request-packet
                            container request-packet {
                                description "Enter the request-packet context";

                                ///global-operations/oam/lsp-trace/bgp-label/output/results/request-packet/size
                                leaf size {
                                    type uint32;
                                    units "bytes";
                                    description "Indicates the number of bytes of each request packet sent";
                                }

                                ///global-operations/oam/lsp-trace/bgp-label/output/results/request-packet/source-address
                                leaf source-address {
                                    type types-sros:ip-address;
                                    description "Indicates the source address of the test run";
                                }

                                ///global-operations/oam/lsp-trace/bgp-label/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/bgp-label/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/bgp-label/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/bgp-label/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/bgp-label/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/bgp-label/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/bgp-label/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/bgp-label/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/bgp-label/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/bgp-label/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/bgp-label/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/bgp-label/output/results/hop
                            list hop {
                                key "hop-index";
                                description "Per-hop test results";

                                ///global-operations/oam/lsp-trace/bgp-label/output/results/hop/hop-index
                                leaf hop-index {
                                    type uint32 {
                                        range "1..max";
                                    }
                                    description "The hop index of the test results";
                                }

                                ///global-operations/oam/lsp-trace/bgp-label/output/results/hop/probe
                                list probe {
                                    key "probe-index";
                                    description "Probe data for the specified test run";

                                    ///global-operations/oam/lsp-trace/bgp-label/output/results/hop/probe/probe-index
                                    leaf probe-index {
                                        type uint32 {
                                            range "1..10";
                                        }
                                        description "The probe index of lsp-trace reply, in the context of a hop";
                                    }

                                    ///global-operations/oam/lsp-trace/bgp-label/output/results/hop/probe/probe-instance
                                    list probe-instance {
                                        key "probe-instance-index";
                                        description "Probe instance of a probe, in the contex of a hop";

                                        ///global-operations/oam/lsp-trace/bgp-label/output/results/hop/probe/probe-instance/probe-instance-index
                                        leaf probe-instance-index {
                                            type uint32 {
                                                range "1..4294967295";
                                            }
                                            description "Index of probes with the specified test run";
                                        }

                                        ///global-operations/oam/lsp-trace/bgp-label/output/results/hop/probe/probe-instance/egress-interface
                                        leaf egress-interface {
                                            type types-sros:interface-name;
                                            description "The interface name this probe was transmitted from";
                                        }

                                        ///global-operations/oam/lsp-trace/bgp-label/output/results/hop/probe/probe-instance/round-trip-time
                                        leaf round-trip-time {
                                            type uint32;
                                            units "microseconds";
                                            description "Indicates the round trip time for the probe";
                                        }

                                        ///global-operations/oam/lsp-trace/bgp-label/output/results/hop/probe/probe-instance/status
                                        leaf status {
                                            type types-oam:response-status;
                                            description "The OAM response status code for the specified test";
                                        }

                                        ///global-operations/oam/lsp-trace/bgp-label/output/results/hop/probe/probe-instance/response-packet
                                        container response-packet {
                                            description "Data from packet received as a response to transmitted probe";

                                            ///global-operations/oam/lsp-trace/bgp-label/output/results/hop/probe/probe-instance/response-packet/size
                                            leaf size {
                                                type uint32;
                                                units "bytes";
                                                description "Indicates the number of bytes in the response packet for the probe";
                                            }

                                            ///global-operations/oam/lsp-trace/bgp-label/output/results/hop/probe/probe-instance/response-packet/source-address
                                            leaf source-address {
                                                type types-sros:ip-address;
                                                description
                                                    "Indicates the source address in the response packet for the specified
                                                     probe";
                                            }

                                            ///global-operations/oam/lsp-trace/bgp-label/output/results/hop/probe/probe-instance/response-packet/return-code
                                            leaf return-code {
                                                type int32;
                                                description "Indicates the OAM return code received in the probe response";
                                            }

                                            ///global-operations/oam/lsp-trace/bgp-label/output/results/hop/probe/probe-instance/response-packet/return-code-string
                                            leaf return-code-string {
                                                type types-oam:lsp-ping-trace-return-code;
                                                description "Description of the return-code";
                                            }

                                            ///global-operations/oam/lsp-trace/bgp-label/output/results/hop/probe/probe-instance/response-packet/return-subcode
                                            leaf return-subcode {
                                                type uint32;
                                                description
                                                    "Indicates the stack-depth where processing was terminated with
                                                     the value in the return-code";
                                            }

                                            ///global-operations/oam/lsp-trace/bgp-label/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/bgp-label/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/bgp-label/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/bgp-label/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/bgp-label/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/bgp-label/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/bgp-label/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/bgp-label/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/bgp-label/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/bgp-label/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/bgp-label/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/bgp-label/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/bgp-label/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/bgp-label/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/bgp-label/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/bgp-label/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/bgp-label/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/bgp-label/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/bgp-label/output/status
                        leaf status {
                            type types-operation:operation-status;
                            description "Status of the operation";
                        }

                        ///global-operations/oam/lsp-trace/bgp-label/output/error-message
                        leaf-list error-message {
                            type types-operation:operation-message;
                            description "Error messages reported during execution of the operation.";
                        }

                        ///global-operations/oam/lsp-trace/bgp-label/output/warning-message
                        leaf-list warning-message {
                            type types-operation:operation-message;
                            description "Warning messages reported during execution of the operation.";
                        }

                        ///global-operations/oam/lsp-trace/bgp-label/output/info-message
                        leaf-list info-message {
                            type types-operation:operation-message;
                            description "Info messages reported during execution of the operation.";
                        }

                        ///global-operations/oam/lsp-trace/bgp-label/output/end-time
                        leaf end-time {
                            type types-operation:operation-timestamp;
                            description "Time when the operation ended its execution.";
                        }

                    }
                } // action bgp-label

                ///global-operations/oam/lsp-trace/ldp
                action ldp {
                    description "Perform an LDP LSP trace test";

                    input {

                        ///global-operations/oam/lsp-trace/ldp/input/prefix
                        leaf prefix {
                            type types-sros:ip-prefix;
                            mandatory true;
                            description "Destination IP prefix for the test";
                        }

                        ///global-operations/oam/lsp-trace/ldp/input/path-destination
                        leaf path-destination {
                            type types-sros:ip-address;
                            description "IP address of the path destination";
                        }

                        ///global-operations/oam/lsp-trace/ldp/input/path-destination-egress
                        choice path-destination-egress {
                            ///global-operations/oam/lsp-trace/ldp/input/path-destination-egress/case-interface
                            case case-interface {

                                ///global-operations/oam/lsp-trace/ldp/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/ldp/input/path-destination-egress/case-next-hop
                            case case-next-hop {

                                ///global-operations/oam/lsp-trace/ldp/input/path-destination-egress/case-next-hop/next-hop
                                leaf next-hop {
                                    type types-sros:ip-address;
                                    description "Egress IP next hop address to use with path destination";
                                }

                            }
                        }
                        ///global-operations/oam/lsp-trace/ldp/input/source-ip-address
                        leaf source-ip-address {
                            type types-sros:ip-address;
                            description "Source IP address";
                        }

                        ///global-operations/oam/lsp-trace/ldp/input/interval
                        leaf interval {
                            type uint32 {
                                range "1..10";
                            }
                            units "seconds";
                            default "1";
                            description "Minimum time to expire before next echo request is sent";
                        }

                        ///global-operations/oam/lsp-trace/ldp/input/size
                        leaf size {
                            type uint32 {
                                range "1..9786";
                            }
                            units "bytes";
                            default "1";
                            description "Echo request packet pad size";
                        }

                        ///global-operations/oam/lsp-trace/ldp/input/fc
                        leaf fc {
                            type types-sros:fc-name;
                            default "be";
                            description "QoS forwarding class for the sent echo request packet";
                        }

                        ///global-operations/oam/lsp-trace/ldp/input/profile
                        leaf profile {
                            type types-qos:profile-in-out;
                            default "out";
                            description "QoS profile for the transmitted echo request packets";
                        }

                        ///global-operations/oam/lsp-trace/ldp/input/timeout
                        leaf timeout {
                            type uint32 {
                                range "1..10";
                            }
                            units "seconds";
                            default "5";
                            description "Time to wait for a reply after sending an echo request";
                        }

                        ///global-operations/oam/lsp-trace/ldp/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/ldp/input/min-ttl
                        leaf min-ttl {
                            type uint32 {
                                range "1..255";
                            }
                            default "1";
                            description "Initial TTL for the test";
                        }

                        ///global-operations/oam/lsp-trace/ldp/input/max-ttl
                        leaf max-ttl {
                            type uint32 {
                                range "1..255";
                            }
                            default "30";
                            description "Maximum TTL";
                        }

                        ///global-operations/oam/lsp-trace/ldp/input/max-fail
                        leaf max-fail {
                            type uint32 {
                                range "1..255";
                            }
                            default "5";
                            description "Maximum consecutive timeouts before terminating test";
                        }

                        ///global-operations/oam/lsp-trace/ldp/input/probe-count
                        leaf probe-count {
                            type uint32 {
                                range "1..10";
                            }
                            default "1";
                            description "Number of OAM trace probes to send per TTL";
                        }

                    }
                    output {

                        ///global-operations/oam/lsp-trace/ldp/output/operation-id
                        leaf operation-id {
                            type types-operation:operation-id;
                            description "ID assigned to the operation.";
                        }

                        ///global-operations/oam/lsp-trace/ldp/output/start-time
                        leaf start-time {
                            type types-operation:operation-timestamp;
                            description "Time when the operation started its execution.";
                        }

                        ///global-operations/oam/lsp-trace/ldp/output/results-path
                        leaf results-path {
                            type types-operation:operation-path;
                            description "Path to the results of the operation formatted as xpath.";
                        }

                        ///global-operations/oam/lsp-trace/ldp/output/results
                        container results {
                            description "Enter the results context";

                            ///global-operations/oam/lsp-trace/ldp/output/results/test-parameters
                            container test-parameters {
                                description "Enter the test-parameters context";

                                ///global-operations/oam/lsp-trace/ldp/output/results/test-parameters/prefix
                                leaf prefix {
                                    type types-sros:ip-prefix;
                                    description "The destination IP prefix for the test";
                                }

                                ///global-operations/oam/lsp-trace/ldp/output/results/test-parameters/path-destination
                                leaf path-destination {
                                    type types-sros:ip-address;
                                    description "The IP address of the path destination";
                                }

                                ///global-operations/oam/lsp-trace/ldp/output/results/test-parameters/path-destination-egress
                                choice path-destination-egress {
                                    ///global-operations/oam/lsp-trace/ldp/output/results/test-parameters/path-destination-egress/case-interface
                                    case case-interface {

                                        ///global-operations/oam/lsp-trace/ldp/output/results/test-parameters/path-destination-egress/case-interface/interface
                                        leaf interface {
                                            type types-sros:interface-name;
                                            description "The egress router interface, used in conjunction with path-destination";
                                        }

                                    }
                                    ///global-operations/oam/lsp-trace/ldp/output/results/test-parameters/path-destination-egress/case-next-hop
                                    case case-next-hop {

                                        ///global-operations/oam/lsp-trace/ldp/output/results/test-parameters/path-destination-egress/case-next-hop/next-hop
                                        leaf next-hop {
                                            type types-sros:ip-address;
                                            description "The egress IP next hop address, used in conjunction with path-destination";
                                        }

                                    }
                                }
                                ///global-operations/oam/lsp-trace/ldp/output/results/test-parameters/source-ip-address
                                leaf source-ip-address {
                                    type types-sros:ip-address;
                                    description "Source IP address";
                                }

                                ///global-operations/oam/lsp-trace/ldp/output/results/test-parameters/interval
                                leaf interval {
                                    type uint32 {
                                        range "1..10";
                                    }
                                    units "seconds";
                                    description "Minimum time to expire before the next request is sent";
                                }

                                ///global-operations/oam/lsp-trace/ldp/output/results/test-parameters/size
                                leaf size {
                                    type uint32 {
                                        range "1..9786";
                                    }
                                    units "bytes";
                                    description "Packet pad size of request";
                                }

                                ///global-operations/oam/lsp-trace/ldp/output/results/test-parameters/fc
                                leaf fc {
                                    type types-sros:fc-name;
                                    description "QoS Forwarding Class for the transmitted request packet(s)";
                                }

                                ///global-operations/oam/lsp-trace/ldp/output/results/test-parameters/profile
                                leaf profile {
                                    type types-qos:profile-in-out;
                                    description "QoS profile for the transmitted request packet(s)";
                                }

                                ///global-operations/oam/lsp-trace/ldp/output/results/test-parameters/timeout
                                leaf timeout {
                                    type uint32 {
                                        range "1..10";
                                    }
                                    units "seconds";
                                    description "Time router waits for a reply after sending a request";
                                }

                                ///global-operations/oam/lsp-trace/ldp/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/ldp/output/results/test-parameters/min-ttl
                                leaf min-ttl {
                                    type uint32 {
                                        range "1..255";
                                    }
                                    description "The initial time-to-live value for the test";
                                }

                                ///global-operations/oam/lsp-trace/ldp/output/results/test-parameters/max-ttl
                                leaf max-ttl {
                                    type uint32 {
                                        range "1..255";
                                    }
                                    description "The maximum time-to-live value for the test";
                                }

                                ///global-operations/oam/lsp-trace/ldp/output/results/test-parameters/max-fail
                                leaf max-fail {
                                    type uint32 {
                                        range "1..255";
                                    }
                                    description "The maximum number of consecutive timeouts allowed before terminating test";
                                }

                                ///global-operations/oam/lsp-trace/ldp/output/results/test-parameters/probe-count
                                leaf probe-count {
                                    type uint32 {
                                        range "1..10";
                                    }
                                    description "The number of OAM trace probes to send per TTL";
                                }

                            } // container test-parameters

                            ///global-operations/oam/lsp-trace/ldp/output/results/request-packet
                            container request-packet {
                                description "Enter the request-packet context";

                                ///global-operations/oam/lsp-trace/ldp/output/results/request-packet/size
                                leaf size {
                                    type uint32;
                                    units "bytes";
                                    description "Indicates the number of bytes of each request packet sent";
                                }

                                ///global-operations/oam/lsp-trace/ldp/output/results/request-packet/source-address
                                leaf source-address {
                                    type types-sros:ip-address;
                                    description "Indicates the source address of the test run";
                                }

                                ///global-operations/oam/lsp-trace/ldp/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/ldp/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/ldp/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/ldp/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/ldp/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/ldp/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/ldp/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/ldp/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/ldp/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/ldp/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/ldp/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/ldp/output/results/hop
                            list hop {
                                key "hop-index";
                                description "Per-hop test results";

                                ///global-operations/oam/lsp-trace/ldp/output/results/hop/hop-index
                                leaf hop-index {
                                    type uint32 {
                                        range "1..max";
                                    }
                                    description "The hop index of the test results";
                                }

                                ///global-operations/oam/lsp-trace/ldp/output/results/hop/probe
                                list probe {
                                    key "probe-index";
                                    description "Probe data for the specified test run";

                                    ///global-operations/oam/lsp-trace/ldp/output/results/hop/probe/probe-index
                                    leaf probe-index {
                                        type uint32 {
                                            range "1..10";
                                        }
                                        description "The probe index of lsp-trace reply, in the context of a hop";
                                    }

                                    ///global-operations/oam/lsp-trace/ldp/output/results/hop/probe/probe-instance
                                    list probe-instance {
                                        key "probe-instance-index";
                                        description "Probe instance of a probe, in the contex of a hop";

                                        ///global-operations/oam/lsp-trace/ldp/output/results/hop/probe/probe-instance/probe-instance-index
                                        leaf probe-instance-index {
                                            type uint32 {
                                                range "1..4294967295";
                                            }
                                            description "Index of probes with the specified test run";
                                        }

                                        ///global-operations/oam/lsp-trace/ldp/output/results/hop/probe/probe-instance/egress-interface
                                        leaf egress-interface {
                                            type types-sros:interface-name;
                                            description "The interface name this probe was transmitted from";
                                        }

                                        ///global-operations/oam/lsp-trace/ldp/output/results/hop/probe/probe-instance/round-trip-time
                                        leaf round-trip-time {
                                            type uint32;
                                            units "microseconds";
                                            description "Indicates the round trip time for the probe";
                                        }

                                        ///global-operations/oam/lsp-trace/ldp/output/results/hop/probe/probe-instance/status
                                        leaf status {
                                            type types-oam:response-status;
                                            description "The OAM response status code for the specified test";
                                        }

                                        ///global-operations/oam/lsp-trace/ldp/output/results/hop/probe/probe-instance/response-packet
                                        container response-packet {
                                            description "Data from packet received as a response to transmitted probe";

                                            ///global-operations/oam/lsp-trace/ldp/output/results/hop/probe/probe-instance/response-packet/size
                                            leaf size {
                                                type uint32;
                                                units "bytes";
                                                description "Indicates the number of bytes in the response packet for the probe";
                                            }

                                            ///global-operations/oam/lsp-trace/ldp/output/results/hop/probe/probe-instance/response-packet/source-address
                                            leaf source-address {
                                                type types-sros:ip-address;
                                                description
                                                    "Indicates the source address in the response packet for the specified
                                                     probe";
                                            }

                                            ///global-operations/oam/lsp-trace/ldp/output/results/hop/probe/probe-instance/response-packet/return-code
                                            leaf return-code {
                                                type int32;
                                                description "Indicates the OAM return code received in the probe response";
                                            }

                                            ///global-operations/oam/lsp-trace/ldp/output/results/hop/probe/probe-instance/response-packet/return-code-string
                                            leaf return-code-string {
                                                type types-oam:lsp-ping-trace-return-code;
                                                description "Description of the return-code";
                                            }

                                            ///global-operations/oam/lsp-trace/ldp/output/results/hop/probe/probe-instance/response-packet/return-subcode
                                            leaf return-subcode {
                                                type uint32;
                                                description
                                                    "Indicates the stack-depth where processing was terminated with
                                                     the value in the return-code";
                                            }

                                            ///global-operations/oam/lsp-trace/ldp/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/ldp/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/ldp/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/ldp/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/ldp/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/ldp/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/ldp/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/ldp/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/ldp/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/ldp/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/ldp/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/ldp/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/ldp/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/ldp/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/ldp/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/ldp/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/ldp/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/ldp/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/ldp/output/status
                        leaf status {
                            type types-operation:operation-status;
                            description "Status of the operation";
                        }

                        ///global-operations/oam/lsp-trace/ldp/output/error-message
                        leaf-list error-message {
                            type types-operation:operation-message;
                            description "Error messages reported during execution of the operation.";
                        }

                        ///global-operations/oam/lsp-trace/ldp/output/warning-message
                        leaf-list warning-message {
                            type types-operation:operation-message;
                            description "Warning messages reported during execution of the operation.";
                        }

                        ///global-operations/oam/lsp-trace/ldp/output/info-message
                        leaf-list info-message {
                            type types-operation:operation-message;
                            description "Info messages reported during execution of the operation.";
                        }

                        ///global-operations/oam/lsp-trace/ldp/output/end-time
                        leaf end-time {
                            type types-operation:operation-timestamp;
                            description "Time when the operation ended its execution.";
                        }

                    }
                } // action ldp

                ///global-operations/oam/lsp-trace/rsvp-te
                action rsvp-te {
                    description "Perform an RSVP-TE LSP trace test";

                    input {

                        ///global-operations/oam/lsp-trace/rsvp-te/input/lsp-name
                        leaf lsp-name {
                            type leafref {
                                path "/state:state/state:router/state:mpls/state:lsp/state:lsp-name";
                                require-instance "false";
                            }
                            mandatory true;
                            description "Name of the LSP to test";
                        }

                        ///global-operations/oam/lsp-trace/rsvp-te/input/path
                        leaf path {
                            type leafref {
                                path "/state:state/state:router/state:mpls/state:path/state:path-name";
                                require-instance "false";
                            }
                            description "Name of the MPLS path to test";
                        }

                        ///global-operations/oam/lsp-trace/rsvp-te/input/source-ip-address
                        leaf source-ip-address {
                            type types-sros:ip-address;
                            description "Source IP address";
                        }

                        ///global-operations/oam/lsp-trace/rsvp-te/input/interval
                        leaf interval {
                            type uint32 {
                                range "1..10";
                            }
                            units "seconds";
                            default "1";
                            description "Minimum time to expire before next echo request is sent";
                        }

                        ///global-operations/oam/lsp-trace/rsvp-te/input/size
                        leaf size {
                            type uint32 {
                                range "1..9786";
                            }
                            units "bytes";
                            default "1";
                            description "Echo request packet pad size";
                        }

                        ///global-operations/oam/lsp-trace/rsvp-te/input/fc
                        leaf fc {
                            type types-sros:fc-name;
                            default "be";
                            description "QoS forwarding class for the sent echo request packet";
                        }

                        ///global-operations/oam/lsp-trace/rsvp-te/input/profile
                        leaf profile {
                            type types-qos:profile-in-out;
                            default "out";
                            description "QoS profile for the transmitted echo request packets";
                        }

                        ///global-operations/oam/lsp-trace/rsvp-te/input/timeout
                        leaf timeout {
                            type uint32 {
                                range "1..10";
                            }
                            units "seconds";
                            default "5";
                            description "Time to wait for a reply after sending an echo request";
                        }

                        ///global-operations/oam/lsp-trace/rsvp-te/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/rsvp-te/input/min-ttl
                        leaf min-ttl {
                            type uint32 {
                                range "1..255";
                            }
                            default "1";
                            description "Initial TTL for the test";
                        }

                        ///global-operations/oam/lsp-trace/rsvp-te/input/max-ttl
                        leaf max-ttl {
                            type uint32 {
                                range "1..255";
                            }
                            default "30";
                            description "Maximum TTL";
                        }

                        ///global-operations/oam/lsp-trace/rsvp-te/input/max-fail
                        leaf max-fail {
                            type uint32 {
                                range "1..255";
                            }
                            default "5";
                            description "Maximum consecutive timeouts before terminating test";
                        }

                        ///global-operations/oam/lsp-trace/rsvp-te/input/probe-count
                        leaf probe-count {
                            type uint32 {
                                range "1..10";
                            }
                            default "1";
                            description "Number of OAM trace probes to send per TTL";
                        }

                    }
                    output {

                        ///global-operations/oam/lsp-trace/rsvp-te/output/operation-id
                        leaf operation-id {
                            type types-operation:operation-id;
                            description "ID assigned to the operation.";
                        }

                        ///global-operations/oam/lsp-trace/rsvp-te/output/start-time
                        leaf start-time {
                            type types-operation:operation-timestamp;
                            description "Time when the operation started its execution.";
                        }

                        ///global-operations/oam/lsp-trace/rsvp-te/output/results-path
                        leaf results-path {
                            type types-operation:operation-path;
                            description "Path to the results of the operation formatted as xpath.";
                        }

                        ///global-operations/oam/lsp-trace/rsvp-te/output/results
                        container results {
                            description "Enter the results context";

                            ///global-operations/oam/lsp-trace/rsvp-te/output/results/test-parameters
                            container test-parameters {
                                description "Enter the test-parameters context";

                                ///global-operations/oam/lsp-trace/rsvp-te/output/results/test-parameters/lsp-name
                                leaf lsp-name {
                                    type types-sros:named-item-64;
                                    description "The name of the LSP to be tested";
                                }

                                ///global-operations/oam/lsp-trace/rsvp-te/output/results/test-parameters/path
                                leaf path {
                                    type types-sros:named-item-64;
                                    description "The name of the MPLS path to be tested";
                                }

                                ///global-operations/oam/lsp-trace/rsvp-te/output/results/test-parameters/source-ip-address
                                leaf source-ip-address {
                                    type types-sros:ip-address;
                                    description "Source IP address";
                                }

                                ///global-operations/oam/lsp-trace/rsvp-te/output/results/test-parameters/interval
                                leaf interval {
                                    type uint32 {
                                        range "1..10";
                                    }
                                    units "seconds";
                                    description "Minimum time to expire before the next request is sent";
                                }

                                ///global-operations/oam/lsp-trace/rsvp-te/output/results/test-parameters/size
                                leaf size {
                                    type uint32 {
                                        range "1..9786";
                                    }
                                    units "bytes";
                                    description "Packet pad size of request";
                                }

                                ///global-operations/oam/lsp-trace/rsvp-te/output/results/test-parameters/fc
                                leaf fc {
                                    type types-sros:fc-name;
                                    description "QoS Forwarding Class for the transmitted request packet(s)";
                                }

                                ///global-operations/oam/lsp-trace/rsvp-te/output/results/test-parameters/profile
                                leaf profile {
                                    type types-qos:profile-in-out;
                                    description "QoS profile for the transmitted request packet(s)";
                                }

                                ///global-operations/oam/lsp-trace/rsvp-te/output/results/test-parameters/timeout
                                leaf timeout {
                                    type uint32 {
                                        range "1..10";
                                    }
                                    units "seconds";
                                    description "Time router waits for a reply after sending a request";
                                }

                                ///global-operations/oam/lsp-trace/rsvp-te/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/rsvp-te/output/results/test-parameters/min-ttl
                                leaf min-ttl {
                                    type uint32 {
                                        range "1..255";
                                    }
                                    description "The initial time-to-live value for the test";
                                }

                                ///global-operations/oam/lsp-trace/rsvp-te/output/results/test-parameters/max-ttl
                                leaf max-ttl {
                                    type uint32 {
                                        range "1..255";
                                    }
                                    description "The maximum time-to-live value for the test";
                                }

                                ///global-operations/oam/lsp-trace/rsvp-te/output/results/test-parameters/max-fail
                                leaf max-fail {
                                    type uint32 {
                                        range "1..255";
                                    }
                                    description "The maximum number of consecutive timeouts allowed before terminating test";
                                }

                                ///global-operations/oam/lsp-trace/rsvp-te/output/results/test-parameters/probe-count
                                leaf probe-count {
                                    type uint32 {
                                        range "1..10";
                                    }
                                    description "The number of OAM trace probes to send per TTL";
                                }

                            } // container test-parameters

                            ///global-operations/oam/lsp-trace/rsvp-te/output/results/request-packet
                            container request-packet {
                                description "Enter the request-packet context";

                                ///global-operations/oam/lsp-trace/rsvp-te/output/results/request-packet/size
                                leaf size {
                                    type uint32;
                                    units "bytes";
                                    description "Indicates the number of bytes of each request packet sent";
                                }

                                ///global-operations/oam/lsp-trace/rsvp-te/output/results/request-packet/source-address
                                leaf source-address {
                                    type types-sros:ip-address;
                                    description "Indicates the source address of the test run";
                                }

                                ///global-operations/oam/lsp-trace/rsvp-te/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/rsvp-te/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/rsvp-te/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/rsvp-te/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/rsvp-te/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/rsvp-te/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/rsvp-te/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/rsvp-te/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/rsvp-te/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/rsvp-te/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/rsvp-te/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/rsvp-te/output/results/hop
                            list hop {
                                key "hop-index";
                                description "Per-hop test results";

                                ///global-operations/oam/lsp-trace/rsvp-te/output/results/hop/hop-index
                                leaf hop-index {
                                    type uint32 {
                                        range "1..max";
                                    }
                                    description "The hop index of the test results";
                                }

                                ///global-operations/oam/lsp-trace/rsvp-te/output/results/hop/probe
                                list probe {
                                    key "probe-index";
                                    description "Probe data for the specified test run";

                                    ///global-operations/oam/lsp-trace/rsvp-te/output/results/hop/probe/probe-index
                                    leaf probe-index {
                                        type uint32 {
                                            range "1..10";
                                        }
                                        description "The probe index of lsp-trace reply, in the context of a hop";
                                    }

                                    ///global-operations/oam/lsp-trace/rsvp-te/output/results/hop/probe/probe-instance
                                    list probe-instance {
                                        key "probe-instance-index";
                                        description "Probe instance of a probe, in the contex of a hop";

                                        ///global-operations/oam/lsp-trace/rsvp-te/output/results/hop/probe/probe-instance/probe-instance-index
                                        leaf probe-instance-index {
                                            type uint32 {
                                                range "1..4294967295";
                                            }
                                            description "Index of probes with the specified test run";
                                        }

                                        ///global-operations/oam/lsp-trace/rsvp-te/output/results/hop/probe/probe-instance/egress-interface
                                        leaf egress-interface {
                                            type types-sros:interface-name;
                                            description "The interface name this probe was transmitted from";
                                        }

                                        ///global-operations/oam/lsp-trace/rsvp-te/output/results/hop/probe/probe-instance/round-trip-time
                                        leaf round-trip-time {
                                            type uint32;
                                            units "microseconds";
                                            description "Indicates the round trip time for the probe";
                                        }

                                        ///global-operations/oam/lsp-trace/rsvp-te/output/results/hop/probe/probe-instance/status
                                        leaf status {
                                            type types-oam:response-status;
                                            description "The OAM response status code for the specified test";
                                        }

                                        ///global-operations/oam/lsp-trace/rsvp-te/output/results/hop/probe/probe-instance/response-packet
                                        container response-packet {
                                            description "Data from packet received as a response to transmitted probe";

                                            ///global-operations/oam/lsp-trace/rsvp-te/output/results/hop/probe/probe-instance/response-packet/size
                                            leaf size {
                                                type uint32;
                                                units "bytes";
                                                description "Indicates the number of bytes in the response packet for the probe";
                                            }

                                            ///global-operations/oam/lsp-trace/rsvp-te/output/results/hop/probe/probe-instance/response-packet/source-address
                                            leaf source-address {
                                                type types-sros:ip-address;
                                                description
                                                    "Indicates the source address in the response packet for the specified
                                                     probe";
                                            }

                                            ///global-operations/oam/lsp-trace/rsvp-te/output/results/hop/probe/probe-instance/response-packet/return-code
                                            leaf return-code {
                                                type int32;
                                                description "Indicates the OAM return code received in the probe response";
                                            }

                                            ///global-operations/oam/lsp-trace/rsvp-te/output/results/hop/probe/probe-instance/response-packet/return-code-string
                                            leaf return-code-string {
                                                type types-oam:lsp-ping-trace-return-code;
                                                description "Description of the return-code";
                                            }

                                            ///global-operations/oam/lsp-trace/rsvp-te/output/results/hop/probe/probe-instance/response-packet/return-subcode
                                            leaf return-subcode {
                                                type uint32;
                                                description
                                                    "Indicates the stack-depth where processing was terminated with
                                                     the value in the return-code";
                                            }

                                            ///global-operations/oam/lsp-trace/rsvp-te/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/rsvp-te/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/rsvp-te/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/rsvp-te/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/rsvp-te/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/rsvp-te/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/rsvp-te/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/rsvp-te/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/rsvp-te/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/rsvp-te/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/rsvp-te/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/rsvp-te/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/rsvp-te/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/rsvp-te/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/rsvp-te/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/rsvp-te/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/rsvp-te/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/rsvp-te/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/rsvp-te/output/status
                        leaf status {
                            type types-operation:operation-status;
                            description "Status of the operation";
                        }

                        ///global-operations/oam/lsp-trace/rsvp-te/output/error-message
                        leaf-list error-message {
                            type types-operation:operation-message;
                            description "Error messages reported during execution of the operation.";
                        }

                        ///global-operations/oam/lsp-trace/rsvp-te/output/warning-message
                        leaf-list warning-message {
                            type types-operation:operation-message;
                            description "Warning messages reported during execution of the operation.";
                        }

                        ///global-operations/oam/lsp-trace/rsvp-te/output/info-message
                        leaf-list info-message {
                            type types-operation:operation-message;
                            description "Info messages reported during execution of the operation.";
                        }

                        ///global-operations/oam/lsp-trace/rsvp-te/output/end-time
                        leaf end-time {
                            type types-operation:operation-timestamp;
                            description "Time when the operation ended its execution.";
                        }

                    }
                } // action rsvp-te

                ///global-operations/oam/lsp-trace/sr-isis
                action sr-isis {
                    description "Perform an SR-ISIS LSP trace test";

                    input {

                        ///global-operations/oam/lsp-trace/sr-isis/input/prefix
                        leaf prefix {
                            type types-sros:ip-prefix;
                            mandatory true;
                            description "Destination IP prefix for the test";
                        }

                        ///global-operations/oam/lsp-trace/sr-isis/input/igp-instance
                        leaf igp-instance {
                            type uint32 {
                                range "0..127";
                            }
                            default "0";
                            description "IGP instance for the SR-ISIS test";
                        }

                        ///global-operations/oam/lsp-trace/sr-isis/input/flex-algo
                        leaf flex-algo {
                            type uint32 {
                                range "128..255";
                            }
                            description "Segment Routing Flexible Algorithm for the test";
                        }

                        ///global-operations/oam/lsp-trace/sr-isis/input/path-destination
                        leaf path-destination {
                            type types-sros:ip-address;
                            description "IP address of the path destination";
                        }

                        ///global-operations/oam/lsp-trace/sr-isis/input/path-destination-egress
                        choice path-destination-egress {
                            ///global-operations/oam/lsp-trace/sr-isis/input/path-destination-egress/case-interface
                            case case-interface {

                                ///global-operations/oam/lsp-trace/sr-isis/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/sr-isis/input/path-destination-egress/case-next-hop
                            case case-next-hop {

                                ///global-operations/oam/lsp-trace/sr-isis/input/path-destination-egress/case-next-hop/next-hop
                                leaf next-hop {
                                    type types-sros:ip-address;
                                    description "Egress IP next hop address to use with path destination";
                                }

                            }
                        }
                        ///global-operations/oam/lsp-trace/sr-isis/input/source-ip-address
                        leaf source-ip-address {
                            type types-sros:ip-address;
                            description "Source IP address";
                        }

                        ///global-operations/oam/lsp-trace/sr-isis/input/interval
                        leaf interval {
                            type uint32 {
                                range "1..10";
                            }
                            units "seconds";
                            default "1";
                            description "Minimum time to expire before next echo request is sent";
                        }

                        ///global-operations/oam/lsp-trace/sr-isis/input/size
                        leaf size {
                            type uint32 {
                                range "1..9786";
                            }
                            units "bytes";
                            default "1";
                            description "Echo request packet pad size";
                        }

                        ///global-operations/oam/lsp-trace/sr-isis/input/fc
                        leaf fc {
                            type types-sros:fc-name;
                            default "be";
                            description "QoS forwarding class for the sent echo request packet";
                        }

                        ///global-operations/oam/lsp-trace/sr-isis/input/profile
                        leaf profile {
                            type types-qos:profile-in-out;
                            default "out";
                            description "QoS profile for the transmitted echo request packets";
                        }

                        ///global-operations/oam/lsp-trace/sr-isis/input/timeout
                        leaf timeout {
                            type uint32 {
                                range "1..10";
                            }
                            units "seconds";
                            default "5";
                            description "Time to wait for a reply after sending an echo request";
                        }

                        ///global-operations/oam/lsp-trace/sr-isis/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/sr-isis/input/min-ttl
                        leaf min-ttl {
                            type uint32 {
                                range "1..255";
                            }
                            default "1";
                            description "Initial TTL for the test";
                        }

                        ///global-operations/oam/lsp-trace/sr-isis/input/max-ttl
                        leaf max-ttl {
                            type uint32 {
                                range "1..255";
                            }
                            default "30";
                            description "Maximum TTL";
                        }

                        ///global-operations/oam/lsp-trace/sr-isis/input/max-fail
                        leaf max-fail {
                            type uint32 {
                                range "1..255";
                            }
                            default "5";
                            description "Maximum consecutive timeouts before terminating test";
                        }

                        ///global-operations/oam/lsp-trace/sr-isis/input/probe-count
                        leaf probe-count {
                            type uint32 {
                                range "1..10";
                            }
                            default "1";
                            description "Number of OAM trace probes to send per TTL";
                        }

                    }
                    output {

                        ///global-operations/oam/lsp-trace/sr-isis/output/operation-id
                        leaf operation-id {
                            type types-operation:operation-id;
                            description "ID assigned to the operation.";
                        }

                        ///global-operations/oam/lsp-trace/sr-isis/output/start-time
                        leaf start-time {
                            type types-operation:operation-timestamp;
                            description "Time when the operation started its execution.";
                        }

                        ///global-operations/oam/lsp-trace/sr-isis/output/results-path
                        leaf results-path {
                            type types-operation:operation-path;
                            description "Path to the results of the operation formatted as xpath.";
                        }

                        ///global-operations/oam/lsp-trace/sr-isis/output/results
                        container results {
                            description "Enter the results context";

                            ///global-operations/oam/lsp-trace/sr-isis/output/results/test-parameters
                            container test-parameters {
                                description "Enter the test-parameters context";

                                ///global-operations/oam/lsp-trace/sr-isis/output/results/test-parameters/prefix
                                leaf prefix {
                                    type types-sros:ip-prefix;
                                    description "The destination IP prefix for the test";
                                }

                                ///global-operations/oam/lsp-trace/sr-isis/output/results/test-parameters/igp-instance
                                leaf igp-instance {
                                    type uint32 {
                                        range "0..127";
                                    }
                                    description "The IGP instance for the test";
                                }

                                ///global-operations/oam/lsp-trace/sr-isis/output/results/test-parameters/flex-algo
                                leaf flex-algo {
                                    type uint32 {
                                        range "128..255";
                                    }
                                    description "Segment Routing Flexible Algorithm for the test";
                                }

                                ///global-operations/oam/lsp-trace/sr-isis/output/results/test-parameters/path-destination
                                leaf path-destination {
                                    type types-sros:ip-address;
                                    description "The IP address of the path destination";
                                }

                                ///global-operations/oam/lsp-trace/sr-isis/output/results/test-parameters/path-destination-egress
                                choice path-destination-egress {
                                    ///global-operations/oam/lsp-trace/sr-isis/output/results/test-parameters/path-destination-egress/case-interface
                                    case case-interface {

                                        ///global-operations/oam/lsp-trace/sr-isis/output/results/test-parameters/path-destination-egress/case-interface/interface
                                        leaf interface {
                                            type types-sros:interface-name;
                                            description "The egress router interface, used in conjunction with path-destination";
                                        }

                                    }
                                    ///global-operations/oam/lsp-trace/sr-isis/output/results/test-parameters/path-destination-egress/case-next-hop
                                    case case-next-hop {

                                        ///global-operations/oam/lsp-trace/sr-isis/output/results/test-parameters/path-destination-egress/case-next-hop/next-hop
                                        leaf next-hop {
                                            type types-sros:ip-address;
                                            description "The egress IP next hop address, used in conjunction with path-destination";
                                        }

                                    }
                                }
                                ///global-operations/oam/lsp-trace/sr-isis/output/results/test-parameters/source-ip-address
                                leaf source-ip-address {
                                    type types-sros:ip-address;
                                    description "Source IP address";
                                }

                                ///global-operations/oam/lsp-trace/sr-isis/output/results/test-parameters/interval
                                leaf interval {
                                    type uint32 {
                                        range "1..10";
                                    }
                                    units "seconds";
                                    description "Minimum time to expire before the next request is sent";
                                }

                                ///global-operations/oam/lsp-trace/sr-isis/output/results/test-parameters/size
                                leaf size {
                                    type uint32 {
                                        range "1..9786";
                                    }
                                    units "bytes";
                                    description "Packet pad size of request";
                                }

                                ///global-operations/oam/lsp-trace/sr-isis/output/results/test-parameters/fc
                                leaf fc {
                                    type types-sros:fc-name;
                                    description "QoS Forwarding Class for the transmitted request packet(s)";
                                }

                                ///global-operations/oam/lsp-trace/sr-isis/output/results/test-parameters/profile
                                leaf profile {
                                    type types-qos:profile-in-out;
                                    description "QoS profile for the transmitted request packet(s)";
                                }

                                ///global-operations/oam/lsp-trace/sr-isis/output/results/test-parameters/timeout
                                leaf timeout {
                                    type uint32 {
                                        range "1..10";
                                    }
                                    units "seconds";
                                    description "Time router waits for a reply after sending a request";
                                }

                                ///global-operations/oam/lsp-trace/sr-isis/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/sr-isis/output/results/test-parameters/min-ttl
                                leaf min-ttl {
                                    type uint32 {
                                        range "1..255";
                                    }
                                    description "The initial time-to-live value for the test";
                                }

                                ///global-operations/oam/lsp-trace/sr-isis/output/results/test-parameters/max-ttl
                                leaf max-ttl {
                                    type uint32 {
                                        range "1..255";
                                    }
                                    description "The maximum time-to-live value for the test";
                                }

                                ///global-operations/oam/lsp-trace/sr-isis/output/results/test-parameters/max-fail
                                leaf max-fail {
                                    type uint32 {
                                        range "1..255";
                                    }
                                    description "The maximum number of consecutive timeouts allowed before terminating test";
                                }

                                ///global-operations/oam/lsp-trace/sr-isis/output/results/test-parameters/probe-count
                                leaf probe-count {
                                    type uint32 {
                                        range "1..10";
                                    }
                                    description "The number of OAM trace probes to send per TTL";
                                }

                            } // container test-parameters

                            ///global-operations/oam/lsp-trace/sr-isis/output/results/request-packet
                            container request-packet {
                                description "Enter the request-packet context";

                                ///global-operations/oam/lsp-trace/sr-isis/output/results/request-packet/size
                                leaf size {
                                    type uint32;
                                    units "bytes";
                                    description "Indicates the number of bytes of each request packet sent";
                                }

                                ///global-operations/oam/lsp-trace/sr-isis/output/results/request-packet/source-address
                                leaf source-address {
                                    type types-sros:ip-address;
                                    description "Indicates the source address of the test run";
                                }

                                ///global-operations/oam/lsp-trace/sr-isis/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/sr-isis/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/sr-isis/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/sr-isis/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/sr-isis/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/sr-isis/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/sr-isis/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/sr-isis/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/sr-isis/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/sr-isis/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/sr-isis/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/sr-isis/output/results/hop
                            list hop {
                                key "hop-index";
                                description "Per-hop test results";

                                ///global-operations/oam/lsp-trace/sr-isis/output/results/hop/hop-index
                                leaf hop-index {
                                    type uint32 {
                                        range "1..max";
                                    }
                                    description "The hop index of the test results";
                                }

                                ///global-operations/oam/lsp-trace/sr-isis/output/results/hop/probe
                                list probe {
                                    key "probe-index";
                                    description "Probe data for the specified test run";

                                    ///global-operations/oam/lsp-trace/sr-isis/output/results/hop/probe/probe-index
                                    leaf probe-index {
                                        type uint32 {
                                            range "1..10";
                                        }
                                        description "The probe index of lsp-trace reply, in the context of a hop";
                                    }

                                    ///global-operations/oam/lsp-trace/sr-isis/output/results/hop/probe/probe-instance
                                    list probe-instance {
                                        key "probe-instance-index";
                                        description "Probe instance of a probe, in the contex of a hop";

                                        ///global-operations/oam/lsp-trace/sr-isis/output/results/hop/probe/probe-instance/probe-instance-index
                                        leaf probe-instance-index {
                                            type uint32 {
                                                range "1..4294967295";
                                            }
                                            description "Index of probes with the specified test run";
                                        }

                                        ///global-operations/oam/lsp-trace/sr-isis/output/results/hop/probe/probe-instance/egress-interface
                                        leaf egress-interface {
                                            type types-sros:interface-name;
                                            description "The interface name this probe was transmitted from";
                                        }

                                        ///global-operations/oam/lsp-trace/sr-isis/output/results/hop/probe/probe-instance/round-trip-time
                                        leaf round-trip-time {
                                            type uint32;
                                            units "microseconds";
                                            description "Indicates the round trip time for the probe";
                                        }

                                        ///global-operations/oam/lsp-trace/sr-isis/output/results/hop/probe/probe-instance/status
                                        leaf status {
                                            type types-oam:response-status;
                                            description "The OAM response status code for the specified test";
                                        }

                                        ///global-operations/oam/lsp-trace/sr-isis/output/results/hop/probe/probe-instance/response-packet
                                        container response-packet {
                                            description "Data from packet received as a response to transmitted probe";

                                            ///global-operations/oam/lsp-trace/sr-isis/output/results/hop/probe/probe-instance/response-packet/size
                                            leaf size {
                                                type uint32;
                                                units "bytes";
                                                description "Indicates the number of bytes in the response packet for the probe";
                                            }

                                            ///global-operations/oam/lsp-trace/sr-isis/output/results/hop/probe/probe-instance/response-packet/source-address
                                            leaf source-address {
                                                type types-sros:ip-address;
                                                description
                                                    "Indicates the source address in the response packet for the specified
                                                     probe";
                                            }

                                            ///global-operations/oam/lsp-trace/sr-isis/output/results/hop/probe/probe-instance/response-packet/return-code
                                            leaf return-code {
                                                type int32;
                                                description "Indicates the OAM return code received in the probe response";
                                            }

                                            ///global-operations/oam/lsp-trace/sr-isis/output/results/hop/probe/probe-instance/response-packet/return-code-string
                                            leaf return-code-string {
                                                type types-oam:lsp-ping-trace-return-code;
                                                description "Description of the return-code";
                                            }

                                            ///global-operations/oam/lsp-trace/sr-isis/output/results/hop/probe/probe-instance/response-packet/return-subcode
                                            leaf return-subcode {
                                                type uint32;
                                                description
                                                    "Indicates the stack-depth where processing was terminated with
                                                     the value in the return-code";
                                            }

                                            ///global-operations/oam/lsp-trace/sr-isis/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/sr-isis/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/sr-isis/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/sr-isis/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/sr-isis/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/sr-isis/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/sr-isis/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/sr-isis/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/sr-isis/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/sr-isis/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/sr-isis/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/sr-isis/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/sr-isis/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/sr-isis/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/sr-isis/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/sr-isis/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/sr-isis/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/sr-isis/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/sr-isis/output/status
                        leaf status {
                            type types-operation:operation-status;
                            description "Status of the operation";
                        }

                        ///global-operations/oam/lsp-trace/sr-isis/output/error-message
                        leaf-list error-message {
                            type types-operation:operation-message;
                            description "Error messages reported during execution of the operation.";
                        }

                        ///global-operations/oam/lsp-trace/sr-isis/output/warning-message
                        leaf-list warning-message {
                            type types-operation:operation-message;
                            description "Warning messages reported during execution of the operation.";
                        }

                        ///global-operations/oam/lsp-trace/sr-isis/output/info-message
                        leaf-list info-message {
                            type types-operation:operation-message;
                            description "Info messages reported during execution of the operation.";
                        }

                        ///global-operations/oam/lsp-trace/sr-isis/output/end-time
                        leaf end-time {
                            type types-operation:operation-timestamp;
                            description "Time when the operation ended its execution.";
                        }

                    }
                } // action sr-isis

                ///global-operations/oam/lsp-trace/sr-ospf
                action sr-ospf {
                    description "Perform an SR-OSPF LSP trace test";

                    input {

                        ///global-operations/oam/lsp-trace/sr-ospf/input/prefix
                        leaf prefix {
                            type types-sros:ip-prefix;
                            mandatory true;
                            description "Destination IP prefix for the test";
                        }

                        ///global-operations/oam/lsp-trace/sr-ospf/input/igp-instance
                        leaf igp-instance {
                            type uint32 {
                                range "0..31";
                            }
                            default "0";
                            description "IGP instance for the SR-OSPF test";
                        }

                        ///global-operations/oam/lsp-trace/sr-ospf/input/flex-algo
                        leaf flex-algo {
                            type uint32 {
                                range "128..255";
                            }
                            description "Segment Routing Flexible Algorithm for the test";
                        }

                        ///global-operations/oam/lsp-trace/sr-ospf/input/path-destination
                        leaf path-destination {
                            type types-sros:ipv4-address;
                            description "IP address of the path destination";
                        }

                        ///global-operations/oam/lsp-trace/sr-ospf/input/path-destination-egress
                        choice path-destination-egress {
                            ///global-operations/oam/lsp-trace/sr-ospf/input/path-destination-egress/case-interface
                            case case-interface {

                                ///global-operations/oam/lsp-trace/sr-ospf/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/sr-ospf/input/path-destination-egress/case-next-hop
                            case case-next-hop {

                                ///global-operations/oam/lsp-trace/sr-ospf/input/path-destination-egress/case-next-hop/next-hop
                                leaf next-hop {
                                    type types-sros:ipv4-address;
                                    description "Egress IP next hop address to use with path destination";
                                }

                            }
                        }
                        ///global-operations/oam/lsp-trace/sr-ospf/input/source-ip-address
                        leaf source-ip-address {
                            type types-sros:ipv4-address;
                            description "Source IP address";
                        }

                        ///global-operations/oam/lsp-trace/sr-ospf/input/interval
                        leaf interval {
                            type uint32 {
                                range "1..10";
                            }
                            units "seconds";
                            default "1";
                            description "Minimum time to expire before next echo request is sent";
                        }

                        ///global-operations/oam/lsp-trace/sr-ospf/input/size
                        leaf size {
                            type uint32 {
                                range "1..9786";
                            }
                            units "bytes";
                            default "1";
                            description "Echo request packet pad size";
                        }

                        ///global-operations/oam/lsp-trace/sr-ospf/input/fc
                        leaf fc {
                            type types-sros:fc-name;
                            default "be";
                            description "QoS forwarding class for the sent echo request packet";
                        }

                        ///global-operations/oam/lsp-trace/sr-ospf/input/profile
                        leaf profile {
                            type types-qos:profile-in-out;
                            default "out";
                            description "QoS profile for the transmitted echo request packets";
                        }

                        ///global-operations/oam/lsp-trace/sr-ospf/input/timeout
                        leaf timeout {
                            type uint32 {
                                range "1..10";
                            }
                            units "seconds";
                            default "5";
                            description "Time to wait for a reply after sending an echo request";
                        }

                        ///global-operations/oam/lsp-trace/sr-ospf/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/sr-ospf/input/min-ttl
                        leaf min-ttl {
                            type uint32 {
                                range "1..255";
                            }
                            default "1";
                            description "Initial TTL for the test";
                        }

                        ///global-operations/oam/lsp-trace/sr-ospf/input/max-ttl
                        leaf max-ttl {
                            type uint32 {
                                range "1..255";
                            }
                            default "30";
                            description "Maximum TTL";
                        }

                        ///global-operations/oam/lsp-trace/sr-ospf/input/max-fail
                        leaf max-fail {
                            type uint32 {
                                range "1..255";
                            }
                            default "5";
                            description "Maximum consecutive timeouts before terminating test";
                        }

                        ///global-operations/oam/lsp-trace/sr-ospf/input/probe-count
                        leaf probe-count {
                            type uint32 {
                                range "1..10";
                            }
                            default "1";
                            description "Number of OAM trace probes to send per TTL";
                        }

                    }
                    output {

                        ///global-operations/oam/lsp-trace/sr-ospf/output/operation-id
                        leaf operation-id {
                            type types-operation:operation-id;
                            description "ID assigned to the operation.";
                        }

                        ///global-operations/oam/lsp-trace/sr-ospf/output/start-time
                        leaf start-time {
                            type types-operation:operation-timestamp;
                            description "Time when the operation started its execution.";
                        }

                        ///global-operations/oam/lsp-trace/sr-ospf/output/results-path
                        leaf results-path {
                            type types-operation:operation-path;
                            description "Path to the results of the operation formatted as xpath.";
                        }

                        ///global-operations/oam/lsp-trace/sr-ospf/output/results
                        container results {
                            description "Enter the results context";

                            ///global-operations/oam/lsp-trace/sr-ospf/output/results/test-parameters
                            container test-parameters {
                                description "Enter the test-parameters context";

                                ///global-operations/oam/lsp-trace/sr-ospf/output/results/test-parameters/prefix
                                leaf prefix {
                                    type types-sros:ip-prefix;
                                    description "The destination IP prefix for the test";
                                }

                                ///global-operations/oam/lsp-trace/sr-ospf/output/results/test-parameters/igp-instance
                                leaf igp-instance {
                                    type uint32 {
                                        range "0..127";
                                    }
                                    description "The IGP instance for the test";
                                }

                                ///global-operations/oam/lsp-trace/sr-ospf/output/results/test-parameters/flex-algo
                                leaf flex-algo {
                                    type uint32 {
                                        range "128..255";
                                    }
                                    description "Segment Routing Flexible Algorithm for the test";
                                }

                                ///global-operations/oam/lsp-trace/sr-ospf/output/results/test-parameters/path-destination
                                leaf path-destination {
                                    type types-sros:ip-address;
                                    description "The IP address of the path destination";
                                }

                                ///global-operations/oam/lsp-trace/sr-ospf/output/results/test-parameters/path-destination-egress
                                choice path-destination-egress {
                                    ///global-operations/oam/lsp-trace/sr-ospf/output/results/test-parameters/path-destination-egress/case-interface
                                    case case-interface {

                                        ///global-operations/oam/lsp-trace/sr-ospf/output/results/test-parameters/path-destination-egress/case-interface/interface
                                        leaf interface {
                                            type types-sros:interface-name;
                                            description "The egress router interface, used in conjunction with path-destination";
                                        }

                                    }
                                    ///global-operations/oam/lsp-trace/sr-ospf/output/results/test-parameters/path-destination-egress/case-next-hop
                                    case case-next-hop {

                                        ///global-operations/oam/lsp-trace/sr-ospf/output/results/test-parameters/path-destination-egress/case-next-hop/next-hop
                                        leaf next-hop {
                                            type types-sros:ip-address;
                                            description "The egress IP next hop address, used in conjunction with path-destination";
                                        }

                                    }
                                }
                                ///global-operations/oam/lsp-trace/sr-ospf/output/results/test-parameters/source-ip-address
                                leaf source-ip-address {
                                    type types-sros:ipv4-address;
                                    description "Source IP address";
                                }

                                ///global-operations/oam/lsp-trace/sr-ospf/output/results/test-parameters/interval
                                leaf interval {
                                    type uint32 {
                                        range "1..10";
                                    }
                                    units "seconds";
                                    description "Minimum time to expire before the next request is sent";
                                }

                                ///global-operations/oam/lsp-trace/sr-ospf/output/results/test-parameters/size
                                leaf size {
                                    type uint32 {
                                        range "1..9786";
                                    }
                                    units "bytes";
                                    description "Packet pad size of request";
                                }

                                ///global-operations/oam/lsp-trace/sr-ospf/output/results/test-parameters/fc
                                leaf fc {
                                    type types-sros:fc-name;
                                    description "QoS Forwarding Class for the transmitted request packet(s)";
                                }

                                ///global-operations/oam/lsp-trace/sr-ospf/output/results/test-parameters/profile
                                leaf profile {
                                    type types-qos:profile-in-out;
                                    description "QoS profile for the transmitted request packet(s)";
                                }

                                ///global-operations/oam/lsp-trace/sr-ospf/output/results/test-parameters/timeout
                                leaf timeout {
                                    type uint32 {
                                        range "1..10";
                                    }
                                    units "seconds";
                                    description "Time router waits for a reply after sending a request";
                                }

                                ///global-operations/oam/lsp-trace/sr-ospf/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/sr-ospf/output/results/test-parameters/min-ttl
                                leaf min-ttl {
                                    type uint32 {
                                        range "1..255";
                                    }
                                    description "The initial time-to-live value for the test";
                                }

                                ///global-operations/oam/lsp-trace/sr-ospf/output/results/test-parameters/max-ttl
                                leaf max-ttl {
                                    type uint32 {
                                        range "1..255";
                                    }
                                    description "The maximum time-to-live value for the test";
                                }

                                ///global-operations/oam/lsp-trace/sr-ospf/output/results/test-parameters/max-fail
                                leaf max-fail {
                                    type uint32 {
                                        range "1..255";
                                    }
                                    description "The maximum number of consecutive timeouts allowed before terminating test";
                                }

                                ///global-operations/oam/lsp-trace/sr-ospf/output/results/test-parameters/probe-count
                                leaf probe-count {
                                    type uint32 {
                                        range "1..10";
                                    }
                                    description "The number of OAM trace probes to send per TTL";
                                }

                            } // container test-parameters

                            ///global-operations/oam/lsp-trace/sr-ospf/output/results/request-packet
                            container request-packet {
                                description "Enter the request-packet context";

                                ///global-operations/oam/lsp-trace/sr-ospf/output/results/request-packet/size
                                leaf size {
                                    type uint32;
                                    units "bytes";
                                    description "Indicates the number of bytes of each request packet sent";
                                }

                                ///global-operations/oam/lsp-trace/sr-ospf/output/results/request-packet/source-address
                                leaf source-address {
                                    type types-sros:ip-address;
                                    description "Indicates the source address of the test run";
                                }

                                ///global-operations/oam/lsp-trace/sr-ospf/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/sr-ospf/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/sr-ospf/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/sr-ospf/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/sr-ospf/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/sr-ospf/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/sr-ospf/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/sr-ospf/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/sr-ospf/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/sr-ospf/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/sr-ospf/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/sr-ospf/output/results/hop
                            list hop {
                                key "hop-index";
                                description "Per-hop test results";

                                ///global-operations/oam/lsp-trace/sr-ospf/output/results/hop/hop-index
                                leaf hop-index {
                                    type uint32 {
                                        range "1..max";
                                    }
                                    description "The hop index of the test results";
                                }

                                ///global-operations/oam/lsp-trace/sr-ospf/output/results/hop/probe
                                list probe {
                                    key "probe-index";
                                    description "Probe data for the specified test run";

                                    ///global-operations/oam/lsp-trace/sr-ospf/output/results/hop/probe/probe-index
                                    leaf probe-index {
                                        type uint32 {
                                            range "1..10";
                                        }
                                        description "The probe index of lsp-trace reply, in the context of a hop";
                                    }

                                    ///global-operations/oam/lsp-trace/sr-ospf/output/results/hop/probe/probe-instance
                                    list probe-instance {
                                        key "probe-instance-index";
                                        description "Probe instance of a probe, in the contex of a hop";

                                        ///global-operations/oam/lsp-trace/sr-ospf/output/results/hop/probe/probe-instance/probe-instance-index
                                        leaf probe-instance-index {
                                            type uint32 {
                                                range "1..4294967295";
                                            }
                                            description "Index of probes with the specified test run";
                                        }

                                        ///global-operations/oam/lsp-trace/sr-ospf/output/results/hop/probe/probe-instance/egress-interface
                                        leaf egress-interface {
                                            type types-sros:interface-name;
                                            description "The interface name this probe was transmitted from";
                                        }

                                        ///global-operations/oam/lsp-trace/sr-ospf/output/results/hop/probe/probe-instance/round-trip-time
                                        leaf round-trip-time {
                                            type uint32;
                                            units "microseconds";
                                            description "Indicates the round trip time for the probe";
                                        }

                                        ///global-operations/oam/lsp-trace/sr-ospf/output/results/hop/probe/probe-instance/status
                                        leaf status {
                                            type types-oam:response-status;
                                            description "The OAM response status code for the specified test";
                                        }

                                        ///global-operations/oam/lsp-trace/sr-ospf/output/results/hop/probe/probe-instance/response-packet
                                        container response-packet {
                                            description "Data from packet received as a response to transmitted probe";

                                            ///global-operations/oam/lsp-trace/sr-ospf/output/results/hop/probe/probe-instance/response-packet/size
                                            leaf size {
                                                type uint32;
                                                units "bytes";
                                                description "Indicates the number of bytes in the response packet for the probe";
                                            }

                                            ///global-operations/oam/lsp-trace/sr-ospf/output/results/hop/probe/probe-instance/response-packet/source-address
                                            leaf source-address {
                                                type types-sros:ip-address;
                                                description
                                                    "Indicates the source address in the response packet for the specified
                                                     probe";
                                            }

                                            ///global-operations/oam/lsp-trace/sr-ospf/output/results/hop/probe/probe-instance/response-packet/return-code
                                            leaf return-code {
                                                type int32;
                                                description "Indicates the OAM return code received in the probe response";
                                            }

                                            ///global-operations/oam/lsp-trace/sr-ospf/output/results/hop/probe/probe-instance/response-packet/return-code-string
                                            leaf return-code-string {
                                                type types-oam:lsp-ping-trace-return-code;
                                                description "Description of the return-code";
                                            }

                                            ///global-operations/oam/lsp-trace/sr-ospf/output/results/hop/probe/probe-instance/response-packet/return-subcode
                                            leaf return-subcode {
                                                type uint32;
                                                description
                                                    "Indicates the stack-depth where processing was terminated with
                                                     the value in the return-code";
                                            }

                                            ///global-operations/oam/lsp-trace/sr-ospf/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/sr-ospf/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/sr-ospf/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/sr-ospf/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/sr-ospf/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/sr-ospf/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/sr-ospf/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/sr-ospf/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/sr-ospf/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/sr-ospf/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/sr-ospf/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/sr-ospf/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/sr-ospf/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/sr-ospf/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/sr-ospf/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/sr-ospf/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/sr-ospf/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/sr-ospf/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/sr-ospf/output/status
                        leaf status {
                            type types-operation:operation-status;
                            description "Status of the operation";
                        }

                        ///global-operations/oam/lsp-trace/sr-ospf/output/error-message
                        leaf-list error-message {
                            type types-operation:operation-message;
                            description "Error messages reported during execution of the operation.";
                        }

                        ///global-operations/oam/lsp-trace/sr-ospf/output/warning-message
                        leaf-list warning-message {
                            type types-operation:operation-message;
                            description "Warning messages reported during execution of the operation.";
                        }

                        ///global-operations/oam/lsp-trace/sr-ospf/output/info-message
                        leaf-list info-message {
                            type types-operation:operation-message;
                            description "Info messages reported during execution of the operation.";
                        }

                        ///global-operations/oam/lsp-trace/sr-ospf/output/end-time
                        leaf end-time {
                            type types-operation:operation-timestamp;
                            description "Time when the operation ended its execution.";
                        }

                    }
                } // action sr-ospf

                ///global-operations/oam/lsp-trace/sr-ospf3
                action sr-ospf3 {
                    description "Perform an SR-OSPFv3 LSP trace test";

                    input {

                        ///global-operations/oam/lsp-trace/sr-ospf3/input/prefix
                        leaf prefix {
                            type types-sros:ip-prefix;
                            mandatory true;
                            description "Destination IP prefix for the test";
                        }

                        ///global-operations/oam/lsp-trace/sr-ospf3/input/igp-instance
                        leaf igp-instance {
                            type uint32 {
                                range "0..31|64..95";
                            }
                            default "0";
                            description "IGP instance for the SR-OSPFv3 test";
                        }

                        ///global-operations/oam/lsp-trace/sr-ospf3/input/path-destination
                        leaf path-destination {
                            type types-sros:ip-address;
                            description "IP address of the path destination";
                        }

                        ///global-operations/oam/lsp-trace/sr-ospf3/input/path-destination-egress
                        choice path-destination-egress {
                            ///global-operations/oam/lsp-trace/sr-ospf3/input/path-destination-egress/case-interface
                            case case-interface {

                                ///global-operations/oam/lsp-trace/sr-ospf3/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/sr-ospf3/input/path-destination-egress/case-next-hop
                            case case-next-hop {

                                ///global-operations/oam/lsp-trace/sr-ospf3/input/path-destination-egress/case-next-hop/next-hop
                                leaf next-hop {
                                    type types-sros:ip-address;
                                    description "Egress IP next hop address to use with path destination";
                                }

                            }
                        }
                        ///global-operations/oam/lsp-trace/sr-ospf3/input/source-ip-address
                        leaf source-ip-address {
                            type types-sros:ip-address;
                            description "Source IP address";
                        }

                        ///global-operations/oam/lsp-trace/sr-ospf3/input/interval
                        leaf interval {
                            type uint32 {
                                range "1..10";
                            }
                            units "seconds";
                            default "1";
                            description "Minimum time to expire before next echo request is sent";
                        }

                        ///global-operations/oam/lsp-trace/sr-ospf3/input/size
                        leaf size {
                            type uint32 {
                                range "1..9786";
                            }
                            units "bytes";
                            default "1";
                            description "Echo request packet pad size";
                        }

                        ///global-operations/oam/lsp-trace/sr-ospf3/input/fc
                        leaf fc {
                            type types-sros:fc-name;
                            default "be";
                            description "QoS forwarding class for the sent echo request packet";
                        }

                        ///global-operations/oam/lsp-trace/sr-ospf3/input/profile
                        leaf profile {
                            type types-qos:profile-in-out;
                            default "out";
                            description "QoS profile for the transmitted echo request packets";
                        }

                        ///global-operations/oam/lsp-trace/sr-ospf3/input/timeout
                        leaf timeout {
                            type uint32 {
                                range "1..10";
                            }
                            units "seconds";
                            default "5";
                            description "Time to wait for a reply after sending an echo request";
                        }

                        ///global-operations/oam/lsp-trace/sr-ospf3/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/sr-ospf3/input/min-ttl
                        leaf min-ttl {
                            type uint32 {
                                range "1..255";
                            }
                            default "1";
                            description "Initial TTL for the test";
                        }

                        ///global-operations/oam/lsp-trace/sr-ospf3/input/max-ttl
                        leaf max-ttl {
                            type uint32 {
                                range "1..255";
                            }
                            default "30";
                            description "Maximum TTL";
                        }

                        ///global-operations/oam/lsp-trace/sr-ospf3/input/max-fail
                        leaf max-fail {
                            type uint32 {
                                range "1..255";
                            }
                            default "5";
                            description "Maximum consecutive timeouts before terminating test";
                        }

                        ///global-operations/oam/lsp-trace/sr-ospf3/input/probe-count
                        leaf probe-count {
                            type uint32 {
                                range "1..10";
                            }
                            default "1";
                            description "Number of OAM trace probes to send per TTL";
                        }

                    }
                    output {

                        ///global-operations/oam/lsp-trace/sr-ospf3/output/operation-id
                        leaf operation-id {
                            type types-operation:operation-id;
                            description "ID assigned to the operation.";
                        }

                        ///global-operations/oam/lsp-trace/sr-ospf3/output/start-time
                        leaf start-time {
                            type types-operation:operation-timestamp;
                            description "Time when the operation started its execution.";
                        }

                        ///global-operations/oam/lsp-trace/sr-ospf3/output/results-path
                        leaf results-path {
                            type types-operation:operation-path;
                            description "Path to the results of the operation formatted as xpath.";
                        }

                        ///global-operations/oam/lsp-trace/sr-ospf3/output/results
                        container results {
                            description "Enter the results context";

                            ///global-operations/oam/lsp-trace/sr-ospf3/output/results/test-parameters
                            container test-parameters {
                                description "Enter the test-parameters context";

                                ///global-operations/oam/lsp-trace/sr-ospf3/output/results/test-parameters/prefix
                                leaf prefix {
                                    type types-sros:ip-prefix;
                                    description "The destination IP prefix for the test";
                                }

                                ///global-operations/oam/lsp-trace/sr-ospf3/output/results/test-parameters/igp-instance
                                leaf igp-instance {
                                    type uint32 {
                                        range "0..127";
                                    }
                                    description "The IGP instance for the test";
                                }

                                ///global-operations/oam/lsp-trace/sr-ospf3/output/results/test-parameters/path-destination
                                leaf path-destination {
                                    type types-sros:ip-address;
                                    description "The IP address of the path destination";
                                }

                                ///global-operations/oam/lsp-trace/sr-ospf3/output/results/test-parameters/path-destination-egress
                                choice path-destination-egress {
                                    ///global-operations/oam/lsp-trace/sr-ospf3/output/results/test-parameters/path-destination-egress/case-interface
                                    case case-interface {

                                        ///global-operations/oam/lsp-trace/sr-ospf3/output/results/test-parameters/path-destination-egress/case-interface/interface
                                        leaf interface {
                                            type types-sros:interface-name;
                                            description "The egress router interface, used in conjunction with path-destination";
                                        }

                                    }
                                    ///global-operations/oam/lsp-trace/sr-ospf3/output/results/test-parameters/path-destination-egress/case-next-hop
                                    case case-next-hop {

                                        ///global-operations/oam/lsp-trace/sr-ospf3/output/results/test-parameters/path-destination-egress/case-next-hop/next-hop
                                        leaf next-hop {
                                            type types-sros:ip-address;
                                            description "The egress IP next hop address, used in conjunction with path-destination";
                                        }

                                    }
                                }
                                ///global-operations/oam/lsp-trace/sr-ospf3/output/results/test-parameters/source-ip-address
                                leaf source-ip-address {
                                    type types-sros:ip-address;
                                    description "Source IP address";
                                }

                                ///global-operations/oam/lsp-trace/sr-ospf3/output/results/test-parameters/interval
                                leaf interval {
                                    type uint32 {
                                        range "1..10";
                                    }
                                    units "seconds";
                                    description "Minimum time to expire before the next request is sent";
                                }

                                ///global-operations/oam/lsp-trace/sr-ospf3/output/results/test-parameters/size
                                leaf size {
                                    type uint32 {
                                        range "1..9786";
                                    }
                                    units "bytes";
                                    description "Packet pad size of request";
                                }

                                ///global-operations/oam/lsp-trace/sr-ospf3/output/results/test-parameters/fc
                                leaf fc {
                                    type types-sros:fc-name;
                                    description "QoS Forwarding Class for the transmitted request packet(s)";
                                }

                                ///global-operations/oam/lsp-trace/sr-ospf3/output/results/test-parameters/profile
                                leaf profile {
                                    type types-qos:profile-in-out;
                                    description "QoS profile for the transmitted request packet(s)";
                                }

                                ///global-operations/oam/lsp-trace/sr-ospf3/output/results/test-parameters/timeout
                                leaf timeout {
                                    type uint32 {
                                        range "1..10";
                                    }
                                    units "seconds";
                                    description "Time router waits for a reply after sending a request";
                                }

                                ///global-operations/oam/lsp-trace/sr-ospf3/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/sr-ospf3/output/results/test-parameters/min-ttl
                                leaf min-ttl {
                                    type uint32 {
                                        range "1..255";
                                    }
                                    description "The initial time-to-live value for the test";
                                }

                                ///global-operations/oam/lsp-trace/sr-ospf3/output/results/test-parameters/max-ttl
                                leaf max-ttl {
                                    type uint32 {
                                        range "1..255";
                                    }
                                    description "The maximum time-to-live value for the test";
                                }

                                ///global-operations/oam/lsp-trace/sr-ospf3/output/results/test-parameters/max-fail
                                leaf max-fail {
                                    type uint32 {
                                        range "1..255";
                                    }
                                    description "The maximum number of consecutive timeouts allowed before terminating test";
                                }

                                ///global-operations/oam/lsp-trace/sr-ospf3/output/results/test-parameters/probe-count
                                leaf probe-count {
                                    type uint32 {
                                        range "1..10";
                                    }
                                    description "The number of OAM trace probes to send per TTL";
                                }

                            } // container test-parameters

                            ///global-operations/oam/lsp-trace/sr-ospf3/output/results/request-packet
                            container request-packet {
                                description "Enter the request-packet context";

                                ///global-operations/oam/lsp-trace/sr-ospf3/output/results/request-packet/size
                                leaf size {
                                    type uint32;
                                    units "bytes";
                                    description "Indicates the number of bytes of each request packet sent";
                                }

                                ///global-operations/oam/lsp-trace/sr-ospf3/output/results/request-packet/source-address
                                leaf source-address {
                                    type types-sros:ip-address;
                                    description "Indicates the source address of the test run";
                                }

                                ///global-operations/oam/lsp-trace/sr-ospf3/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/sr-ospf3/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/sr-ospf3/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/sr-ospf3/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/sr-ospf3/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/sr-ospf3/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/sr-ospf3/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/sr-ospf3/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/sr-ospf3/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/sr-ospf3/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/sr-ospf3/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/sr-ospf3/output/results/hop
                            list hop {
                                key "hop-index";
                                description "Per-hop test results";

                                ///global-operations/oam/lsp-trace/sr-ospf3/output/results/hop/hop-index
                                leaf hop-index {
                                    type uint32 {
                                        range "1..max";
                                    }
                                    description "The hop index of the test results";
                                }

                                ///global-operations/oam/lsp-trace/sr-ospf3/output/results/hop/probe
                                list probe {
                                    key "probe-index";
                                    description "Probe data for the specified test run";

                                    ///global-operations/oam/lsp-trace/sr-ospf3/output/results/hop/probe/probe-index
                                    leaf probe-index {
                                        type uint32 {
                                            range "1..10";
                                        }
                                        description "The probe index of lsp-trace reply, in the context of a hop";
                                    }

                                    ///global-operations/oam/lsp-trace/sr-ospf3/output/results/hop/probe/probe-instance
                                    list probe-instance {
                                        key "probe-instance-index";
                                        description "Probe instance of a probe, in the contex of a hop";

                                        ///global-operations/oam/lsp-trace/sr-ospf3/output/results/hop/probe/probe-instance/probe-instance-index
                                        leaf probe-instance-index {
                                            type uint32 {
                                                range "1..4294967295";
                                            }
                                            description "Index of probes with the specified test run";
                                        }

                                        ///global-operations/oam/lsp-trace/sr-ospf3/output/results/hop/probe/probe-instance/egress-interface
                                        leaf egress-interface {
                                            type types-sros:interface-name;
                                            description "The interface name this probe was transmitted from";
                                        }

                                        ///global-operations/oam/lsp-trace/sr-ospf3/output/results/hop/probe/probe-instance/round-trip-time
                                        leaf round-trip-time {
                                            type uint32;
                                            units "microseconds";
                                            description "Indicates the round trip time for the probe";
                                        }

                                        ///global-operations/oam/lsp-trace/sr-ospf3/output/results/hop/probe/probe-instance/status
                                        leaf status {
                                            type types-oam:response-status;
                                            description "The OAM response status code for the specified test";
                                        }

                                        ///global-operations/oam/lsp-trace/sr-ospf3/output/results/hop/probe/probe-instance/response-packet
                                        container response-packet {
                                            description "Data from packet received as a response to transmitted probe";

                                            ///global-operations/oam/lsp-trace/sr-ospf3/output/results/hop/probe/probe-instance/response-packet/size
                                            leaf size {
                                                type uint32;
                                                units "bytes";
                                                description "Indicates the number of bytes in the response packet for the probe";
                                            }

                                            ///global-operations/oam/lsp-trace/sr-ospf3/output/results/hop/probe/probe-instance/response-packet/source-address
                                            leaf source-address {
                                                type types-sros:ip-address;
                                                description
                                                    "Indicates the source address in the response packet for the specified
                                                     probe";
                                            }

                                            ///global-operations/oam/lsp-trace/sr-ospf3/output/results/hop/probe/probe-instance/response-packet/return-code
                                            leaf return-code {
                                                type int32;
                                                description "Indicates the OAM return code received in the probe response";
                                            }

                                            ///global-operations/oam/lsp-trace/sr-ospf3/output/results/hop/probe/probe-instance/response-packet/return-code-string
                                            leaf return-code-string {
                                                type types-oam:lsp-ping-trace-return-code;
                                                description "Description of the return-code";
                                            }

                                            ///global-operations/oam/lsp-trace/sr-ospf3/output/results/hop/probe/probe-instance/response-packet/return-subcode
                                            leaf return-subcode {
                                                type uint32;
                                                description
                                                    "Indicates the stack-depth where processing was terminated with
                                                     the value in the return-code";
                                            }

                                            ///global-operations/oam/lsp-trace/sr-ospf3/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/sr-ospf3/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/sr-ospf3/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/sr-ospf3/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/sr-ospf3/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/sr-ospf3/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/sr-ospf3/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/sr-ospf3/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/sr-ospf3/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/sr-ospf3/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/sr-ospf3/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/sr-ospf3/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/sr-ospf3/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/sr-ospf3/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/sr-ospf3/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/sr-ospf3/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/sr-ospf3/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/sr-ospf3/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/sr-ospf3/output/status
                        leaf status {
                            type types-operation:operation-status;
                            description "Status of the operation";
                        }

                        ///global-operations/oam/lsp-trace/sr-ospf3/output/error-message
                        leaf-list error-message {
                            type types-operation:operation-message;
                            description "Error messages reported during execution of the operation.";
                        }

                        ///global-operations/oam/lsp-trace/sr-ospf3/output/warning-message
                        leaf-list warning-message {
                            type types-operation:operation-message;
                            description "Warning messages reported during execution of the operation.";
                        }

                        ///global-operations/oam/lsp-trace/sr-ospf3/output/info-message
                        leaf-list info-message {
                            type types-operation:operation-message;
                            description "Info messages reported during execution of the operation.";
                        }

                        ///global-operations/oam/lsp-trace/sr-ospf3/output/end-time
                        leaf end-time {
                            type types-operation:operation-timestamp;
                            description "Time when the operation ended its execution.";
                        }

                    }
                } // action sr-ospf3

                ///global-operations/oam/lsp-trace/sr-policy
                action sr-policy {
                    description "Perform an SR policy LSP trace test";

                    input {

                        ///global-operations/oam/lsp-trace/sr-policy/input/color
                        leaf color {
                            type uint32;
                            mandatory true;
                            description "Segment Routing color for the test";
                        }

                        ///global-operations/oam/lsp-trace/sr-policy/input/endpoint
                        leaf endpoint {
                            type types-sros:ip-address;
                            mandatory true;
                            description "Segment Routing endpoint for the test";
                        }

                        ///global-operations/oam/lsp-trace/sr-policy/input/segment-list
                        leaf segment-list {
                            type uint32 {
                                range "1..32";
                            }
                            description "Segment Routing segment list for the test";
                        }

                        ///global-operations/oam/lsp-trace/sr-policy/input/path-destination
                        leaf path-destination {
                            type types-sros:ip-address;
                            description "IP address of the path destination";
                        }

                        ///global-operations/oam/lsp-trace/sr-policy/input/path-destination-egress
                        choice path-destination-egress {
                            ///global-operations/oam/lsp-trace/sr-policy/input/path-destination-egress/case-interface
                            case case-interface {

                                ///global-operations/oam/lsp-trace/sr-policy/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/sr-policy/input/path-destination-egress/case-next-hop
                            case case-next-hop {

                                ///global-operations/oam/lsp-trace/sr-policy/input/path-destination-egress/case-next-hop/next-hop
                                leaf next-hop {
                                    type types-sros:ip-address;
                                    description "Egress IP next hop address to use with path destination";
                                }

                            }
                        }
                        ///global-operations/oam/lsp-trace/sr-policy/input/source-ip-address
                        leaf source-ip-address {
                            type types-sros:ip-address;
                            description "Source IP address";
                        }

                        ///global-operations/oam/lsp-trace/sr-policy/input/interval
                        leaf interval {
                            type uint32 {
                                range "1..10";
                            }
                            units "seconds";
                            default "1";
                            description "Minimum time to expire before next echo request is sent";
                        }

                        ///global-operations/oam/lsp-trace/sr-policy/input/size
                        leaf size {
                            type uint32 {
                                range "1..9786";
                            }
                            units "bytes";
                            default "1";
                            description "Echo request packet pad size";
                        }

                        ///global-operations/oam/lsp-trace/sr-policy/input/fc
                        leaf fc {
                            type types-sros:fc-name;
                            default "be";
                            description "QoS forwarding class for the sent echo request packet";
                        }

                        ///global-operations/oam/lsp-trace/sr-policy/input/profile
                        leaf profile {
                            type types-qos:profile-in-out;
                            default "out";
                            description "QoS profile for the transmitted echo request packets";
                        }

                        ///global-operations/oam/lsp-trace/sr-policy/input/timeout
                        leaf timeout {
                            type uint32 {
                                range "1..10";
                            }
                            units "seconds";
                            default "5";
                            description "Time to wait for a reply after sending an echo request";
                        }

                        ///global-operations/oam/lsp-trace/sr-policy/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/sr-policy/input/min-ttl
                        leaf min-ttl {
                            type uint32 {
                                range "1..255";
                            }
                            default "1";
                            description "Initial TTL for the test";
                        }

                        ///global-operations/oam/lsp-trace/sr-policy/input/max-ttl
                        leaf max-ttl {
                            type uint32 {
                                range "1..255";
                            }
                            default "30";
                            description "Maximum TTL";
                        }

                        ///global-operations/oam/lsp-trace/sr-policy/input/max-fail
                        leaf max-fail {
                            type uint32 {
                                range "1..255";
                            }
                            default "5";
                            description "Maximum consecutive timeouts before terminating test";
                        }

                        ///global-operations/oam/lsp-trace/sr-policy/input/probe-count
                        leaf probe-count {
                            type uint32 {
                                range "1..10";
                            }
                            default "1";
                            description "Number of OAM trace probes to send per TTL";
                        }

                    }
                    output {

                        ///global-operations/oam/lsp-trace/sr-policy/output/operation-id
                        leaf operation-id {
                            type types-operation:operation-id;
                            description "ID assigned to the operation.";
                        }

                        ///global-operations/oam/lsp-trace/sr-policy/output/start-time
                        leaf start-time {
                            type types-operation:operation-timestamp;
                            description "Time when the operation started its execution.";
                        }

                        ///global-operations/oam/lsp-trace/sr-policy/output/results-path
                        leaf results-path {
                            type types-operation:operation-path;
                            description "Path to the results of the operation formatted as xpath.";
                        }

                        ///global-operations/oam/lsp-trace/sr-policy/output/results
                        container results {
                            description "Enter the results context";

                            ///global-operations/oam/lsp-trace/sr-policy/output/results/test-parameters
                            container test-parameters {
                                description "Enter the test-parameters context";

                                ///global-operations/oam/lsp-trace/sr-policy/output/results/test-parameters/color
                                leaf color {
                                    type uint32;
                                    description "The Segment Routing color for the test";
                                }

                                ///global-operations/oam/lsp-trace/sr-policy/output/results/test-parameters/endpoint
                                leaf endpoint {
                                    type types-sros:ip-address;
                                    description "The Segment Routing endpoint for the test";
                                }

                                ///global-operations/oam/lsp-trace/sr-policy/output/results/test-parameters/segment-list
                                leaf segment-list {
                                    type uint32 {
                                        range "0..32";
                                    }
                                    description "The Segment Routing segment list for the test";
                                }

                                ///global-operations/oam/lsp-trace/sr-policy/output/results/test-parameters/path-destination
                                leaf path-destination {
                                    type types-sros:ip-address;
                                    description "The IP address of the path destination";
                                }

                                ///global-operations/oam/lsp-trace/sr-policy/output/results/test-parameters/path-destination-egress
                                choice path-destination-egress {
                                    ///global-operations/oam/lsp-trace/sr-policy/output/results/test-parameters/path-destination-egress/case-interface
                                    case case-interface {

                                        ///global-operations/oam/lsp-trace/sr-policy/output/results/test-parameters/path-destination-egress/case-interface/interface
                                        leaf interface {
                                            type types-sros:interface-name;
                                            description "The egress router interface, used in conjunction with path-destination";
                                        }

                                    }
                                    ///global-operations/oam/lsp-trace/sr-policy/output/results/test-parameters/path-destination-egress/case-next-hop
                                    case case-next-hop {

                                        ///global-operations/oam/lsp-trace/sr-policy/output/results/test-parameters/path-destination-egress/case-next-hop/next-hop
                                        leaf next-hop {
                                            type types-sros:ip-address;
                                            description "The egress IP next hop address, used in conjunction with path-destination";
                                        }

                                    }
                                }
                                ///global-operations/oam/lsp-trace/sr-policy/output/results/test-parameters/source-ip-address
                                leaf source-ip-address {
                                    type types-sros:ip-address;
                                    description "Source IP address";
                                }

                                ///global-operations/oam/lsp-trace/sr-policy/output/results/test-parameters/interval
                                leaf interval {
                                    type uint32 {
                                        range "1..10";
                                    }
                                    units "seconds";
                                    description "Minimum time to expire before the next request is sent";
                                }

                                ///global-operations/oam/lsp-trace/sr-policy/output/results/test-parameters/size
                                leaf size {
                                    type uint32 {
                                        range "1..9786";
                                    }
                                    units "bytes";
                                    description "Packet pad size of request";
                                }

                                ///global-operations/oam/lsp-trace/sr-policy/output/results/test-parameters/fc
                                leaf fc {
                                    type types-sros:fc-name;
                                    description "QoS Forwarding Class for the transmitted request packet(s)";
                                }

                                ///global-operations/oam/lsp-trace/sr-policy/output/results/test-parameters/profile
                                leaf profile {
                                    type types-qos:profile-in-out;
                                    description "QoS profile for the transmitted request packet(s)";
                                }

                                ///global-operations/oam/lsp-trace/sr-policy/output/results/test-parameters/timeout
                                leaf timeout {
                                    type uint32 {
                                        range "1..10";
                                    }
                                    units "seconds";
                                    description "Time router waits for a reply after sending a request";
                                }

                                ///global-operations/oam/lsp-trace/sr-policy/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/sr-policy/output/results/test-parameters/min-ttl
                                leaf min-ttl {
                                    type uint32 {
                                        range "1..255";
                                    }
                                    description "The initial time-to-live value for the test";
                                }

                                ///global-operations/oam/lsp-trace/sr-policy/output/results/test-parameters/max-ttl
                                leaf max-ttl {
                                    type uint32 {
                                        range "1..255";
                                    }
                                    description "The maximum time-to-live value for the test";
                                }

                                ///global-operations/oam/lsp-trace/sr-policy/output/results/test-parameters/max-fail
                                leaf max-fail {
                                    type uint32 {
                                        range "1..255";
                                    }
                                    description "The maximum number of consecutive timeouts allowed before terminating test";
                                }

                                ///global-operations/oam/lsp-trace/sr-policy/output/results/test-parameters/probe-count
                                leaf probe-count {
                                    type uint32 {
                                        range "1..10";
                                    }
                                    description "The number of OAM trace probes to send per TTL";
                                }

                            } // container test-parameters

                            ///global-operations/oam/lsp-trace/sr-policy/output/results/request-packet
                            container request-packet {
                                description "Enter the request-packet context";

                                ///global-operations/oam/lsp-trace/sr-policy/output/results/request-packet/size
                                leaf size {
                                    type uint32;
                                    units "bytes";
                                    description "Indicates the number of bytes of each request packet sent";
                                }

                                ///global-operations/oam/lsp-trace/sr-policy/output/results/request-packet/source-address
                                leaf source-address {
                                    type types-sros:ip-address;
                                    description "Indicates the source address of the test run";
                                }

                                ///global-operations/oam/lsp-trace/sr-policy/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/sr-policy/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/sr-policy/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/sr-policy/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/sr-policy/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/sr-policy/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/sr-policy/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/sr-policy/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/sr-policy/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/sr-policy/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/sr-policy/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/sr-policy/output/results/hop
                            list hop {
                                key "hop-index";
                                description "Per-hop test results";

                                ///global-operations/oam/lsp-trace/sr-policy/output/results/hop/hop-index
                                leaf hop-index {
                                    type uint32 {
                                        range "1..max";
                                    }
                                    description "The hop index of the test results";
                                }

                                ///global-operations/oam/lsp-trace/sr-policy/output/results/hop/probe
                                list probe {
                                    key "probe-index";
                                    description "Probe data for the specified test run";

                                    ///global-operations/oam/lsp-trace/sr-policy/output/results/hop/probe/probe-index
                                    leaf probe-index {
                                        type uint32 {
                                            range "1..10";
                                        }
                                        description "The probe index of lsp-trace reply, in the context of a hop";
                                    }

                                    ///global-operations/oam/lsp-trace/sr-policy/output/results/hop/probe/probe-instance
                                    list probe-instance {
                                        key "probe-instance-index";
                                        description "Probe instance of a probe, in the contex of a hop";

                                        ///global-operations/oam/lsp-trace/sr-policy/output/results/hop/probe/probe-instance/probe-instance-index
                                        leaf probe-instance-index {
                                            type uint32 {
                                                range "1..4294967295";
                                            }
                                            description "Index of probes with the specified test run";
                                        }

                                        ///global-operations/oam/lsp-trace/sr-policy/output/results/hop/probe/probe-instance/egress-interface
                                        leaf egress-interface {
                                            type types-sros:interface-name;
                                            description "The interface name this probe was transmitted from";
                                        }

                                        ///global-operations/oam/lsp-trace/sr-policy/output/results/hop/probe/probe-instance/round-trip-time
                                        leaf round-trip-time {
                                            type uint32;
                                            units "microseconds";
                                            description "Indicates the round trip time for the probe";
                                        }

                                        ///global-operations/oam/lsp-trace/sr-policy/output/results/hop/probe/probe-instance/status
                                        leaf status {
                                            type types-oam:response-status;
                                            description "The OAM response status code for the specified test";
                                        }

                                        ///global-operations/oam/lsp-trace/sr-policy/output/results/hop/probe/probe-instance/response-packet
                                        container response-packet {
                                            description "Data from packet received as a response to transmitted probe";

                                            ///global-operations/oam/lsp-trace/sr-policy/output/results/hop/probe/probe-instance/response-packet/size
                                            leaf size {
                                                type uint32;
                                                units "bytes";
                                                description "Indicates the number of bytes in the response packet for the probe";
                                            }

                                            ///global-operations/oam/lsp-trace/sr-policy/output/results/hop/probe/probe-instance/response-packet/source-address
                                            leaf source-address {
                                                type types-sros:ip-address;
                                                description
                                                    "Indicates the source address in the response packet for the specified
                                                     probe";
                                            }

                                            ///global-operations/oam/lsp-trace/sr-policy/output/results/hop/probe/probe-instance/response-packet/return-code
                                            leaf return-code {
                                                type int32;
                                                description "Indicates the OAM return code received in the probe response";
                                            }

                                            ///global-operations/oam/lsp-trace/sr-policy/output/results/hop/probe/probe-instance/response-packet/return-code-string
                                            leaf return-code-string {
                                                type types-oam:lsp-ping-trace-return-code;
                                                description "Description of the return-code";
                                            }

                                            ///global-operations/oam/lsp-trace/sr-policy/output/results/hop/probe/probe-instance/response-packet/return-subcode
                                            leaf return-subcode {
                                                type uint32;
                                                description
                                                    "Indicates the stack-depth where processing was terminated with
                                                     the value in the return-code";
                                            }

                                            ///global-operations/oam/lsp-trace/sr-policy/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/sr-policy/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/sr-policy/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/sr-policy/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/sr-policy/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/sr-policy/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/sr-policy/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/sr-policy/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/sr-policy/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/sr-policy/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/sr-policy/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/sr-policy/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/sr-policy/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/sr-policy/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/sr-policy/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/sr-policy/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/sr-policy/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/sr-policy/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/sr-policy/output/status
                        leaf status {
                            type types-operation:operation-status;
                            description "Status of the operation";
                        }

                        ///global-operations/oam/lsp-trace/sr-policy/output/error-message
                        leaf-list error-message {
                            type types-operation:operation-message;
                            description "Error messages reported during execution of the operation.";
                        }

                        ///global-operations/oam/lsp-trace/sr-policy/output/warning-message
                        leaf-list warning-message {
                            type types-operation:operation-message;
                            description "Warning messages reported during execution of the operation.";
                        }

                        ///global-operations/oam/lsp-trace/sr-policy/output/info-message
                        leaf-list info-message {
                            type types-operation:operation-message;
                            description "Info messages reported during execution of the operation.";
                        }

                        ///global-operations/oam/lsp-trace/sr-policy/output/end-time
                        leaf end-time {
                            type types-operation:operation-timestamp;
                            description "Time when the operation ended its execution.";
                        }

                    }
                } // action sr-policy

                ///global-operations/oam/lsp-trace/sr-te
                action sr-te {
                    description "Perform an SR-TE LSP trace test";

                    input {

                        ///global-operations/oam/lsp-trace/sr-te/input/lsp-name
                        leaf lsp-name {
                            type leafref {
                                path "/state:state/state:router/state:mpls/state:lsp/state:lsp-name";
                                require-instance "false";
                            }
                            mandatory true;
                            description "Name of the LSP to test";
                        }

                        ///global-operations/oam/lsp-trace/sr-te/input/path
                        leaf path {
                            type leafref {
                                path "/state:state/state:router/state:mpls/state:path/state:path-name";
                                require-instance "false";
                            }
                            description "Name of the MPLS path to test";
                        }

                        ///global-operations/oam/lsp-trace/sr-te/input/path-destination
                        leaf path-destination {
                            type types-sros:ip-address;
                            description "IP address of the path destination";
                        }

                        ///global-operations/oam/lsp-trace/sr-te/input/path-destination-egress
                        choice path-destination-egress {
                            ///global-operations/oam/lsp-trace/sr-te/input/path-destination-egress/case-interface
                            case case-interface {

                                ///global-operations/oam/lsp-trace/sr-te/input/path-destination-egress/case-interface/interface
                                leaf interface {
                                    type leafref {
                                        path "/state:state/state:router/state:interface/state:interface-name";
                                        require-instance "false";
                                    }
                                    description "Egress router interface to use with path destination";
                                }

                            }
                            ///global-operations/oam/lsp-trace/sr-te/input/path-destination-egress/case-next-hop
                            case case-next-hop {

                                ///global-operations/oam/lsp-trace/sr-te/input/path-destination-egress/case-next-hop/next-hop
                                leaf next-hop {
                                    type types-sros:ip-address;
                                    description "Egress IP next hop address to use with path destination";
                                }

                            }
                        }
                        ///global-operations/oam/lsp-trace/sr-te/input/source-ip-address
                        leaf source-ip-address {
                            type types-sros:ip-address;
                            description "Source IP address";
                        }

                        ///global-operations/oam/lsp-trace/sr-te/input/interval
                        leaf interval {
                            type uint32 {
                                range "1..10";
                            }
                            units "seconds";
                            default "1";
                            description "Minimum time to expire before next echo request is sent";
                        }

                        ///global-operations/oam/lsp-trace/sr-te/input/size
                        leaf size {
                            type uint32 {
                                range "1..9786";
                            }
                            units "bytes";
                            default "1";
                            description "Echo request packet pad size";
                        }

                        ///global-operations/oam/lsp-trace/sr-te/input/fc
                        leaf fc {
                            type types-sros:fc-name;
                            default "be";
                            description "QoS forwarding class for the sent echo request packet";
                        }

                        ///global-operations/oam/lsp-trace/sr-te/input/profile
                        leaf profile {
                            type types-qos:profile-in-out;
                            default "out";
                            description "QoS profile for the transmitted echo request packets";
                        }

                        ///global-operations/oam/lsp-trace/sr-te/input/timeout
                        leaf timeout {
                            type uint32 {
                                range "1..10";
                            }
                            units "seconds";
                            default "5";
                            description "Time to wait for a reply after sending an echo request";
                        }

                        ///global-operations/oam/lsp-trace/sr-te/input/downstream-map-tlv
                        leaf downstream-map-tlv {
                            type enumeration {
                                enum dsmap {
                                    value 1;
                                    description "Downstream mapping TLV";
                                }
                                enum ddmap {
                                    value 2;
                                    description "Detailed downstream mapping TLV";
                                }
                                enum none {
                                    value 3;
                                    description "No mapping TLV";
                                }
                            }
                            description "Type of downstream mapping TLV in MPLS echo request PDU";
                        }

                        ///global-operations/oam/lsp-trace/sr-te/input/min-ttl
                        leaf min-ttl {
                            type uint32 {
                                range "1..255";
                            }
                            default "1";
                            description "Initial TTL for the test";
                        }

                        ///global-operations/oam/lsp-trace/sr-te/input/max-ttl
                        leaf max-ttl {
                            type uint32 {
                                range "1..255";
                            }
                            default "30";
                            description "Maximum TTL";
                        }

                        ///global-operations/oam/lsp-trace/sr-te/input/max-fail
                        leaf max-fail {
                            type uint32 {
                                range "1..255";
                            }
                            default "5";
                            description "Maximum consecutive timeouts before terminating test";
                        }

                        ///global-operations/oam/lsp-trace/sr-te/input/probe-count
                        leaf probe-count {
                            type uint32 {
                                range "1..10";
                            }
                            default "1";
                            description "Number of OAM trace probes to send per TTL";
                        }

                    }
                    output {

                        ///global-operations/oam/lsp-trace/sr-te/output/operation-id
                        leaf operation-id {
                            type types-operation:operation-id;
                            description "ID assigned to the operation.";
                        }

                        ///global-operations/oam/lsp-trace/sr-te/output/start-time
                        leaf start-time {
                            type types-operation:operation-timestamp;
                            description "Time when the operation started its execution.";
                        }

                        ///global-operations/oam/lsp-trace/sr-te/output/results-path
                        leaf results-path {
                            type types-operation:operation-path;
                            description "Path to the results of the operation formatted as xpath.";
                        }

                        ///global-operations/oam/lsp-trace/sr-te/output/results
                        container results {
                            description "Enter the results context";

                            ///global-operations/oam/lsp-trace/sr-te/output/results/test-parameters
                            container test-parameters {
                                description "Enter the test-parameters context";

                                ///global-operations/oam/lsp-trace/sr-te/output/results/test-parameters/lsp-name
                                leaf lsp-name {
                                    type types-sros:named-item-64;
                                    description "The name of the LSP to be tested";
                                }

                                ///global-operations/oam/lsp-trace/sr-te/output/results/test-parameters/path
                                leaf path {
                                    type types-sros:named-item-64;
                                    description "The name of the MPLS path to be tested";
                                }

                                ///global-operations/oam/lsp-trace/sr-te/output/results/test-parameters/path-destination
                                leaf path-destination {
                                    type types-sros:ip-address;
                                    description "The IP address of the path destination";
                                }

                                ///global-operations/oam/lsp-trace/sr-te/output/results/test-parameters/path-destination-egress
                                choice path-destination-egress {
                                    ///global-operations/oam/lsp-trace/sr-te/output/results/test-parameters/path-destination-egress/case-interface
                                    case case-interface {

                                        ///global-operations/oam/lsp-trace/sr-te/output/results/test-parameters/path-destination-egress/case-interface/interface
                                        leaf interface {
                                            type types-sros:interface-name;
                                            description "The egress router interface, used in conjunction with path-destination";
                                        }

                                    }
                                    ///global-operations/oam/lsp-trace/sr-te/output/results/test-parameters/path-destination-egress/case-next-hop
                                    case case-next-hop {

                                        ///global-operations/oam/lsp-trace/sr-te/output/results/test-parameters/path-destination-egress/case-next-hop/next-hop
                                        leaf next-hop {
                                            type types-sros:ip-address;
                                            description "The egress IP next hop address, used in conjunction with path-destination";
                                        }

                                    }
                                }
                                ///global-operations/oam/lsp-trace/sr-te/output/results/test-parameters/source-ip-address
                                leaf source-ip-address {
                                    type types-sros:ip-address;
                                    description "Source IP address";
                                }

                                ///global-operations/oam/lsp-trace/sr-te/output/results/test-parameters/interval
                                leaf interval {
                                    type uint32 {
                                        range "1..10";
                                    }
                                    units "seconds";
                                    description "Minimum time to expire before the next request is sent";
                                }

                                ///global-operations/oam/lsp-trace/sr-te/output/results/test-parameters/size
                                leaf size {
                                    type uint32 {
                                        range "1..9786";
                                    }
                                    units "bytes";
                                    description "Packet pad size of request";
                                }

                                ///global-operations/oam/lsp-trace/sr-te/output/results/test-parameters/fc
                                leaf fc {
                                    type types-sros:fc-name;
                                    description "QoS Forwarding Class for the transmitted request packet(s)";
                                }

                                ///global-operations/oam/lsp-trace/sr-te/output/results/test-parameters/profile
                                leaf profile {
                                    type types-qos:profile-in-out;
                                    description "QoS profile for the transmitted request packet(s)";
                                }

                                ///global-operations/oam/lsp-trace/sr-te/output/results/test-parameters/timeout
                                leaf timeout {
                                    type uint32 {
                                        range "1..10";
                                    }
                                    units "seconds";
                                    description "Time router waits for a reply after sending a request";
                                }

                                ///global-operations/oam/lsp-trace/sr-te/output/results/test-parameters/downstream-map-tlv
                                leaf downstream-map-tlv {
                                    type enumeration {
                                        enum dsmap                          { value 1; }
                                        enum ddmap                          { value 2; }
                                        enum none                           { value 3; }
                                    }
                                    description "The type of downstream mapping TLV in MPLS echo request PDU";
                                }

                                ///global-operations/oam/lsp-trace/sr-te/output/results/test-parameters/min-ttl
                                leaf min-ttl {
                                    type uint32 {
                                        range "1..255";
                                    }
                                    description "The initial time-to-live value for the test";
                                }

                                ///global-operations/oam/lsp-trace/sr-te/output/results/test-parameters/max-ttl
                                leaf max-ttl {
                                    type uint32 {
                                        range "1..255";
                                    }
                                    description "The maximum time-to-live value for the test";
                                }

                                ///global-operations/oam/lsp-trace/sr-te/output/results/test-parameters/max-fail
                                leaf max-fail {
                                    type uint32 {
                                        range "1..255";
                                    }
                                    description "The maximum number of consecutive timeouts allowed before terminating test";
                                }

                                ///global-operations/oam/lsp-trace/sr-te/output/results/test-parameters/probe-count
                                leaf probe-count {
                                    type uint32 {
                                        range "1..10";
                                    }
                                    description "The number of OAM trace probes to send per TTL";
                                }

                            } // container test-parameters

                            ///global-operations/oam/lsp-trace/sr-te/output/results/request-packet
                            container request-packet {
                                description "Enter the request-packet context";

                                ///global-operations/oam/lsp-trace/sr-te/output/results/request-packet/size
                                leaf size {
                                    type uint32;
                                    units "bytes";
                                    description "Indicates the number of bytes of each request packet sent";
                                }

                                ///global-operations/oam/lsp-trace/sr-te/output/results/request-packet/source-address
                                leaf source-address {
                                    type types-sros:ip-address;
                                    description "Indicates the source address of the test run";
                                }

                                ///global-operations/oam/lsp-trace/sr-te/output/results/request-packet/downstream-mapping-tlv
                                list downstream-mapping-tlv {
                                    key "mapping-tlv-index";
                                    description
                                        "MPLS downstream label information copied by the originating node
                                         into the specified RFC 4379 Downstream Mapping TLV or RFC 6424
                                         Downstream Detailed Mapping TLV of the first request packet of
                                         the 'lsp-trace' test run";

                                    ///global-operations/oam/lsp-trace/sr-te/output/results/request-packet/downstream-mapping-tlv/mapping-tlv-index
                                    leaf mapping-tlv-index {
                                        type uint32;
                                        description
                                            "The index value identifies one RFC 4379 Downstream Mapping
                                             TLV (or one RFC 6424 Downstream Detailed Mapping TLV) within
                                             the first request packet sent for the specified test run";
                                    }

                                    ///global-operations/oam/lsp-trace/sr-te/output/results/request-packet/downstream-mapping-tlv/mtu
                                    leaf mtu {
                                        type uint32;
                                        description
                                            "The largest MPLS frame (including the label stack) that fits on the
                                             interface to the downstream LSR (Label Switching Router).  The value
                                             from the MTU (Maximum Transmission Unit) field of the specified
                                             RFC 4379 Downstream Mapping TLV (or RFC 6424 Downstream
                                             Detailed Mapping TLV)";
                                    }

                                    ///global-operations/oam/lsp-trace/sr-te/output/results/request-packet/downstream-mapping-tlv/address-type
                                    leaf address-type {
                                        type enumeration {
                                            enum unknown                        { value 0; }
                                            enum ipv4-numbered                  { value 1; }
                                            enum ipv6-numbered                  { value 2; }
                                            enum ipv4-unnumbered                { value 3; }
                                            enum ipv6-unnumbered                { value 4; }
                                            enum non-ip                         { value 5; }
                                        }
                                        description
                                            "The value of the Adress Type field of the specified RFC 4379 Downstream
                                             Mapping TLV or RFC 6424 Downstream Detailed Mapping TLV";
                                    }

                                    ///global-operations/oam/lsp-trace/sr-te/output/results/request-packet/downstream-mapping-tlv/ip-address
                                    leaf ip-address {
                                        type types-sros:ip-address;
                                        description
                                            "The Downstream IP Address field in the specified RFC 4379 Downstream Mapping TLV (or the
                                             Downstream Address field in the specified RFC 6424 Downstream Detailed
                                             Mapping TLV)";
                                    }

                                    ///global-operations/oam/lsp-trace/sr-te/output/results/request-packet/downstream-mapping-tlv/interface-address
                                    leaf interface-address {
                                        type types-sros:ip-address;
                                        description
                                            "The value of the Downstream Interface Address field in the specified
                                             RFC 4379 Downstream Mapping TLV (or RFC 6424 Downstream Detailed Mapping TLV)";
                                    }

                                    ///global-operations/oam/lsp-trace/sr-te/output/results/request-packet/downstream-mapping-tlv/egress-interface
                                    leaf egress-interface {
                                        type types-sros:interface-name;
                                        description
                                            "The egress interface name corresponding to the interface number in the
                                             Downstream IP Address field of the specified RFC 4379 Downstream Mapping
                                             TLV (or the RFC 6424 Downstream Address field of the specified RFC 6424
                                             Downstream Detailed Mapping TLV)";
                                    }

                                    ///global-operations/oam/lsp-trace/sr-te/output/results/request-packet/downstream-mapping-tlv/mpls-label-stack-entry
                                    list mpls-label-stack-entry {
                                        key "label-index";
                                        description
                                            "Info in MPLS Downstream Label information copied by the originating node
                                             into the specified RFC 4379 Downstream Mapping TLV or RFC 6424 Downstream
                                             Detailed Mapping TLV of the first request packet of the 'lsp-trace' test run";

                                        ///global-operations/oam/lsp-trace/sr-te/output/results/request-packet/downstream-mapping-tlv/mpls-label-stack-entry/label-index
                                        leaf label-index {
                                            type uint32 {
                                                range "1..max";
                                            }
                                            description
                                                "The index value identifies one RFC 4379 Downstream Mapping (or one
                                                 RFC 6424 Downstream Detailed Mapping) {Downstream Label, Protocol} pair";
                                        }

                                        ///global-operations/oam/lsp-trace/sr-te/output/results/request-packet/downstream-mapping-tlv/mpls-label-stack-entry/label
                                        leaf label {
                                            type int32;
                                            description
                                                "The value in the Downstream Label field of the specified RFC 4379 Downstream
                                                 Mapping TLV or RFC 6424 Downstream Detailed Mapping TLV";
                                        }

                                        ///global-operations/oam/lsp-trace/sr-te/output/results/request-packet/downstream-mapping-tlv/mpls-label-stack-entry/protocol
                                        leaf protocol {
                                            type enumeration {
                                                enum unknown                        { value 0; }
                                                enum static                         { value 1; }
                                                enum bgp                            { value 2; }
                                                enum ldp                            { value 3; }
                                                enum rsvp-te                        { value 4; }
                                                enum ospf                           { value 5; }
                                                enum isis                           { value 6; }
                                                enum ospf3                          { value 7; }
                                            }
                                            description
                                                "The value in the Protocol field of the specified RFC 4379 Downstream
                                                 Mapping TLV or RFC 6424 Downstream Detailed Mapping TLV";
                                        }

                                    } // list mpls-label-stack-entry

                                } // list downstream-mapping-tlv

                            } // container request-packet

                            ///global-operations/oam/lsp-trace/sr-te/output/results/hop
                            list hop {
                                key "hop-index";
                                description "Per-hop test results";

                                ///global-operations/oam/lsp-trace/sr-te/output/results/hop/hop-index
                                leaf hop-index {
                                    type uint32 {
                                        range "1..max";
                                    }
                                    description "The hop index of the test results";
                                }

                                ///global-operations/oam/lsp-trace/sr-te/output/results/hop/probe
                                list probe {
                                    key "probe-index";
                                    description "Probe data for the specified test run";

                                    ///global-operations/oam/lsp-trace/sr-te/output/results/hop/probe/probe-index
                                    leaf probe-index {
                                        type uint32 {
                                            range "1..10";
                                        }
                                        description "The probe index of lsp-trace reply, in the context of a hop";
                                    }

                                    ///global-operations/oam/lsp-trace/sr-te/output/results/hop/probe/probe-instance
                                    list probe-instance {
                                        key "probe-instance-index";
                                        description "Probe instance of a probe, in the contex of a hop";

                                        ///global-operations/oam/lsp-trace/sr-te/output/results/hop/probe/probe-instance/probe-instance-index
                                        leaf probe-instance-index {
                                            type uint32 {
                                                range "1..4294967295";
                                            }
                                            description "Index of probes with the specified test run";
                                        }

                                        ///global-operations/oam/lsp-trace/sr-te/output/results/hop/probe/probe-instance/egress-interface
                                        leaf egress-interface {
                                            type types-sros:interface-name;
                                            description "The interface name this probe was transmitted from";
                                        }

                                        ///global-operations/oam/lsp-trace/sr-te/output/results/hop/probe/probe-instance/round-trip-time
                                        leaf round-trip-time {
                                            type uint32;
                                            units "microseconds";
                                            description "Indicates the round trip time for the probe";
                                        }

                                        ///global-operations/oam/lsp-trace/sr-te/output/results/hop/probe/probe-instance/status
                                        leaf status {
                                            type types-oam:response-status;
                                            description "The OAM response status code for the specified test";
                                        }

                                        ///global-operations/oam/lsp-trace/sr-te/output/results/hop/probe/probe-instance/response-packet
                                        container response-packet {
                                            description "Data from packet received as a response to transmitted probe";

                                            ///global-operations/oam/lsp-trace/sr-te/output/results/hop/probe/probe-instance/response-packet/size
                                            leaf size {
                                                type uint32;
                                                units "bytes";
                                                description "Indicates the number of bytes in the response packet for the probe";
                                            }

                                            ///global-operations/oam/lsp-trace/sr-te/output/results/hop/probe/probe-instance/response-packet/source-address
                                            leaf source-address {
                                                type types-sros:ip-address;
                                                description
                                                    "Indicates the source address in the response packet for the specified
                                                     probe";
                                            }

                                            ///global-operations/oam/lsp-trace/sr-te/output/results/hop/probe/probe-instance/response-packet/return-code
                                            leaf return-code {
                                                type int32;
                                                description "Indicates the OAM return code received in the probe response";
                                            }

                                            ///global-operations/oam/lsp-trace/sr-te/output/results/hop/probe/probe-instance/response-packet/return-code-string
                                            leaf return-code-string {
                                                type types-oam:lsp-ping-trace-return-code;
                                                description "Description of the return-code";
                                            }

                                            ///global-operations/oam/lsp-trace/sr-te/output/results/hop/probe/probe-instance/response-packet/return-subcode
                                            leaf return-subcode {
                                                type uint32;
                                                description
                                                    "Indicates the stack-depth where processing was terminated with
                                                     the value in the return-code";
                                            }

                                            ///global-operations/oam/lsp-trace/sr-te/output/results/hop/probe/probe-instance/response-packet/downstream-mapping-tlv
                                            list downstream-mapping-tlv {
                                                key "mapping-tlv-index";
                                                description
                                                    "Content of the RFC 4379 Downstream Mapping TLV
                                                     (or one RFC 6424 Downstream Detailed Mapping TLV) within
                                                     the reply PDU";

                                                ///global-operations/oam/lsp-trace/sr-te/output/results/hop/probe/probe-instance/response-packet/downstream-mapping-tlv/mapping-tlv-index
                                                leaf mapping-tlv-index {
                                                    type uint32;
                                                    description
                                                        "The index value identifies a RFC 4379 Downstream Mapping TLV
                                                         (or one RFC 6424 Downstream Detailed Mapping TLV) within
                                                         the reply PDU";
                                                }

                                                ///global-operations/oam/lsp-trace/sr-te/output/results/hop/probe/probe-instance/response-packet/downstream-mapping-tlv/mtu
                                                leaf mtu {
                                                    type uint32;
                                                    description
                                                        "The largest MPLS frame (including the label stack) that fits on the
                                                         interface to the downstream LSR (Label Switching Router).  The value
                                                         from the MTU (Maximum Transmission Unit) field of the specified
                                                         RFC 4379 Downstream Mapping TLV (or RFC 6424 Downstream
                                                         Detailed Mapping TLV)";
                                                }

                                                ///global-operations/oam/lsp-trace/sr-te/output/results/hop/probe/probe-instance/response-packet/downstream-mapping-tlv/address-type
                                                leaf address-type {
                                                    type enumeration {
                                                        enum unknown                        { value 0; }
                                                        enum ipv4-numbered                  { value 1; }
                                                        enum ipv6-numbered                  { value 2; }
                                                        enum ipv4-unnumbered                { value 3; }
                                                        enum ipv6-unnumbered                { value 4; }
                                                        enum non-ip                         { value 5; }
                                                    }
                                                    description
                                                        "The value of the Adress Type field of the specified RFC 4379 Downstream
                                                         Mapping TLV or RFC 6424 Downstream Detailed Mapping TLV";
                                                }

                                                ///global-operations/oam/lsp-trace/sr-te/output/results/hop/probe/probe-instance/response-packet/downstream-mapping-tlv/ip-address
                                                leaf ip-address {
                                                    type types-sros:ip-address;
                                                    description
                                                        "The Downstream IP Address field in the specified RFC 4379 Downstream Mapping TLV (or the
                                                         Downstream Address field in the specified RFC 6424 Downstream Detailed
                                                         Mapping TLV)";
                                                }

                                                ///global-operations/oam/lsp-trace/sr-te/output/results/hop/probe/probe-instance/response-packet/downstream-mapping-tlv/interface-address
                                                leaf interface-address {
                                                    type types-sros:ip-address;
                                                    description
                                                        "The value of the Downstream Interface Address field in the specified
                                                         RFC 4379 Downstream Mapping TLV (or RFC 6424 Downstream Detailed Mapping TLV)";
                                                }

                                                ///global-operations/oam/lsp-trace/sr-te/output/results/hop/probe/probe-instance/response-packet/downstream-mapping-tlv/egress-interface
                                                leaf egress-interface {
                                                    type types-sros:interface-name;
                                                    description
                                                        "The egress interface name corresponding to the interface number in the
                                                         Downstream IP Address field of the specified RFC 4379 Downstream Mapping
                                                         TLV (or the RFC 6424 Downstream Address field of the specified RFC 6424
                                                         Downstream Detailed Mapping TLV)";
                                                }

                                                ///global-operations/oam/lsp-trace/sr-te/output/results/hop/probe/probe-instance/response-packet/downstream-mapping-tlv/ingress-interface
                                                leaf ingress-interface {
                                                    type types-sros:interface-name;
                                                    description
                                                        "The ingress interface number reported by the replying node.
                                                         This value is copied from the Downstream Interface Address field";
                                                }

                                                ///global-operations/oam/lsp-trace/sr-te/output/results/hop/probe/probe-instance/response-packet/downstream-mapping-tlv/mpls-label-stack-entry
                                                list mpls-label-stack-entry {
                                                    key "label-index";
                                                    description "The information of a single downstream label within a returned Downstream L2 Mapping TLV";

                                                    ///global-operations/oam/lsp-trace/sr-te/output/results/hop/probe/probe-instance/response-packet/downstream-mapping-tlv/mpls-label-stack-entry/label-index
                                                    leaf label-index {
                                                        type uint32 {
                                                            range "1..max";
                                                        }
                                                        description "The index value identifies a downstream label entry within a specific L2 mapping entry";
                                                    }

                                                    ///global-operations/oam/lsp-trace/sr-te/output/results/hop/probe/probe-instance/response-packet/downstream-mapping-tlv/mpls-label-stack-entry/label
                                                    leaf label {
                                                        type int32;
                                                        description
                                                            "The value in the Downstream Label field of the specified RFC 4379 Downstream
                                                             Mapping TLV or RFC 6424 Downstream Detailed Mapping TLV";
                                                    }

                                                    ///global-operations/oam/lsp-trace/sr-te/output/results/hop/probe/probe-instance/response-packet/downstream-mapping-tlv/mpls-label-stack-entry/protocol
                                                    leaf protocol {
                                                        type enumeration {
                                                            enum unknown                        { value 0; }
                                                            enum static                         { value 1; }
                                                            enum bgp                            { value 2; }
                                                            enum ldp                            { value 3; }
                                                            enum rsvp-te                        { value 4; }
                                                            enum ospf                           { value 5; }
                                                            enum isis                           { value 6; }
                                                            enum ospf3                          { value 7; }
                                                        }
                                                        description
                                                            "The value in the Protocol field of the specified RFC 4379 Downstream
                                                             Mapping TLV or RFC 6424 Downstream Detailed Mapping TLV";
                                                    }

                                                } // list mpls-label-stack-entry

                                                ///global-operations/oam/lsp-trace/sr-te/output/results/hop/probe/probe-instance/response-packet/downstream-mapping-tlv/fec-stack-entry
                                                list fec-stack-entry {
                                                    key "fec-index";
                                                    description
                                                        "Content of RFC 6424 FEC (Forwarding Equivalence Class) Stack
                                                         Change sub-TLV within the specified Downstream Detailed Mapping TLV
                                                         present in the reply PDU";

                                                    ///global-operations/oam/lsp-trace/sr-te/output/results/hop/probe/probe-instance/response-packet/downstream-mapping-tlv/fec-stack-entry/fec-index
                                                    leaf fec-index {
                                                        type uint32 {
                                                            range "1..8";
                                                        }
                                                        description "The index value of one RFC 6424 FEC Stack Change sub-TLV";
                                                    }

                                                    ///global-operations/oam/lsp-trace/sr-te/output/results/hop/probe/probe-instance/response-packet/downstream-mapping-tlv/fec-stack-entry/operation-type
                                                    leaf operation-type {
                                                        type enumeration {
                                                            enum push                           { value 1; }
                                                            enum pop                            { value 2; }
                                                        }
                                                        description
                                                            "The value of the Operation Type field in
                                                             RFC 6424 FEC Stack Change sub-TLV";
                                                    }

                                                    ///global-operations/oam/lsp-trace/sr-te/output/results/hop/probe/probe-instance/response-packet/downstream-mapping-tlv/fec-stack-entry/sub-type
                                                    leaf sub-type {
                                                        type types-sros:named-item-or-empty;
                                                        description "The value of Subtype field in RFC 4379 FEC-type-specific sub-TLV";
                                                    }

                                                    ///global-operations/oam/lsp-trace/sr-te/output/results/hop/probe/probe-instance/response-packet/downstream-mapping-tlv/fec-stack-entry/prefix
                                                    leaf prefix {
                                                        type types-sros:ip-address;
                                                        description
                                                            "The value of FEC-type-specific IP prefix (or IP address) field
                                                             in RFC 6424 FEC Stack Change sub-TLV";
                                                    }

                                                    ///global-operations/oam/lsp-trace/sr-te/output/results/hop/probe/probe-instance/response-packet/downstream-mapping-tlv/fec-stack-entry/remote-peer-address
                                                    leaf remote-peer-address {
                                                        type types-sros:ip-address;
                                                        description "The value of Remote Peer Address field in RFC 6424 FEC Stack Change sub-TLV";
                                                    }

                                                } // list fec-stack-entry

                                            } // list downstream-mapping-tlv

                                        } // container response-packet

                                    } // list probe-instance

                                } // list probe

                            } // list hop

                        } // container results

                        ///global-operations/oam/lsp-trace/sr-te/output/status
                        leaf status {
                            type types-operation:operation-status;
                            description "Status of the operation";
                        }

                        ///global-operations/oam/lsp-trace/sr-te/output/error-message
                        leaf-list error-message {
                            type types-operation:operation-message;
                            description "Error messages reported during execution of the operation.";
                        }

                        ///global-operations/oam/lsp-trace/sr-te/output/warning-message
                        leaf-list warning-message {
                            type types-operation:operation-message;
                            description "Warning messages reported during execution of the operation.";
                        }

                        ///global-operations/oam/lsp-trace/sr-te/output/info-message
                        leaf-list info-message {
                            type types-operation:operation-message;
                            description "Info messages reported during execution of the operation.";
                        }

                        ///global-operations/oam/lsp-trace/sr-te/output/end-time
                        leaf end-time {
                            type types-operation:operation-timestamp;
                            description "Time when the operation ended its execution.";
                        }

                    }
                } // action sr-te

            } // container lsp-trace

            ///global-operations/oam/saa
            container saa {
                description "Enter the saa context";

                ///global-operations/oam/saa/owner
                list owner {
                    key "owner-name test";
                    description "SAA owner name";

                    ///global-operations/oam/saa/owner/owner-name
                    leaf owner-name {
                        type leafref {
                            path "/state:state/state:saa/state:owner[state:test=current()/../test]/state:owner-name";
                        }
                        description "Name of the owner of SAA test to be stopped or started";
                    }

                    ///global-operations/oam/saa/owner/test
                    leaf test {
                        type leafref {
                            path "/state:state/state:saa/state:owner[state:owner-name=current()/../owner-name]/state:test";
                        }
                        description "Name of the SAA test to be stopped or started";
                    }

                    ///global-operations/oam/saa/owner/start
                    action start {
                        description "Start the SAA test";

                        input {

                            ///global-operations/oam/saa/owner/start/input/accounting
                            leaf accounting {
                                type boolean;
                                default "true";
                                description "Disable recording results in accounting policy";
                            }

                        }
                        output {

                            ///global-operations/oam/saa/owner/start/output/operation-id
                            leaf operation-id {
                                type types-operation:operation-id;
                                description "ID assigned to the operation.";
                            }

                            ///global-operations/oam/saa/owner/start/output/start-time
                            leaf start-time {
                                type types-operation:operation-timestamp;
                                description "Time when the operation started its execution.";
                            }

                            ///global-operations/oam/saa/owner/start/output/results-path
                            leaf results-path {
                                type types-operation:operation-path;
                                description "Path to the results of the operation formatted as xpath.";
                            }

                            ///global-operations/oam/saa/owner/start/output/status
                            leaf status {
                                type types-operation:operation-status;
                                description "Status of the operation";
                            }

                            ///global-operations/oam/saa/owner/start/output/error-message
                            leaf-list error-message {
                                type types-operation:operation-message;
                                description "Error messages reported during execution of the operation.";
                            }

                            ///global-operations/oam/saa/owner/start/output/warning-message
                            leaf-list warning-message {
                                type types-operation:operation-message;
                                description "Warning messages reported during execution of the operation.";
                            }

                            ///global-operations/oam/saa/owner/start/output/info-message
                            leaf-list info-message {
                                type types-operation:operation-message;
                                description "Info messages reported during execution of the operation.";
                            }

                            ///global-operations/oam/saa/owner/start/output/end-time
                            leaf end-time {
                                type types-operation:operation-timestamp;
                                description "Time when the operation ended its execution.";
                            }

                        }
                    } // action start

                    ///global-operations/oam/saa/owner/stop
                    action stop {
                        description "Stop the SAA test";

                        input {

                            ///global-operations/oam/saa/owner/stop/input/accounting
                            leaf accounting {
                                type boolean;
                                default "true";
                                description "Disable recording results in accounting policy";
                            }

                        }
                        output {

                            ///global-operations/oam/saa/owner/stop/output/operation-id
                            leaf operation-id {
                                type types-operation:operation-id;
                                description "ID assigned to the operation.";
                            }

                            ///global-operations/oam/saa/owner/stop/output/start-time
                            leaf start-time {
                                type types-operation:operation-timestamp;
                                description "Time when the operation started its execution.";
                            }

                            ///global-operations/oam/saa/owner/stop/output/results-path
                            leaf results-path {
                                type types-operation:operation-path;
                                description "Path to the results of the operation formatted as xpath.";
                            }

                            ///global-operations/oam/saa/owner/stop/output/status
                            leaf status {
                                type types-operation:operation-status;
                                description "Status of the operation";
                            }

                            ///global-operations/oam/saa/owner/stop/output/error-message
                            leaf-list error-message {
                                type types-operation:operation-message;
                                description "Error messages reported during execution of the operation.";
                            }

                            ///global-operations/oam/saa/owner/stop/output/warning-message
                            leaf-list warning-message {
                                type types-operation:operation-message;
                                description "Warning messages reported during execution of the operation.";
                            }

                            ///global-operations/oam/saa/owner/stop/output/info-message
                            leaf-list info-message {
                                type types-operation:operation-message;
                                description "Info messages reported during execution of the operation.";
                            }

                            ///global-operations/oam/saa/owner/stop/output/end-time
                            leaf end-time {
                                type types-operation:operation-timestamp;
                                description "Time when the operation ended its execution.";
                            }

                        }
                    } // action stop

                } // list owner

            } // container saa

            ///global-operations/oam/service-activation-testhead
            container service-activation-testhead {
                description "Start or stop Service Activation Testhead service test";

                ///global-operations/oam/service-activation-testhead/service-test
                list service-test {
                    key "service-test-name";
                    description "Service test name";

                    ///global-operations/oam/service-activation-testhead/service-test/service-test-name
                    leaf service-test-name {
                        type leafref {
                            path "/state:state/state:test-oam/state:service-activation-testhead/state:service-test/state:test-name";
                        }
                        description "Name of the Service Test to be started or stopped";
                    }

                    ///global-operations/oam/service-activation-testhead/service-test/start
                    action start {
                        description "Start OAM Service Activation Testhead Service Test";

                        output {

                            ///global-operations/oam/service-activation-testhead/service-test/start/output/operation-id
                            leaf operation-id {
                                type types-operation:operation-id;
                                description "ID assigned to the operation.";
                            }

                            ///global-operations/oam/service-activation-testhead/service-test/start/output/start-time
                            leaf start-time {
                                type types-operation:operation-timestamp;
                                description "Time when the operation started its execution.";
                            }

                            ///global-operations/oam/service-activation-testhead/service-test/start/output/results-path
                            leaf results-path {
                                type types-operation:operation-path;
                                description "Path to the results of the operation formatted as xpath.";
                            }

                            ///global-operations/oam/service-activation-testhead/service-test/start/output/status
                            leaf status {
                                type types-operation:operation-status;
                                description "Status of the operation";
                            }

                            ///global-operations/oam/service-activation-testhead/service-test/start/output/error-message
                            leaf-list error-message {
                                type types-operation:operation-message;
                                description "Error messages reported during execution of the operation.";
                            }

                            ///global-operations/oam/service-activation-testhead/service-test/start/output/warning-message
                            leaf-list warning-message {
                                type types-operation:operation-message;
                                description "Warning messages reported during execution of the operation.";
                            }

                            ///global-operations/oam/service-activation-testhead/service-test/start/output/info-message
                            leaf-list info-message {
                                type types-operation:operation-message;
                                description "Info messages reported during execution of the operation.";
                            }

                            ///global-operations/oam/service-activation-testhead/service-test/start/output/end-time
                            leaf end-time {
                                type types-operation:operation-timestamp;
                                description "Time when the operation ended its execution.";
                            }

                        }
                    } // action start

                    ///global-operations/oam/service-activation-testhead/service-test/stop
                    action stop {
                        description "Stop OAM Service Activation Testhead Service Test";

                        output {

                            ///global-operations/oam/service-activation-testhead/service-test/stop/output/operation-id
                            leaf operation-id {
                                type types-operation:operation-id;
                                description "ID assigned to the operation.";
                            }

                            ///global-operations/oam/service-activation-testhead/service-test/stop/output/start-time
                            leaf start-time {
                                type types-operation:operation-timestamp;
                                description "Time when the operation started its execution.";
                            }

                            ///global-operations/oam/service-activation-testhead/service-test/stop/output/results-path
                            leaf results-path {
                                type types-operation:operation-path;
                                description "Path to the results of the operation formatted as xpath.";
                            }

                            ///global-operations/oam/service-activation-testhead/service-test/stop/output/status
                            leaf status {
                                type types-operation:operation-status;
                                description "Status of the operation";
                            }

                            ///global-operations/oam/service-activation-testhead/service-test/stop/output/error-message
                            leaf-list error-message {
                                type types-operation:operation-message;
                                description "Error messages reported during execution of the operation.";
                            }

                            ///global-operations/oam/service-activation-testhead/service-test/stop/output/warning-message
                            leaf-list warning-message {
                                type types-operation:operation-message;
                                description "Warning messages reported during execution of the operation.";
                            }

                            ///global-operations/oam/service-activation-testhead/service-test/stop/output/info-message
                            leaf-list info-message {
                                type types-operation:operation-message;
                                description "Info messages reported during execution of the operation.";
                            }

                            ///global-operations/oam/service-activation-testhead/service-test/stop/output/end-time
                            leaf end-time {
                                type types-operation:operation-timestamp;
                                description "Time when the operation ended its execution.";
                            }

                        }
                    } // action stop

                } // list service-test

            } // container service-activation-testhead

        } // container oam

        ///global-operations/ping
        action ping {
            description "Trigger ping of address or dns-name via machine interface";

            input {

                ///global-operations/ping/input/ping-type
                choice ping-type {
                    mandatory true;
                    ///global-operations/ping/input/ping-type/case-ip-or-dns
                    case case-ip-or-dns {

                        ///global-operations/ping/input/ping-type/case-ip-or-dns/destination
                        leaf destination {
                            type union {
                                type types-sros:ip-address-with-zone;
                                type types-sros:string-not-all-spaces {
                                    length "1..128";
                                }
                            }
                            mandatory true;
                            description "Destination IP address or DNS name";
                        }

                        ///global-operations/ping/input/ping-type/case-ip-or-dns/routing-options
                        choice routing-options {
                            ///global-operations/ping/input/ping-type/case-ip-or-dns/routing-options/case-bypass-routing
                            case case-bypass-routing {

                                ///global-operations/ping/input/ping-type/case-ip-or-dns/routing-options/case-bypass-routing/bypass-routing
                                leaf bypass-routing {
                                    type empty;
                                    description "Bypass routing table when sending ping request to host";
                                }

                            }
                            ///global-operations/ping/input/ping-type/case-ip-or-dns/routing-options/case-interface
                            case case-interface {

                                ///global-operations/ping/input/ping-type/case-ip-or-dns/routing-options/case-interface/interface
                                leaf interface {
                                    type types-sros:interface-name;
                                    description "Sending interface name";
                                }

                            }
                            ///global-operations/ping/input/ping-type/case-ip-or-dns/routing-options/case-next-hop
                            case case-next-hop {

                                ///global-operations/ping/input/ping-type/case-ip-or-dns/routing-options/case-next-hop/next-hop-address
                                leaf next-hop-address {
                                    type types-sros:ip-address;
                                    description "Next-hop address to send packet, ignoring routing table";
                                }

                            }
                            ///global-operations/ping/input/ping-type/case-ip-or-dns/routing-options/case-subscriber
                            case case-subscriber {

                                ///global-operations/ping/input/ping-type/case-ip-or-dns/routing-options/case-subscriber/subscriber
                                leaf subscriber {
                                    type types-subscriber-mgmt:subscriber-id;
                                    description "Subscriber ID for sending ICMP Echo Request packets";
                                }

                            }
                        }
                        ///global-operations/ping/input/ping-type/case-ip-or-dns/router-instance
                        leaf router-instance {
                            type string;
                            default "Base";
                            description "Router name or VPRN service name";
                        }

                        ///global-operations/ping/input/ping-type/case-ip-or-dns/source-address
                        leaf source-address {
                            type types-sros:ip-address;
                            description "Source IP address used in the ICMP Echo Request packet";
                        }

                    }
                    ///global-operations/ping/input/ping-type/case-srv6-policy
                    case case-srv6-policy {

                        ///global-operations/ping/input/ping-type/case-srv6-policy/srv6-policy
                        leaf srv6-policy {
                            type empty;
                            mandatory true;
                            description "Ping a Segment Routing IPv6 policy";
                        }

                        ///global-operations/ping/input/ping-type/case-srv6-policy/color
                        leaf color {
                            type uint32;
                            mandatory true;
                            description "Color identifier of the Segment Routing IPv6 policy";
                        }

                        ///global-operations/ping/input/ping-type/case-srv6-policy/endpoint
                        leaf endpoint {
                            type types-sros:ipv6-unicast-or-zero-address;
                            mandatory true;
                            description "Endpoint identifier of the Segment Routing IPv6 policy to be pinged";
                        }

                        ///global-operations/ping/input/ping-type/case-srv6-policy/segment-list
                        leaf segment-list {
                            type uint32 {
                                range "1..32";
                            }
                            description "Segment Routing IPv6 segment list to be pinged";
                        }

                    }
                }
                ///global-operations/ping/input/count
                leaf count {
                    type uint32 {
                        range "1..100000";
                    }
                    units "packets";
                    default "5";
                    description "Number of ping requests to send to the remote host";
                }

                ///global-operations/ping/input/output-format
                leaf output-format {
                    type enumeration {
                        enum summary                        { value 1; }
                        enum detail                         { value 2; }
                    }
                    default "detail";
                    description "Output format";
                }

                ///global-operations/ping/input/do-not-fragment
                leaf do-not-fragment {
                    type empty;
                    description "Do not fragment the request frame";
                }

                ///global-operations/ping/input/fc
                leaf fc {
                    type types-sros:fc-name;
                    default "nc";
                    description "Forwarding class option for the transmitted packet";
                }

                ///global-operations/ping/input/interval
                leaf interval {
                    type union {
                        type uint32 {
                            range "1..10000";
                        }
                        type decimal64 {
                            range "0.01..100.00";
                            fraction-digits 2;
                        }
                    }
                    units "seconds";
                    default "1";
                    description "Time between consecutive ping requests";
                }

                ///global-operations/ping/input/pattern
                leaf pattern {
                    type union {
                        type enumeration {
                            enum sequential                     { value -1; }
                        }
                        type int32 {
                            range "0..65535";
                        }
                    }
                    default "sequential";
                    description "Pattern string to include in the packet";
                }

                ///global-operations/ping/input/size
                leaf size {
                    type uint32 {
                        range "0..16384";
                    }
                    units "bytes";
                    default "56";
                    description "Request packet size including ICMP header and payload";
                }

                ///global-operations/ping/input/timeout
                leaf timeout {
                    type uint32 {
                        range "1..10";
                    }
                    units "seconds";
                    default "5";
                    description "Wait time for the ICMP Echo Reply packet";
                }

                ///global-operations/ping/input/tos
                leaf tos {
                    type uint32 {
                        range "0..255";
                    }
                    default "0";
                    description "Type of Service (ToS) bits in the IP header";
                }

                ///global-operations/ping/input/ttl
                leaf ttl {
                    type uint32 {
                        range "1..128";
                    }
                    default "64";
                    description "Time to Live (TTL) included in the request packet";
                }

            }
            output {

                ///global-operations/ping/output/operation-id
                leaf operation-id {
                    type types-operation:operation-id;
                    description "ID assigned to the operation.";
                }

                ///global-operations/ping/output/start-time
                leaf start-time {
                    type types-operation:operation-timestamp;
                    description "Time when the operation started its execution.";
                }

                ///global-operations/ping/output/results-path
                leaf results-path {
                    type types-operation:operation-path;
                    description "Path to the results of the operation formatted as xpath.";
                }

                ///global-operations/ping/output/results
                container results {
                    description "Enter the results context";

                    ///global-operations/ping/output/results/test-parameters
                    container test-parameters {
                        description "Enter the test-parameters context";

                        ///global-operations/ping/output/results/test-parameters/ping-type
                        choice ping-type {
                            ///global-operations/ping/output/results/test-parameters/ping-type/case-ip-or-dns
                            case case-ip-or-dns {

                                ///global-operations/ping/output/results/test-parameters/ping-type/case-ip-or-dns/destination
                                leaf destination {
                                    type union {
                                        type types-sros:ip-address-with-zone;
                                        type types-sros:string-not-all-spaces {
                                            length "1..128";
                                        }
                                    }
                                    description "IP address or DNS name that was pinged.";
                                }

                                ///global-operations/ping/output/results/test-parameters/ping-type/case-ip-or-dns/routing-options
                                choice routing-options {
                                    ///global-operations/ping/output/results/test-parameters/ping-type/case-ip-or-dns/routing-options/case-bypass-routing
                                    case case-bypass-routing {

                                        ///global-operations/ping/output/results/test-parameters/ping-type/case-ip-or-dns/routing-options/case-bypass-routing/bypass-routing
                                        leaf bypass-routing {
                                            type boolean;
                                            description
                                                "Bypass the routing table when sending to a host on a directly attached
                                                 network.";
                                        }

                                    }
                                    ///global-operations/ping/output/results/test-parameters/ping-type/case-ip-or-dns/routing-options/case-interface
                                    case case-interface {

                                        ///global-operations/ping/output/results/test-parameters/ping-type/case-ip-or-dns/routing-options/case-interface/interface
                                        leaf interface {
                                            type types-sros:interface-name;
                                            description "Sending interface for the ICMP Echo Request packet(s).";
                                        }

                                    }
                                    ///global-operations/ping/output/results/test-parameters/ping-type/case-ip-or-dns/routing-options/case-next-hop
                                    case case-next-hop {

                                        ///global-operations/ping/output/results/test-parameters/ping-type/case-ip-or-dns/routing-options/case-next-hop/next-hop-address
                                        leaf next-hop-address {
                                            type types-sros:ip-address;
                                            description "Next hop IP address used when sending ICMP Echo Request packet(s).";
                                        }

                                    }
                                    ///global-operations/ping/output/results/test-parameters/ping-type/case-ip-or-dns/routing-options/case-subscriber
                                    case case-subscriber {

                                        ///global-operations/ping/output/results/test-parameters/ping-type/case-ip-or-dns/routing-options/case-subscriber/subscriber
                                        leaf subscriber {
                                            type types-subscriber-mgmt:subscriber-id;
                                            description "Subscriber-id used when sending ICMP Echo Request packet(s).";
                                        }

                                    }
                                }
                                ///global-operations/ping/output/results/test-parameters/ping-type/case-ip-or-dns/router-instance
                                leaf router-instance {
                                    type types-sros:router-instance-base-management-vprn-loose;
                                    description "Router used for the test ('Base', 'management', 'vpls-management', or a VPRN service name).";
                                }

                                ///global-operations/ping/output/results/test-parameters/ping-type/case-ip-or-dns/source-address
                                leaf source-address {
                                    type types-sros:ip-address;
                                    description
                                        "Source IP address that was loaded into the IP header of the ICMP Echo
                                         Request packet(s).";
                                }

                            }
                            ///global-operations/ping/output/results/test-parameters/ping-type/case-srv6-policy
                            case case-srv6-policy {

                                ///global-operations/ping/output/results/test-parameters/ping-type/case-srv6-policy/srv6-policy
                                leaf srv6-policy {
                                    type boolean;
                                    description "ping a Segment Routing IPv6 policy";
                                }

                                ///global-operations/ping/output/results/test-parameters/ping-type/case-srv6-policy/color
                                leaf color {
                                    type uint32;
                                    description "Color identifier of the Segment Routing IPv6 policy to be pinged";
                                }

                                ///global-operations/ping/output/results/test-parameters/ping-type/case-srv6-policy/endpoint
                                leaf endpoint {
                                    type types-sros:ipv6-unicast-or-zero-address;
                                    description "Endpoint identifier of the Segment Routing IPv6 policy to be pinged";
                                }

                                ///global-operations/ping/output/results/test-parameters/ping-type/case-srv6-policy/segment-list
                                leaf segment-list {
                                    type uint32 {
                                        range "0..32";
                                    }
                                    description "The Segment Routing IPv6 segment list to be pinged.  Unspecified: system-selected segment list.";
                                }

                            }
                        }
                        ///global-operations/ping/output/results/test-parameters/count
                        leaf count {
                            type uint32 {
                                range "1..100000";
                            }
                            units "packets";
                            description "Number of ICMP Echo Request packet(s) sent.";
                        }

                        ///global-operations/ping/output/results/test-parameters/output-format
                        leaf output-format {
                            type enumeration {
                                enum summary                        { value 1; }
                                enum detail                         { value 2; }
                            }
                            description
                                "If detail output was active, extra information was returned in error
                                 cases";
                        }

                        ///global-operations/ping/output/results/test-parameters/do-not-fragment
                        leaf do-not-fragment {
                            type boolean;
                            description
                                "ICMP Echo Request packet(s) were not allowed to be fragmented (valid for
                                 IPv4 only).";
                        }

                        ///global-operations/ping/output/results/test-parameters/fc
                        leaf fc {
                            type types-sros:fc-name;
                            description "Forwarding Class for the transmitted ICMP Echo Request packet(s).";
                        }

                        ///global-operations/ping/output/results/test-parameters/interval
                        leaf interval {
                            type union {
                                type uint32 {
                                    range "1..10000";
                                }
                                type decimal64 {
                                    range "0.01..100.00";
                                    fraction-digits 2;
                                }
                            }
                            units "seconds";
                            description "Interval between ICMP Echo Request packets sent.";
                        }

                        ///global-operations/ping/output/results/test-parameters/pattern
                        leaf pattern {
                            type union {
                                type enumeration {
                                    enum sequential                     { value -1; }
                                }
                                type int32 {
                                    range "0..65535";
                                }
                            }
                            description
                                "Two byte value used to pad the ICMP Echo Request packet(s). 'sequential'
                                 indicates bytes increasing by one.";
                        }

                        ///global-operations/ping/output/results/test-parameters/size
                        leaf size {
                            type uint32 {
                                range "0..16384";
                            }
                            units "bytes";
                            description
                                "Number of bytes in the combined ICMP Header (8 bytes) and ICMP Payload
                                 (variable size) of the ICMP Echo Request packet(s).";
                        }

                        ///global-operations/ping/output/results/test-parameters/timeout
                        leaf timeout {
                            type uint32 {
                                range "1..10";
                            }
                            units "seconds";
                            description
                                "Maximum time (in seconds) that was allowed for ICMP Echo Reply packet(s).
                                 The timer was started when the last ICMP Echo Request was sent.";
                        }

                        ///global-operations/ping/output/results/test-parameters/tos
                        leaf tos {
                            type uint32 {
                                range "0..255";
                            }
                            description
                                "Type of Service value to be loaded into the DSCP and ECN fields of the IP
                                 header of the ICMP Echo Request packet(s).";
                        }

                        ///global-operations/ping/output/results/test-parameters/ttl
                        leaf ttl {
                            type uint32 {
                                range "1..128";
                            }
                            description
                                "Time To Live value (IPv4) or Hop Limit value (IPv6) to be loaded into the
                                 IP header of the ICMP Echo Request packet(s).";
                        }

                    } // container test-parameters

                    ///global-operations/ping/output/results/probe
                    list probe {
                        key "probe-index";
                        description "Probe data for the specified test run.";

                        ///global-operations/ping/output/results/probe/probe-index
                        leaf probe-index {
                            type uint32 {
                                range "1..max";
                            }
                            description "Index of probes with the specified test run.";
                        }

                        ///global-operations/ping/output/results/probe/status
                        leaf status {
                            type types-oam:response-status;
                            description "The OAM response status code for the specified test.";
                        }

                        ///global-operations/ping/output/results/probe/round-trip-time
                        leaf round-trip-time {
                            type uint32;
                            units "microseconds";
                            description "Indicates the round trip time for the specified probe.";
                        }

                        ///global-operations/ping/output/results/probe/response-packet
                        container response-packet {
                            description "Data from packet received as a response to transmitted probe.";

                            ///global-operations/ping/output/results/probe/response-packet/size
                            leaf size {
                                type uint32;
                                units "bytes";
                                description
                                    "Indicates the number of bytes in the response packet for the specified
                                     probe.";
                            }

                            ///global-operations/ping/output/results/probe/response-packet/source-address
                            leaf source-address {
                                type types-sros:ip-address-with-zone;
                                description
                                    "Indicates the source address in the response packet for the specified
                                     probe.";
                            }

                            ///global-operations/ping/output/results/probe/response-packet/icmp-sequence-number
                            leaf icmp-sequence-number {
                                type uint32;
                                description
                                    "Indicates the ICMP sequence number in the response packet for the
                                     specified probe.";
                            }

                            ///global-operations/ping/output/results/probe/response-packet/ttl
                            leaf ttl {
                                type uint32;
                                description
                                    "Indicates the time to live in the response packet for the specified
                                     probe.";
                            }

                        } // container response-packet

                    } // list probe

                    ///global-operations/ping/output/results/summary
                    container summary {
                        description "Test run summary data.";

                        ///global-operations/ping/output/results/summary/statistics
                        container statistics {
                            description "Test run summary statistics.";

                            ///global-operations/ping/output/results/summary/statistics/packets
                            container packets {
                                description "Packet statistics for the specified test run.";

                                ///global-operations/ping/output/results/summary/statistics/packets/sent
                                leaf sent {
                                    type uint32;
                                    units "packets";
                                    description "Indicates the number of packets sent for the specified test run.";
                                }

                                ///global-operations/ping/output/results/summary/statistics/packets/received
                                leaf received {
                                    type uint32;
                                    units "packets";
                                    description "Indicates the number of packets received for the specified test run.";
                                }

                                ///global-operations/ping/output/results/summary/statistics/packets/loss
                                leaf loss {
                                    type decimal64 {
                                        range "0.00..100.00";
                                        fraction-digits 2;
                                    }
                                    units "percent";
                                    description
                                        "Indicates the number of packet loss percentage for the specified test
                                         run.";
                                }

                            } // container packets

                            ///global-operations/ping/output/results/summary/statistics/round-trip-time
                            container round-trip-time {
                                description "Test run round trip time statistics.";

                                ///global-operations/ping/output/results/summary/statistics/round-trip-time/minimum
                                leaf minimum {
                                    type uint32;
                                    units "microseconds";
                                    description "Indicates the minimum round trip time for the specified test run.";
                                }

                                ///global-operations/ping/output/results/summary/statistics/round-trip-time/average
                                leaf average {
                                    type uint32;
                                    units "microseconds";
                                    description "Indicates the average round trip time for the specified test run.";
                                }

                                ///global-operations/ping/output/results/summary/statistics/round-trip-time/maximum
                                leaf maximum {
                                    type uint32;
                                    units "microseconds";
                                    description "Indicates the maximum round trip time for the specified test run.";
                                }

                                ///global-operations/ping/output/results/summary/statistics/round-trip-time/standard-deviation
                                leaf standard-deviation {
                                    type uint32;
                                    units "microseconds";
                                    description
                                        "Indicates the standard deviation for the round trip times for the
                                         specified test run.";
                                }

                            } // container round-trip-time

                        } // container statistics

                    } // container summary

                } // container results

                ///global-operations/ping/output/status
                leaf status {
                    type types-operation:operation-status;
                    description "Status of the operation";
                }

                ///global-operations/ping/output/error-message
                leaf-list error-message {
                    type types-operation:operation-message;
                    description "Error messages reported during execution of the operation.";
                }

                ///global-operations/ping/output/warning-message
                leaf-list warning-message {
                    type types-operation:operation-message;
                    description "Warning messages reported during execution of the operation.";
                }

                ///global-operations/ping/output/info-message
                leaf-list info-message {
                    type types-operation:operation-message;
                    description "Info messages reported during execution of the operation.";
                }

                ///global-operations/ping/output/end-time
                leaf end-time {
                    type types-operation:operation-timestamp;
                    description "Time when the operation ended its execution.";
                }

            }
        } // action ping

        ///global-operations/traceroute
        action traceroute {
            description "Trigger traceroute via machine interface";

            input {

                ///global-operations/traceroute/input/traceroute-type
                choice traceroute-type {
                    mandatory true;
                    ///global-operations/traceroute/input/traceroute-type/case-ip-or-dns
                    case case-ip-or-dns {

                        ///global-operations/traceroute/input/traceroute-type/case-ip-or-dns/destination
                        leaf destination {
                            type union {
                                type types-sros:ip-unicast-address;
                                type types-sros:string-not-all-spaces {
                                    length "1..128";
                                }
                            }
                            mandatory true;
                            description "Destination IP address or DNS name";
                        }

                        ///global-operations/traceroute/input/traceroute-type/case-ip-or-dns/router-instance
                        leaf router-instance {
                            type string;
                            default "Base";
                            description "Router name or VPRN service name";
                        }

                        ///global-operations/traceroute/input/traceroute-type/case-ip-or-dns/source-address
                        leaf source-address {
                            type types-sros:ip-address;
                            description "Source address of the probe packets";
                        }

                    }
                    ///global-operations/traceroute/input/traceroute-type/case-srv6-policy
                    case case-srv6-policy {

                        ///global-operations/traceroute/input/traceroute-type/case-srv6-policy/srv6-policy
                        leaf srv6-policy {
                            type empty;
                            mandatory true;
                            description "Trace an SRv6 policy";
                        }

                        ///global-operations/traceroute/input/traceroute-type/case-srv6-policy/color
                        leaf color {
                            type uint32;
                            mandatory true;
                            description "Color ID of the SRv6 policy to trace";
                        }

                        ///global-operations/traceroute/input/traceroute-type/case-srv6-policy/endpoint
                        leaf endpoint {
                            type types-sros:ipv6-unicast-or-zero-address;
                            mandatory true;
                            description "Endpoint of the SRv6 policy to trace";
                        }

                        ///global-operations/traceroute/input/traceroute-type/case-srv6-policy/segment-list
                        leaf segment-list {
                            type uint32 {
                                range "1..32";
                            }
                            description "SR IPv6 segment list to trace";
                        }

                    }
                }
                ///global-operations/traceroute/input/decode
                leaf decode {
                    type enumeration {
                        enum none                           { value 0; }
                        enum original-datagram              { value 1; }
                    }
                    default "none";
                    description "Perform original datagram parsing functions";
                }

                ///global-operations/traceroute/input/dest-port
                leaf dest-port {
                    type uint32 {
                        range "1..65535";
                    }
                    default "33434";
                    description "Transport protocol destination port number";
                }

                ///global-operations/traceroute/input/dest-port-udp-fixed
                leaf dest-port-udp-fixed {
                    type empty;
                    description "Avoid increment of destination port number for UDP test";
                }

                ///global-operations/traceroute/input/detail
                leaf detail {
                    type empty;
                    description "Display MPLS label stack information or TCP port status";
                }

                ///global-operations/traceroute/input/min-ttl
                leaf min-ttl {
                    type uint32 {
                        range "1..255";
                    }
                    default "1";
                    description "First hop traceroute probes using the TTL value";
                }

                ///global-operations/traceroute/input/ttl
                leaf ttl {
                    type uint32 {
                        range "1..255";
                    }
                    default "30";
                    description "Maximum number of hops (TTL) to probe";
                }

                ///global-operations/traceroute/input/numeric
                leaf numeric {
                    type empty;
                    description "Display IP addresses instead of DNS names";
                }

                ///global-operations/traceroute/input/probe-count
                leaf probe-count {
                    type uint32 {
                        range "1..10";
                    }
                    default "3";
                    description "Number of probes to send per hop";
                }

                ///global-operations/traceroute/input/protocol
                leaf protocol {
                    type enumeration {
                        enum udp                            { value 1; }
                        enum tcp                            { value 2; }
                    }
                    default "udp";
                    description "Packet type to send";
                }

                ///global-operations/traceroute/input/size
                leaf size {
                    type uint32 {
                        range "0..9786";
                    }
                    units "bytes";
                    default "0";
                    description "Number of pad bytes in each transmitted packet";
                }

                ///global-operations/traceroute/input/tos
                leaf tos {
                    type uint32 {
                        range "0..255";
                    }
                    default "0";
                    description "Type of Service (ToS) bits in the IP header";
                }

                ///global-operations/traceroute/input/wait
                leaf wait {
                    type uint32 {
                        range "10..60000";
                    }
                    units "milliseconds";
                    default "5000";
                    description "Time to wait for a response to the probe";
                }

            }
            output {

                ///global-operations/traceroute/output/operation-id
                leaf operation-id {
                    type types-operation:operation-id;
                    description "ID assigned to the operation.";
                }

                ///global-operations/traceroute/output/start-time
                leaf start-time {
                    type types-operation:operation-timestamp;
                    description "Time when the operation started its execution.";
                }

                ///global-operations/traceroute/output/results-path
                leaf results-path {
                    type types-operation:operation-path;
                    description "Path to the results of the operation formatted as xpath.";
                }

                ///global-operations/traceroute/output/results
                container results {
                    description "Enter the results context";

                    ///global-operations/traceroute/output/results/test-parameters
                    container test-parameters {
                        description "Enter the test-parameters context";

                        ///global-operations/traceroute/output/results/test-parameters/traceroute-type
                        choice traceroute-type {
                            ///global-operations/traceroute/output/results/test-parameters/traceroute-type/case-ip-or-dns
                            case case-ip-or-dns {

                                ///global-operations/traceroute/output/results/test-parameters/traceroute-type/case-ip-or-dns/destination
                                leaf destination {
                                    type union {
                                        type types-sros:ip-address;
                                        type types-sros:string-not-all-spaces {
                                            length "1..128";
                                        }
                                    }
                                    description "The destination IP address or DNS name";
                                }

                                ///global-operations/traceroute/output/results/test-parameters/traceroute-type/case-ip-or-dns/router-instance
                                leaf router-instance {
                                    type types-sros:router-instance-base-management-vprn-loose;
                                    description "Router instance used for the traceroute (i.e. 'Base', 'management', 'vpls-management' or a VPRN service name)";
                                }

                                ///global-operations/traceroute/output/results/test-parameters/traceroute-type/case-ip-or-dns/source-address
                                leaf source-address {
                                    type types-sros:ip-address;
                                    description "The IP source address to use for the test";
                                }

                            }
                            ///global-operations/traceroute/output/results/test-parameters/traceroute-type/case-srv6-policy
                            case case-srv6-policy {

                                ///global-operations/traceroute/output/results/test-parameters/traceroute-type/case-srv6-policy/srv6-policy
                                leaf srv6-policy {
                                    type boolean;
                                    description "Trace a Segment Routing IPv6 policy";
                                }

                                ///global-operations/traceroute/output/results/test-parameters/traceroute-type/case-srv6-policy/color
                                leaf color {
                                    type uint32;
                                    description "Color identifier of the Segment Routing IPv6 policy to be traced";
                                }

                                ///global-operations/traceroute/output/results/test-parameters/traceroute-type/case-srv6-policy/endpoint
                                leaf endpoint {
                                    type types-sros:ipv6-unicast-or-zero-address;
                                    description "Endpoint identifier of the Segment Routing IPv6 policy to be traced";
                                }

                                ///global-operations/traceroute/output/results/test-parameters/traceroute-type/case-srv6-policy/segment-list
                                leaf segment-list {
                                    type uint32 {
                                        range "0..32";
                                    }
                                    description "The Segment Routing IPv6 segment list to be traced.  Zero: system-selected segment list.";
                                }

                            }
                        }
                        ///global-operations/traceroute/output/results/test-parameters/decode
                        leaf decode {
                            type enumeration {
                                enum none                           { value 0; }
                                enum original-datagram              { value 1; }
                            }
                            description "Decode and display additional fields in replies received";
                        }

                        ///global-operations/traceroute/output/results/test-parameters/dest-port
                        leaf dest-port {
                            type uint32 {
                                range "1..65535";
                            }
                            description
                                "For a TCP test, the destination TCP port number to send.
                                 For a UDP test, the base or only destination UDP port number to send (see dest-port-udp-fixed)";
                        }

                        ///global-operations/traceroute/output/results/test-parameters/dest-port-udp-fixed
                        leaf dest-port-udp-fixed {
                            type boolean;
                            description
                                "For a UDP test, 'true' uses the same destination UDP port number in each
                                 transmitted packet (i.e. the port number is not incremented)";
                        }

                        ///global-operations/traceroute/output/results/test-parameters/detail
                        leaf detail {
                            type boolean;
                            description "Display MPLS label stack information (if available)";
                        }

                        ///global-operations/traceroute/output/results/test-parameters/min-ttl
                        leaf min-ttl {
                            type uint32 {
                                range "1..255";
                            }
                            description "The minimum number of hops to probe";
                        }

                        ///global-operations/traceroute/output/results/test-parameters/ttl
                        leaf ttl {
                            type uint32 {
                                range "1..255";
                            }
                            description "The maximum number of hops to probe";
                        }

                        ///global-operations/traceroute/output/results/test-parameters/numeric
                        leaf numeric {
                            type boolean;
                            description "'true' avoids looking up DNS names when displaying results";
                        }

                        ///global-operations/traceroute/output/results/test-parameters/probe-count
                        leaf probe-count {
                            type uint32 {
                                range "1..10";
                            }
                            description "The number of probes to send per hop";
                        }

                        ///global-operations/traceroute/output/results/test-parameters/protocol
                        leaf protocol {
                            type enumeration {
                                enum udp                            { value 1; }
                                enum tcp                            { value 2; }
                            }
                            description "Send UDP packets or TCP-SYN packets";
                        }

                        ///global-operations/traceroute/output/results/test-parameters/size
                        leaf size {
                            type uint32 {
                                range "0..9786";
                            }
                            units "bytes";
                            description "The number of pad bytes in each transmitted packet";
                        }

                        ///global-operations/traceroute/output/results/test-parameters/tos
                        leaf tos {
                            type uint32 {
                                range "0..255";
                            }
                            description "The IPv4 Type of Service or IPv6 Traffic Class in each transmitted packet";
                        }

                        ///global-operations/traceroute/output/results/test-parameters/wait
                        leaf wait {
                            type uint32 {
                                range "10..60000";
                            }
                            units "milliseconds";
                            description "The time (in milliseconds) to wait for a response to a packet";
                        }

                    } // container test-parameters

                    ///global-operations/traceroute/output/results/hop
                    list hop {
                        key "hop-index";
                        description "Per-hop (also known as per-TTL) test results";

                        ///global-operations/traceroute/output/results/hop/hop-index
                        leaf hop-index {
                            type uint32 {
                                range "1..max";
                            }
                            description "The hop index of the test results";
                        }

                        ///global-operations/traceroute/output/results/hop/probe
                        list probe {
                            key "probe-index";
                            description "Per-probe test results";

                            ///global-operations/traceroute/output/results/hop/probe/probe-index
                            leaf probe-index {
                                type uint32 {
                                    range "1..max";
                                }
                                description "Index of the probe within the specified hop for the test";
                            }

                            ///global-operations/traceroute/output/results/hop/probe/status
                            leaf status {
                                type types-oam:response-status;
                                description "The status of the probe (e.g. response-received, request-timed-out)";
                            }

                            ///global-operations/traceroute/output/results/hop/probe/round-trip-time
                            leaf round-trip-time {
                                type uint32;
                                units "microseconds";
                                description "The round trip time for the specified probe and response";
                            }

                            ///global-operations/traceroute/output/results/hop/probe/size
                            leaf size {
                                type uint32;
                                units "bytes";
                                description "The number of bytes in the transmitted packet (zero if no packet was sent)";
                            }

                            ///global-operations/traceroute/output/results/hop/probe/response-packet
                            container response-packet {
                                description "Test results copied (or derived) from a response packet";

                                ///global-operations/traceroute/output/results/hop/probe/response-packet/icmp-type
                                leaf icmp-type {
                                    type uint32 {
                                        range "0..255";
                                    }
                                    description
                                        "The ICMP or ICMPv6 Type in the received response.
                                         icmp-type = 0 AND icmp-code = 0 indicates no Type and Code
                                         is available";
                                }

                                ///global-operations/traceroute/output/results/hop/probe/response-packet/icmp-code
                                leaf icmp-code {
                                    type uint32 {
                                        range "0..255";
                                    }
                                    description
                                        "The ICMP or ICMPv6 Code in the received response.
                                         icmp-type = 0 AND icmp-code = 0 indicates no Type and Code
                                         is available";
                                }

                                ///global-operations/traceroute/output/results/hop/probe/response-packet/mtu-exceeded
                                leaf mtu-exceeded {
                                    type uint32;
                                    units "bytes";
                                    description
                                        "The MTU (Maximum Transmission Unit) in the received response.
                                         When the MTU is non-zero, it indicates the MTU exceeded by
                                         a transmitted packet .";
                                }

                                ///global-operations/traceroute/output/results/hop/probe/response-packet/source-address
                                leaf source-address {
                                    type types-sros:ip-address;
                                    description
                                        "The IP source address in the response packet (i.e. the address of the
                                         replying node)";
                                }

                                ///global-operations/traceroute/output/results/hop/probe/response-packet/source-host-name
                                leaf source-host-name {
                                    type string {
                                        length "0..255";
                                    }
                                    description "The host name looked up (in DNS) using the IP address of the replying node";
                                }

                                ///global-operations/traceroute/output/results/hop/probe/response-packet/tcp-port-status
                                leaf tcp-port-status {
                                    type enumeration {
                                        enum none                           { value 1; }
                                        enum tcp-port-open                  { value 2; }
                                        enum tcp-port-closed                { value 3; }
                                    }
                                    description
                                        "The operational state of the probed TCP port on the
                                         test's destination node. 'none' is returned if the test's protocol
                                         is UDP, or the replying node is not the test's destination";
                                }

                                ///global-operations/traceroute/output/results/hop/probe/response-packet/mpls-label-stack-entry
                                list mpls-label-stack-entry {
                                    key "index";
                                    description "The information read from an RFC 4950 MPLS Label Stack Object in the response packet";

                                    ///global-operations/traceroute/output/results/hop/probe/response-packet/mpls-label-stack-entry/index
                                    leaf index {
                                        type uint32 {
                                            range "1..max";
                                        }
                                        description "Index of an RFC 4950 MPLS Label Stack Entry within the MPLS Label Stack Object";
                                    }

                                    ///global-operations/traceroute/output/results/hop/probe/response-packet/mpls-label-stack-entry/label
                                    leaf label {
                                        type types-sros:mpls-label-full-range;
                                        description "The Label field within the specified RFC 4950 MPLS Label Stack Entry";
                                    }

                                    ///global-operations/traceroute/output/results/hop/probe/response-packet/mpls-label-stack-entry/traffic-class
                                    leaf traffic-class {
                                        type uint32 {
                                            range "0..7";
                                        }
                                        description "The Experimental field within the specified RFC 4950 MPLS Label Stack Entry (subsequently renamed to Traffic Class)";
                                    }

                                    ///global-operations/traceroute/output/results/hop/probe/response-packet/mpls-label-stack-entry/bottom-of-stack
                                    leaf bottom-of-stack {
                                        type uint32 {
                                            range "0..1";
                                        }
                                        description "The Bottom of Stack field within the specified RFC 4950 MPLS Label Stack Entry";
                                    }

                                    ///global-operations/traceroute/output/results/hop/probe/response-packet/mpls-label-stack-entry/ttl
                                    leaf ttl {
                                        type uint32 {
                                            range "0..255";
                                        }
                                        description "The TTL field within the specified RFC 4950 MPLS Label Stack Entry";
                                    }

                                } // list mpls-label-stack-entry

                                ///global-operations/traceroute/output/results/hop/probe/response-packet/original-datagram
                                container original-datagram {
                                    description "Information copied from the Original Datagram field within the ICMPv6 response packet";

                                    ///global-operations/traceroute/output/results/hop/probe/response-packet/original-datagram/header
                                    list header {
                                        key "header-index";
                                        description "information copied from the headers within the Original Datagram field within the ICMPv6 response packet";

                                        ///global-operations/traceroute/output/results/hop/probe/response-packet/original-datagram/header/header-index
                                        leaf header-index {
                                            type uint32 {
                                                range "1..max";
                                            }
                                            description "The sequence number of the header within the Original Datagram field within the ICMPv6 response packet";
                                        }

                                        ///global-operations/traceroute/output/results/hop/probe/response-packet/original-datagram/header/header-type-choice
                                        choice header-type-choice {
                                            ///global-operations/traceroute/output/results/hop/probe/response-packet/original-datagram/header/header-type-choice/ipv6-case
                                            case ipv6-case {

                                                ///global-operations/traceroute/output/results/hop/probe/response-packet/original-datagram/header/header-type-choice/ipv6-case/ipv6-header
                                                container ipv6-header {
                                                    description "An IPv6 header within the Original Datagram field within the ICMPv6 response packet";

                                                    ///global-operations/traceroute/output/results/hop/probe/response-packet/original-datagram/header/header-type-choice/ipv6-case/ipv6-header/destination-address
                                                    leaf destination-address {
                                                        type types-sros:ip-address;
                                                        description "The destination address field within the IPv6 header within the Original Datagram field within the ICMPv6 response packet";
                                                    }

                                                    ///global-operations/traceroute/output/results/hop/probe/response-packet/original-datagram/header/header-type-choice/ipv6-case/ipv6-header/dscp
                                                    leaf dscp {
                                                        type types-sros:named-item-or-empty;
                                                        description "The Differentiated Services Code Point (DSCP) field within the IPv6 header within the Original Datagram field within the ICMPv6 response packet";
                                                    }

                                                    ///global-operations/traceroute/output/results/hop/probe/response-packet/original-datagram/header/header-type-choice/ipv6-case/ipv6-header/hop-limit
                                                    leaf hop-limit {
                                                        type uint32 {
                                                            range "0..255";
                                                        }
                                                        description "The Hop Limit field within the IPv6 header within the Original Datagram field within the ICMPv6 response packet";
                                                    }

                                                    ///global-operations/traceroute/output/results/hop/probe/response-packet/original-datagram/header/header-type-choice/ipv6-case/ipv6-header/source-address
                                                    leaf source-address {
                                                        type types-sros:ip-address;
                                                        description "The source address field within the IPv6 header within the Original Datagram field within the ICMPv6 response packet";
                                                    }

                                                } // container ipv6-header

                                            }
                                            ///global-operations/traceroute/output/results/hop/probe/response-packet/original-datagram/header/header-type-choice/srv6-case
                                            case srv6-case {

                                                ///global-operations/traceroute/output/results/hop/probe/response-packet/original-datagram/header/header-type-choice/srv6-case/srv6-header
                                                container srv6-header {
                                                    description "An SRv6 header within the Original Datagram field within the ICMPv6 response packet";

                                                    ///global-operations/traceroute/output/results/hop/probe/response-packet/original-datagram/header/header-type-choice/srv6-case/srv6-header/segments-left
                                                    leaf segments-left {
                                                        type uint32 {
                                                            range "0..255";
                                                        }
                                                        description "The Segments Left field within the SRv6 header within the Original Datagram field within the ICMPv6 response packet";
                                                    }

                                                    ///global-operations/traceroute/output/results/hop/probe/response-packet/original-datagram/header/header-type-choice/srv6-case/srv6-header/segment-list
                                                    list segment-list {
                                                        key "segment-index";
                                                        description "Segment List addresses copied from the SRv6 header within the Original Datagram field within the ICMPv6 response packet";

                                                        ///global-operations/traceroute/output/results/hop/probe/response-packet/original-datagram/header/header-type-choice/srv6-case/srv6-header/segment-list/segment-index
                                                        leaf segment-index {
                                                            type uint32;
                                                            description "The sequence number of the Segment address within the SRv6 header within the Original Datagram field within the ICMPv6 response packet";
                                                        }

                                                        ///global-operations/traceroute/output/results/hop/probe/response-packet/original-datagram/header/header-type-choice/srv6-case/srv6-header/segment-list/segment-address
                                                        leaf segment-address {
                                                            type types-sros:ip-address;
                                                            description "A Segment address within the SRv6 header within the Original Datagram field within the ICMPv6 response packet";
                                                        }

                                                    } // list segment-list

                                                } // container srv6-header

                                            }
                                        }
                                    } // list header

                                } // container original-datagram

                            } // container response-packet

                        } // list probe

                    } // list hop

                } // container results

                ///global-operations/traceroute/output/status
                leaf status {
                    type types-operation:operation-status;
                    description "Status of the operation";
                }

                ///global-operations/traceroute/output/error-message
                leaf-list error-message {
                    type types-operation:operation-message;
                    description "Error messages reported during execution of the operation.";
                }

                ///global-operations/traceroute/output/warning-message
                leaf-list warning-message {
                    type types-operation:operation-message;
                    description "Warning messages reported during execution of the operation.";
                }

                ///global-operations/traceroute/output/info-message
                leaf-list info-message {
                    type types-operation:operation-message;
                    description "Info messages reported during execution of the operation.";
                }

                ///global-operations/traceroute/output/end-time
                leaf end-time {
                    type types-operation:operation-timestamp;
                    description "Time when the operation ended its execution.";
                }

            }
        } // action traceroute

    } // container global-operations

}
