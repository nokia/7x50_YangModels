module nokia-li-conf {

    yang-version "1.1";

    namespace "urn:nokia.com:sros:ns:yang:sr:li-conf";

    prefix "li-conf";

    import ietf-inet-types                { prefix "inet"; }
    import ietf-yang-types                { prefix "yang"; }
    import nokia-sros-yang-extensions     { prefix "sros-ext"; }
    import nokia-types-filter             { prefix "types-filter"; }
    import nokia-types-log                { prefix "types-log"; }
    import nokia-types-services           { prefix "types-services"; }
    import nokia-types-sros               { prefix "types-sros"; }
    import nokia-types-subscriber-mgmt    { prefix "types-submgt"; }

    sros-ext:sros-major-release "rel23";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-li-conf YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-05-24";

    ///nokia-li-conf/li
    container li {
        description "Configure lawful intercept";


        ///nokia-li-conf/li/li-filter
        container li-filter {
            description "Enter the li-filter context";

            ///nokia-li-conf/li/li-filter/lock-filter
            leaf lock-filter {
                type enumeration {
                    enum lock                           { value 0; }
                    enum unlock                         { value 2; }
                }
                default "lock";
                description "Lock state of LI filters";
            }

            ///nokia-li-conf/li/li-filter/li-ip-filter
            list li-ip-filter {
                key "li-filter-name";
                description "Enter the li-ip-filter list instance";

                ///nokia-li-conf/li/li-filter/li-ip-filter/li-filter-name
                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                ///nokia-li-conf/li/li-filter/li-ip-filter/description
                leaf description {
                    type types-sros:description;
                    description "Text description";
                }

                ///nokia-li-conf/li/li-filter/li-ip-filter/entry
                list entry {
                    key "li-entry-id";
                    description "Enter the entry list instance";

                    ///nokia-li-conf/li/li-filter/li-ip-filter/entry/li-entry-id
                    leaf li-entry-id {
                        type types-filter:limited-entry-id;
                        description "LI filter entry ID";
                    }

                    ///nokia-li-conf/li/li-filter/li-ip-filter/entry/description
                    leaf description {
                        type types-sros:description;
                        description "Text description";
                    }

                    ///nokia-li-conf/li/li-filter/li-ip-filter/entry/match
                    container match {
                        description "Enter the match context";

                        ///nokia-li-conf/li/li-filter/li-ip-filter/entry/match/protocol
                        leaf protocol {
                            type types-sros:match-ip-protocol;
                            description "IP protocol to match";
                        }

                        ///nokia-li-conf/li/li-filter/li-ip-filter/entry/match/fragment
                        leaf fragment {
                            type enumeration {
                                enum false                          { value 2; }
                                enum true                           { value 3; }
                            }
                            description "Fragmentation state as the match criterion";
                        }

                        ///nokia-li-conf/li/li-filter/li-ip-filter/entry/match/dst-port
                        container dst-port {
                            description "Enter the dst-port context";

                            ///nokia-li-conf/li/li-filter/li-ip-filter/entry/match/dst-port/port
                            choice port {
                                ///nokia-li-conf/li/li-filter/li-ip-filter/entry/match/dst-port/port/eq
                                case eq {

                                    ///nokia-li-conf/li/li-filter/li-ip-filter/entry/match/dst-port/port/eq/eq
                                    leaf eq {
                                        type uint16 {
                                            range "0..65535";
                                        }
                                        description "Condition on equality to specified value";
                                    }

                                }
                                ///nokia-li-conf/li/li-filter/li-ip-filter/entry/match/dst-port/port/lt
                                case lt {

                                    ///nokia-li-conf/li/li-filter/li-ip-filter/entry/match/dst-port/port/lt/lt
                                    leaf lt {
                                        type uint16 {
                                            range "1..65535";
                                        }
                                        description "Condition on being less than the specified value";
                                    }

                                }
                                ///nokia-li-conf/li/li-filter/li-ip-filter/entry/match/dst-port/port/gt
                                case gt {

                                    ///nokia-li-conf/li/li-filter/li-ip-filter/entry/match/dst-port/port/gt/gt
                                    leaf gt {
                                        type uint16 {
                                            range "0..65534";
                                        }
                                        description "Condition on being greater than the specified value";
                                    }

                                }
                                ///nokia-li-conf/li/li-filter/li-ip-filter/entry/match/dst-port/port/range
                                case range {

                                    ///nokia-li-conf/li/li-filter/li-ip-filter/entry/match/dst-port/port/range/range
                                    container range {
                                        presence "Enable the range context";
                                        description "Enable the range context";

                                        ///nokia-li-conf/li/li-filter/li-ip-filter/entry/match/dst-port/port/range/range/start
                                        leaf start {
                                            type uint16 {
                                                range "0..65534";
                                            }
                                            mandatory true;
                                            description "Lower bound port to match";
                                        }

                                        ///nokia-li-conf/li/li-filter/li-ip-filter/entry/match/dst-port/port/range/range/end
                                        leaf end {
                                            type uint16 {
                                                range "1..65535";
                                            }
                                            mandatory true;
                                            description "Upper bound port to match";
                                        }

                                    } // container range

                                }
                            }
                        } // container dst-port

                        ///nokia-li-conf/li/li-filter/li-ip-filter/entry/match/src-port
                        container src-port {
                            description "Enter the src-port context";

                            ///nokia-li-conf/li/li-filter/li-ip-filter/entry/match/src-port/port
                            choice port {
                                ///nokia-li-conf/li/li-filter/li-ip-filter/entry/match/src-port/port/eq
                                case eq {

                                    ///nokia-li-conf/li/li-filter/li-ip-filter/entry/match/src-port/port/eq/eq
                                    leaf eq {
                                        type uint16 {
                                            range "0..65535";
                                        }
                                        description "Condition on equality to specified value";
                                    }

                                }
                                ///nokia-li-conf/li/li-filter/li-ip-filter/entry/match/src-port/port/lt
                                case lt {

                                    ///nokia-li-conf/li/li-filter/li-ip-filter/entry/match/src-port/port/lt/lt
                                    leaf lt {
                                        type uint16 {
                                            range "1..65535";
                                        }
                                        description "Condition on being less than the specified value";
                                    }

                                }
                                ///nokia-li-conf/li/li-filter/li-ip-filter/entry/match/src-port/port/gt
                                case gt {

                                    ///nokia-li-conf/li/li-filter/li-ip-filter/entry/match/src-port/port/gt/gt
                                    leaf gt {
                                        type uint16 {
                                            range "0..65534";
                                        }
                                        description "Condition on being greater than the specified value";
                                    }

                                }
                                ///nokia-li-conf/li/li-filter/li-ip-filter/entry/match/src-port/port/range
                                case range {

                                    ///nokia-li-conf/li/li-filter/li-ip-filter/entry/match/src-port/port/range/range
                                    container range {
                                        presence "Enable the range context";
                                        description "Enable the range context";

                                        ///nokia-li-conf/li/li-filter/li-ip-filter/entry/match/src-port/port/range/range/start
                                        leaf start {
                                            type uint16 {
                                                range "0..65534";
                                            }
                                            mandatory true;
                                            description "Lower bound port to match";
                                        }

                                        ///nokia-li-conf/li/li-filter/li-ip-filter/entry/match/src-port/port/range/range/end
                                        leaf end {
                                            type uint16 {
                                                range "1..65535";
                                            }
                                            mandatory true;
                                            description "Upper bound port to match";
                                        }

                                    } // container range

                                }
                            }
                        } // container src-port

                        ///nokia-li-conf/li/li-filter/li-ip-filter/entry/match/dst-ip
                        container dst-ip {
                            description "Enter the dst-ip context";

                            ///nokia-li-conf/li/li-filter/li-ip-filter/entry/match/dst-ip/address
                            leaf address {
                                type union {
                                    type types-sros:ipv4-prefix-with-host-bits;
                                    type types-sros:ipv4-address;
                                }
                                description "IP address to match";
                            }

                            ///nokia-li-conf/li/li-filter/li-ip-filter/entry/match/dst-ip/mask
                            leaf mask {
                                type types-sros:ipv4-address;
                                description "Mask that is applied as an AND to the IP address";
                            }

                        } // container dst-ip

                        ///nokia-li-conf/li/li-filter/li-ip-filter/entry/match/src-ip
                        container src-ip {
                            description "Enter the src-ip context";

                            ///nokia-li-conf/li/li-filter/li-ip-filter/entry/match/src-ip/address
                            leaf address {
                                type union {
                                    type types-sros:ipv4-prefix-with-host-bits;
                                    type types-sros:ipv4-address;
                                }
                                description "IP address to match";
                            }

                            ///nokia-li-conf/li/li-filter/li-ip-filter/entry/match/src-ip/mask
                            leaf mask {
                                type types-sros:ipv4-address;
                                description "Mask that is applied as an AND to the IP address";
                            }

                        } // container src-ip

                    } // container match

                } // list entry

            } // list li-ip-filter

            ///nokia-li-conf/li/li-filter/li-ipv6-filter
            list li-ipv6-filter {
                key "li-filter-name";
                description "Enter the li-ipv6-filter list instance";

                ///nokia-li-conf/li/li-filter/li-ipv6-filter/li-filter-name
                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                ///nokia-li-conf/li/li-filter/li-ipv6-filter/description
                leaf description {
                    type types-sros:description;
                    description "Text description";
                }

                ///nokia-li-conf/li/li-filter/li-ipv6-filter/entry
                list entry {
                    key "li-entry-id";
                    description "Enter the entry list instance";

                    ///nokia-li-conf/li/li-filter/li-ipv6-filter/entry/li-entry-id
                    leaf li-entry-id {
                        type types-filter:limited-entry-id;
                        description "LI filter entry ID";
                    }

                    ///nokia-li-conf/li/li-filter/li-ipv6-filter/entry/description
                    leaf description {
                        type types-sros:description;
                        description "Text description";
                    }

                    ///nokia-li-conf/li/li-filter/li-ipv6-filter/entry/match
                    container match {
                        description "Enter the match context";

                        ///nokia-li-conf/li/li-filter/li-ipv6-filter/entry/match/next-header
                        leaf next-header {
                            type types-sros:match-ip-protocol;
                            description "IP protocol to match";
                        }

                        ///nokia-li-conf/li/li-filter/li-ipv6-filter/entry/match/dst-port
                        container dst-port {
                            description "Enter the dst-port context";

                            ///nokia-li-conf/li/li-filter/li-ipv6-filter/entry/match/dst-port/port
                            choice port {
                                ///nokia-li-conf/li/li-filter/li-ipv6-filter/entry/match/dst-port/port/eq
                                case eq {

                                    ///nokia-li-conf/li/li-filter/li-ipv6-filter/entry/match/dst-port/port/eq/eq
                                    leaf eq {
                                        type uint16 {
                                            range "0..65535";
                                        }
                                        description "Condition on equality to specified value";
                                    }

                                }
                                ///nokia-li-conf/li/li-filter/li-ipv6-filter/entry/match/dst-port/port/lt
                                case lt {

                                    ///nokia-li-conf/li/li-filter/li-ipv6-filter/entry/match/dst-port/port/lt/lt
                                    leaf lt {
                                        type uint16 {
                                            range "1..65535";
                                        }
                                        description "Condition on being less than the specified value";
                                    }

                                }
                                ///nokia-li-conf/li/li-filter/li-ipv6-filter/entry/match/dst-port/port/gt
                                case gt {

                                    ///nokia-li-conf/li/li-filter/li-ipv6-filter/entry/match/dst-port/port/gt/gt
                                    leaf gt {
                                        type uint16 {
                                            range "0..65534";
                                        }
                                        description "Condition on being greater than the specified value";
                                    }

                                }
                                ///nokia-li-conf/li/li-filter/li-ipv6-filter/entry/match/dst-port/port/range
                                case range {

                                    ///nokia-li-conf/li/li-filter/li-ipv6-filter/entry/match/dst-port/port/range/range
                                    container range {
                                        presence "Enable the range context";
                                        description "Enable the range context";

                                        ///nokia-li-conf/li/li-filter/li-ipv6-filter/entry/match/dst-port/port/range/range/start
                                        leaf start {
                                            type uint16 {
                                                range "0..65534";
                                            }
                                            mandatory true;
                                            description "Lower bound port to match";
                                        }

                                        ///nokia-li-conf/li/li-filter/li-ipv6-filter/entry/match/dst-port/port/range/range/end
                                        leaf end {
                                            type uint16 {
                                                range "1..65535";
                                            }
                                            mandatory true;
                                            description "Upper bound port to match";
                                        }

                                    } // container range

                                }
                            }
                        } // container dst-port

                        ///nokia-li-conf/li/li-filter/li-ipv6-filter/entry/match/src-port
                        container src-port {
                            description "Enter the src-port context";

                            ///nokia-li-conf/li/li-filter/li-ipv6-filter/entry/match/src-port/port
                            choice port {
                                ///nokia-li-conf/li/li-filter/li-ipv6-filter/entry/match/src-port/port/eq
                                case eq {

                                    ///nokia-li-conf/li/li-filter/li-ipv6-filter/entry/match/src-port/port/eq/eq
                                    leaf eq {
                                        type uint16 {
                                            range "0..65535";
                                        }
                                        description "Condition on equality to specified value";
                                    }

                                }
                                ///nokia-li-conf/li/li-filter/li-ipv6-filter/entry/match/src-port/port/lt
                                case lt {

                                    ///nokia-li-conf/li/li-filter/li-ipv6-filter/entry/match/src-port/port/lt/lt
                                    leaf lt {
                                        type uint16 {
                                            range "1..65535";
                                        }
                                        description "Condition on being less than the specified value";
                                    }

                                }
                                ///nokia-li-conf/li/li-filter/li-ipv6-filter/entry/match/src-port/port/gt
                                case gt {

                                    ///nokia-li-conf/li/li-filter/li-ipv6-filter/entry/match/src-port/port/gt/gt
                                    leaf gt {
                                        type uint16 {
                                            range "0..65534";
                                        }
                                        description "Condition on being greater than the specified value";
                                    }

                                }
                                ///nokia-li-conf/li/li-filter/li-ipv6-filter/entry/match/src-port/port/range
                                case range {

                                    ///nokia-li-conf/li/li-filter/li-ipv6-filter/entry/match/src-port/port/range/range
                                    container range {
                                        presence "Enable the range context";
                                        description "Enable the range context";

                                        ///nokia-li-conf/li/li-filter/li-ipv6-filter/entry/match/src-port/port/range/range/start
                                        leaf start {
                                            type uint16 {
                                                range "0..65534";
                                            }
                                            mandatory true;
                                            description "Lower bound port to match";
                                        }

                                        ///nokia-li-conf/li/li-filter/li-ipv6-filter/entry/match/src-port/port/range/range/end
                                        leaf end {
                                            type uint16 {
                                                range "1..65535";
                                            }
                                            mandatory true;
                                            description "Upper bound port to match";
                                        }

                                    } // container range

                                }
                            }
                        } // container src-port

                        ///nokia-li-conf/li/li-filter/li-ipv6-filter/entry/match/dst-ip
                        container dst-ip {
                            description "Enter the dst-ip context";

                            ///nokia-li-conf/li/li-filter/li-ipv6-filter/entry/match/dst-ip/address
                            leaf address {
                                type union {
                                    type types-sros:ipv6-prefix-with-host-bits;
                                    type types-sros:ipv6-address;
                                }
                                description "IP address to match";
                            }

                            ///nokia-li-conf/li/li-filter/li-ipv6-filter/entry/match/dst-ip/mask
                            leaf mask {
                                type types-sros:ipv6-address;
                                description "Mask that is applied as an AND to the IPv6 address";
                            }

                        } // container dst-ip

                        ///nokia-li-conf/li/li-filter/li-ipv6-filter/entry/match/src-ip
                        container src-ip {
                            description "Enter the src-ip context";

                            ///nokia-li-conf/li/li-filter/li-ipv6-filter/entry/match/src-ip/address
                            leaf address {
                                type union {
                                    type types-sros:ipv6-prefix-with-host-bits;
                                    type types-sros:ipv6-address;
                                }
                                description "IP address to match";
                            }

                            ///nokia-li-conf/li/li-filter/li-ipv6-filter/entry/match/src-ip/mask
                            leaf mask {
                                type types-sros:ipv6-address;
                                description "Mask that is applied as an AND to the IPv6 address";
                            }

                        } // container src-ip

                    } // container match

                } // list entry

            } // list li-ipv6-filter

            ///nokia-li-conf/li/li-filter/li-mac-filter
            list li-mac-filter {
                key "li-filter-name";
                description "Enter the li-mac-filter list instance";

                ///nokia-li-conf/li/li-filter/li-mac-filter/li-filter-name
                leaf li-filter-name {
                    type types-sros:named-item {
                        pattern "((([^d_ ]|d($|[^e]|e($|[^f]|f($|[^a]|a($|[^u]|u($|[^l]|l($|[^t]|t\\P{C})))))))\\P{C}*))";
                    }
                    description "LI filter name";
                }

                ///nokia-li-conf/li/li-filter/li-mac-filter/description
                leaf description {
                    type types-sros:description;
                    description "Text description";
                }

                ///nokia-li-conf/li/li-filter/li-mac-filter/entry
                list entry {
                    key "li-entry-id";
                    description "Enter the entry list instance";

                    ///nokia-li-conf/li/li-filter/li-mac-filter/entry/li-entry-id
                    leaf li-entry-id {
                        type types-filter:limited-entry-id;
                        description "LI filter entry ID";
                    }

                    ///nokia-li-conf/li/li-filter/li-mac-filter/entry/description
                    leaf description {
                        type types-sros:description;
                        description "Text description";
                    }

                    ///nokia-li-conf/li/li-filter/li-mac-filter/entry/match
                    container match {
                        description "Enter the match context";

                        ///nokia-li-conf/li/li-filter/li-mac-filter/entry/match/frame-type
                        leaf frame-type {
                            type types-filter:mac-frame-type;
                            default "802dot3";
                            description "Frame type for MAC filter match";
                        }

                        ///nokia-li-conf/li/li-filter/li-mac-filter/entry/match/dst-mac
                        container dst-mac {
                            presence "Enable the dst-mac context";
                            description "Enable the dst-mac context";

                            ///nokia-li-conf/li/li-filter/li-mac-filter/entry/match/dst-mac/address
                            leaf address {
                                type yang:mac-address;
                                mandatory true;
                                description "MAC address for filter match";
                            }

                            ///nokia-li-conf/li/li-filter/li-mac-filter/entry/match/dst-mac/mask
                            leaf mask {
                                type yang:mac-address;
                                default "ff:ff:ff:ff:ff:ff";
                                description "MAC address mask for filter match";
                            }

                        } // container dst-mac

                        ///nokia-li-conf/li/li-filter/li-mac-filter/entry/match/src-mac
                        container src-mac {
                            presence "Enable the src-mac context";
                            description "Enable the src-mac context";

                            ///nokia-li-conf/li/li-filter/li-mac-filter/entry/match/src-mac/address
                            leaf address {
                                type yang:mac-address;
                                mandatory true;
                                description "MAC address for filter match";
                            }

                            ///nokia-li-conf/li/li-filter/li-mac-filter/entry/match/src-mac/mask
                            leaf mask {
                                type yang:mac-address;
                                default "ff:ff:ff:ff:ff:ff";
                                description "MAC address mask for filter match";
                            }

                        } // container src-mac

                    } // container match

                } // list entry

            } // list li-mac-filter

            ///nokia-li-conf/li/li-filter/associations
            container associations {
                description "Enter the associations context";

                ///nokia-li-conf/li/li-filter/associations/li-ip-filter
                list li-ip-filter {
                    key "li-filter-name";
                    description "Enter the li-ip-filter list instance";

                    ///nokia-li-conf/li/li-filter/associations/li-ip-filter/li-filter-name
                    leaf li-filter-name {
                        type leafref {
                            path "../../../li-ip-filter/li-filter-name";
                        }
                        description "Name of an existing LI IP filter";
                    }

                    ///nokia-li-conf/li/li-filter/associations/li-ip-filter/ip-filter
                    list ip-filter {
                        key "filter-name";
                        min-elements 1;
                        max-elements 1;
                        description "Add a list entry for ip-filter";

                        ///nokia-li-conf/li/li-filter/associations/li-ip-filter/ip-filter/filter-name
                        leaf filter-name {
                            type types-filter:filter-name;
                            description "IP filter to be associated with specified LI IP filter";
                        }

                    } // list ip-filter

                } // list li-ip-filter

                ///nokia-li-conf/li/li-filter/associations/li-ipv6-filter
                list li-ipv6-filter {
                    key "li-filter-name";
                    description "Enter the li-ipv6-filter list instance";

                    ///nokia-li-conf/li/li-filter/associations/li-ipv6-filter/li-filter-name
                    leaf li-filter-name {
                        type leafref {
                            path "../../../li-ipv6-filter/li-filter-name";
                        }
                        description "LI IPv6 filter name";
                    }

                    ///nokia-li-conf/li/li-filter/associations/li-ipv6-filter/ipv6-filter
                    list ipv6-filter {
                        key "filter-name";
                        min-elements 1;
                        max-elements 1;
                        description "Add a list entry for ipv6-filter";

                        ///nokia-li-conf/li/li-filter/associations/li-ipv6-filter/ipv6-filter/filter-name
                        leaf filter-name {
                            type types-filter:filter-name;
                            description "IP filter to be associated with specified LI IP filter";
                        }

                    } // list ipv6-filter

                } // list li-ipv6-filter

                ///nokia-li-conf/li/li-filter/associations/li-mac-filter
                list li-mac-filter {
                    key "li-filter-name";
                    description "Enter the li-mac-filter list instance";

                    ///nokia-li-conf/li/li-filter/associations/li-mac-filter/li-filter-name
                    leaf li-filter-name {
                        type leafref {
                            path "../../../li-mac-filter/li-filter-name";
                        }
                        description "LI MAC filter name";
                    }

                    ///nokia-li-conf/li/li-filter/associations/li-mac-filter/mac-filter
                    list mac-filter {
                        key "filter-name";
                        min-elements 1;
                        max-elements 1;
                        description "Add a list entry for mac-filter";

                        ///nokia-li-conf/li/li-filter/associations/li-mac-filter/mac-filter/filter-name
                        leaf filter-name {
                            type types-filter:filter-name;
                            description "IP filter to be associated with specified LI IP filter";
                        }

                    } // list mac-filter

                } // list li-mac-filter

            } // container associations

            ///nokia-li-conf/li/li-filter/reserved-block
            list reserved-block {
                key "block-name";
                max-elements 8;
                description "Enter the reserved-block list instance";

                ///nokia-li-conf/li/li-filter/reserved-block/block-name
                leaf block-name {
                    type types-sros:named-item {
                        pattern "((([^d_ ]|d($|[^e]|e($|[^f]|f($|[^a]|a($|[^u]|u($|[^l]|l($|[^t]|t\\P{C})))))))\\P{C}*))";
                    }
                    description "Object uniquely identifying an LI reserved block";
                }

                ///nokia-li-conf/li/li-filter/reserved-block/description
                leaf description {
                    type types-sros:description;
                    description "Text description";
                }

                ///nokia-li-conf/li/li-filter/reserved-block/ip-filter
                list ip-filter {
                    key "filter-name";
                    description "Add a list entry for ip-filter";

                    ///nokia-li-conf/li/li-filter/reserved-block/ip-filter/filter-name
                    leaf filter-name {
                        type types-filter:filter-name;
                        description "IP filter ID for LI filter reserved block";
                    }

                } // list ip-filter

                ///nokia-li-conf/li/li-filter/reserved-block/ipv6-filter
                list ipv6-filter {
                    key "filter-name";
                    description "Add a list entry for ipv6-filter";

                    ///nokia-li-conf/li/li-filter/reserved-block/ipv6-filter/filter-name
                    leaf filter-name {
                        type types-filter:filter-name;
                        description "IP filter ID for LI filter reserved block";
                    }

                } // list ipv6-filter

                ///nokia-li-conf/li/li-filter/reserved-block/mac-filter
                list mac-filter {
                    key "filter-name";
                    description "Add a list entry for mac-filter";

                    ///nokia-li-conf/li/li-filter/reserved-block/mac-filter/filter-name
                    leaf filter-name {
                        type types-filter:filter-name;
                        description "IP filter ID for LI filter reserved block";
                    }

                } // list mac-filter

                ///nokia-li-conf/li/li-filter/reserved-block/entry-range
                container entry-range {
                    presence "Enable the entry-range context";
                    description "Enable the entry-range context";

                    ///nokia-li-conf/li/li-filter/reserved-block/entry-range/start
                    leaf start {
                        type types-filter:entry-id;
                        mandatory true;
                        description "Lower bound of the range";
                    }

                    ///nokia-li-conf/li/li-filter/reserved-block/entry-range/end
                    leaf end {
                        type types-filter:entry-id;
                        mandatory true;
                        description "Upper bound of the range";
                    }

                } // container entry-range

            } // list reserved-block

        } // container li-filter

        ///nokia-li-conf/li/li-source
        list li-source {
            key "service-name";
            description "Enter the li-source list instance";

            ///nokia-li-conf/li/li-source/service-name
            leaf service-name {
                type types-services:service-name;
                description "Administrative service name";
            }

            ///nokia-li-conf/li/li-source/admin-state
            leaf admin-state {
                type types-sros:admin-state;
                default "enable";
                description "Administrative state of mirror service";
            }

            ///nokia-li-conf/li/li-source/port
            list port {
                key "port-id";
                description "Enter the port list instance";

                ///nokia-li-conf/li/li-source/port/port-id
                leaf port-id {
                    type types-services:mirror-source-port-lag-key;
                    description "Port ID";
                }

                ///nokia-li-conf/li/li-source/port/ingress
                leaf ingress {
                    type boolean;
                    default "false";
                    description "Perform lawful intercept on ingress traffic";
                }

                ///nokia-li-conf/li/li-source/port/egress
                leaf egress {
                    type boolean;
                    default "false";
                    description "Perform lawful intercept on egress traffic";
                }

            } // list port

            ///nokia-li-conf/li/li-source/sap
            list sap {
                key "sap-id";
                description "Enter the sap list instance";

                ///nokia-li-conf/li/li-source/sap/intercept-id
                leaf intercept-id {
                    type types-services:li-interception-identifier;
                    description "Intercept ID of the traffic flow";
                }

                ///nokia-li-conf/li/li-source/sap/session-id
                leaf session-id {
                    type types-services:li-session-identifier;
                    description "Session ID of the traffic flow";
                }

                ///nokia-li-conf/li/li-source/sap/sap-id
                leaf sap-id {
                    type types-sros:sap;
                    description "SAP ID";
                }

                ///nokia-li-conf/li/li-source/sap/ingress
                leaf ingress {
                    type boolean;
                    default "false";
                    description "Perform lawful intercept on ingress traffic";
                }

                ///nokia-li-conf/li/li-source/sap/egress
                leaf egress {
                    type boolean;
                    default "false";
                    description "Perform lawful intercept on egress traffic";
                }

            } // list sap

            ///nokia-li-conf/li/li-source/li-ip-filter
            list li-ip-filter {
                key "li-filter-name";
                description "Enter the li-ip-filter list instance";

                ///nokia-li-conf/li/li-source/li-ip-filter/li-filter-name
                leaf li-filter-name {
                    type leafref {
                        path "../../../li-filter/li-ip-filter/li-filter-name";
                    }
                    description "A unique ID for an li-ip-filter";
                }

                ///nokia-li-conf/li/li-source/li-ip-filter/entry
                list entry {
                    key "li-entry-id";
                    min-elements 1;
                    description "Enter the entry list instance";

                    ///nokia-li-conf/li/li-source/li-ip-filter/entry/li-entry-id
                    leaf li-entry-id {
                        type leafref {
                            path "../../../../li-filter/li-ip-filter[li-filter-name=current()/../../li-filter-name]/entry/li-entry-id";
                        }
                        description "A unique ID for an li-ip-filter entry";
                    }

                    ///nokia-li-conf/li/li-source/li-ip-filter/entry/intercept-id
                    leaf intercept-id {
                        type types-services:li-interception-identifier;
                        description "Intercept ID of the traffic flow";
                    }

                    ///nokia-li-conf/li/li-source/li-ip-filter/entry/session-id
                    leaf session-id {
                        type types-services:li-session-identifier;
                        description "Session ID of the traffic flow";
                    }

                } // list entry

            } // list li-ip-filter

            ///nokia-li-conf/li/li-source/li-ipv6-filter
            list li-ipv6-filter {
                key "li-filter-name";
                description "Enter the li-ipv6-filter list instance";

                ///nokia-li-conf/li/li-source/li-ipv6-filter/li-filter-name
                leaf li-filter-name {
                    type leafref {
                        path "../../../li-filter/li-ipv6-filter/li-filter-name";
                    }
                    description "A unique ID for an li-ipv6-filter";
                }

                ///nokia-li-conf/li/li-source/li-ipv6-filter/entry
                list entry {
                    key "li-entry-id";
                    min-elements 1;
                    description "Enter the entry list instance";

                    ///nokia-li-conf/li/li-source/li-ipv6-filter/entry/li-entry-id
                    leaf li-entry-id {
                        type leafref {
                            path "../../../../li-filter/li-ipv6-filter[li-filter-name=current()/../../li-filter-name]/entry/li-entry-id";
                        }
                        description "A unique ID for an li-ipv6-filter entry";
                    }

                    ///nokia-li-conf/li/li-source/li-ipv6-filter/entry/intercept-id
                    leaf intercept-id {
                        type types-services:li-interception-identifier;
                        description "Intercept ID of the traffic flow";
                    }

                    ///nokia-li-conf/li/li-source/li-ipv6-filter/entry/session-id
                    leaf session-id {
                        type types-services:li-session-identifier;
                        description "Session ID of the traffic flow";
                    }

                } // list entry

            } // list li-ipv6-filter

            ///nokia-li-conf/li/li-source/li-mac-filter
            list li-mac-filter {
                key "li-filter-name";
                description "Enter the li-mac-filter list instance";

                ///nokia-li-conf/li/li-source/li-mac-filter/li-filter-name
                leaf li-filter-name {
                    type leafref {
                        path "../../../li-filter/li-mac-filter/li-filter-name";
                    }
                    description "A unique ID for an li-mac-filter";
                }

                ///nokia-li-conf/li/li-source/li-mac-filter/entry
                list entry {
                    key "li-entry-id";
                    min-elements 1;
                    description "Enter the entry list instance";

                    ///nokia-li-conf/li/li-source/li-mac-filter/entry/li-entry-id
                    leaf li-entry-id {
                        type leafref {
                            path "../../../../li-filter/li-mac-filter[li-filter-name=current()/../../li-filter-name]/entry/li-entry-id";
                        }
                        description "A unique ID for an li-mac-filter entry";
                    }

                    ///nokia-li-conf/li/li-source/li-mac-filter/entry/intercept-id
                    leaf intercept-id {
                        type types-services:li-interception-identifier;
                        description "Intercept ID of the traffic flow";
                    }

                    ///nokia-li-conf/li/li-source/li-mac-filter/entry/session-id
                    leaf session-id {
                        type types-services:li-session-identifier;
                        description "Session ID of the traffic flow";
                    }

                } // list entry

            } // list li-mac-filter

            ///nokia-li-conf/li/li-source/nat
            container nat {
                description "Enter the nat context";

                ///nokia-li-conf/li/li-source/nat/ethernet-header
                container ethernet-header {
                    description "Enter the ethernet-header context";

                    ///nokia-li-conf/li/li-source/nat/ethernet-header/source-address
                    leaf source-address {
                        type types-sros:mac-address;
                        description "Source MAC address field of the Ethernet encapsulation";
                    }

                    ///nokia-li-conf/li/li-source/nat/ethernet-header/destination-address
                    leaf destination-address {
                        type types-sros:mac-address;
                        description "Destination MAC address field of Ethernet encapsulation";
                    }

                    ///nokia-li-conf/li/li-source/nat/ethernet-header/type
                    leaf type {
                        type uint16 {
                            range "1536..65535";
                        }
                        default "1792";
                        description "Ethertype of the ethernet encapsulation";
                    }

                } // container ethernet-header

                ///nokia-li-conf/li/li-source/nat/nat44
                list nat44 {
                    key "router-instance ip";
                    description "Enter the nat44 list instance";

                    ///nokia-li-conf/li/li-source/nat/nat44/router-instance
                    leaf router-instance {
                        type types-services:service-name;
                        description "Name of the service";
                    }

                    ///nokia-li-conf/li/li-source/nat/nat44/ip
                    leaf ip {
                        type types-sros:ipv4-address;
                        description "IP address of the subscriber";
                    }

                    ///nokia-li-conf/li/li-source/nat/nat44/intercept-id
                    leaf intercept-id {
                        type types-services:li-interception-identifier-wide;
                        description "The intercept id of the traffic flow";
                    }

                    ///nokia-li-conf/li/li-source/nat/nat44/session-id
                    leaf session-id {
                        type types-services:li-session-identifier;
                        description "The session id of the traffic flow";
                    }

                } // list nat44

                ///nokia-li-conf/li/li-source/nat/dslite
                list dslite {
                    key "router-instance b4";
                    description "Enter the dslite list instance";

                    ///nokia-li-conf/li/li-source/nat/dslite/router-instance
                    leaf router-instance {
                        type types-services:service-name;
                        description "Name of the service";
                    }

                    ///nokia-li-conf/li/li-source/nat/dslite/b4
                    leaf b4 {
                        type types-sros:ipv6-prefix;
                        description "B4 prefix of the subscriber";
                    }

                    ///nokia-li-conf/li/li-source/nat/dslite/intercept-id
                    leaf intercept-id {
                        type types-services:li-interception-identifier-wide;
                        description "The intercept id of the traffic flow";
                    }

                    ///nokia-li-conf/li/li-source/nat/dslite/session-id
                    leaf session-id {
                        type types-services:li-session-identifier;
                        description "The session id of the traffic flow";
                    }

                } // list dslite

                ///nokia-li-conf/li/li-source/nat/nat64
                list nat64 {
                    key "router-instance ip";
                    description "Enter the nat64 list instance";

                    ///nokia-li-conf/li/li-source/nat/nat64/router-instance
                    leaf router-instance {
                        type types-services:service-name;
                        description "Name of the service";
                    }

                    ///nokia-li-conf/li/li-source/nat/nat64/ip
                    leaf ip {
                        type types-sros:ipv6-prefix;
                        description "IP prefix of the subscriber";
                    }

                    ///nokia-li-conf/li/li-source/nat/nat64/intercept-id
                    leaf intercept-id {
                        type types-services:li-interception-identifier-wide;
                        description "The intercept id of the traffic flow";
                    }

                    ///nokia-li-conf/li/li-source/nat/nat64/session-id
                    leaf session-id {
                        type types-services:li-session-identifier;
                        description "The session id of the traffic flow";
                    }

                } // list nat64

                ///nokia-li-conf/li/li-source/nat/l2-aware
                list l2-aware {
                    key "subscriber-id";
                    description "Enter the l2-aware list instance";

                    ///nokia-li-conf/li/li-source/nat/l2-aware/subscriber-id
                    leaf subscriber-id {
                        type types-submgt:subscriber-id;
                        description "The string identifying the subscribe";
                    }

                    ///nokia-li-conf/li/li-source/nat/l2-aware/intercept-id
                    leaf intercept-id {
                        type types-services:li-interception-identifier-wide;
                        description "The intercept id of the traffic flow";
                    }

                    ///nokia-li-conf/li/li-source/nat/l2-aware/session-id
                    leaf session-id {
                        type types-services:li-session-identifier;
                        description "The session id of the traffic flow";
                    }

                } // list l2-aware

            } // container nat

            ///nokia-li-conf/li/li-source/wlan-gw-dsm-ue
            list wlan-gw-dsm-ue {
                key "mac";
                description "Enter the wlan-gw-dsm-ue list instance";

                ///nokia-li-conf/li/li-source/wlan-gw-dsm-ue/mac
                leaf mac {
                    type yang:mac-address;
                    description "MAC address of the DSM UE";
                }

                ///nokia-li-conf/li/li-source/wlan-gw-dsm-ue/intercept-id
                leaf intercept-id {
                    type types-services:li-interception-identifier-wide;
                    description "Intercept identifier";
                }

                ///nokia-li-conf/li/li-source/wlan-gw-dsm-ue/session-id
                leaf session-id {
                    type types-services:li-session-identifier;
                    description "Session identifier";
                }

            } // list wlan-gw-dsm-ue

            ///nokia-li-conf/li/li-source/subscriber
            list subscriber {
                key "subscriber-id";
                description "Enter the subscriber list instance";

                ///nokia-li-conf/li/li-source/subscriber/subscriber-id
                leaf subscriber-id {
                    type types-submgt:subscriber-id;
                    description "Subscriber ID";
                }

                ///nokia-li-conf/li/li-source/subscriber/ingress
                leaf ingress {
                    type boolean;
                    default "false";
                    description "Perform lawful intercept on ingress traffic";
                }

                ///nokia-li-conf/li/li-source/subscriber/egress
                leaf egress {
                    type boolean;
                    default "false";
                    description "Perform lawful intercept on egress traffic";
                }

                ///nokia-li-conf/li/li-source/subscriber/fc
                leaf-list fc {
                    type enumeration {
                        enum be                             { value 0; }
                        enum l2                             { value 1; }
                        enum af                             { value 2; }
                        enum l1                             { value 3; }
                        enum h2                             { value 4; }
                        enum ef                             { value 5; }
                        enum h1                             { value 6; }
                        enum nc                             { value 7; }
                    }
                    max-elements 8;
                    description "Forwarding classes to be mirrored";
                }

                ///nokia-li-conf/li/li-source/subscriber/host-type
                leaf host-type {
                    type enumeration {
                        enum ipoe                           { value 2; }
                        enum ppp                            { value 3; }
                    }
                    description "Subscriber host type to be monitored";
                }

                ///nokia-li-conf/li/li-source/subscriber/ip-family
                leaf ip-family {
                    type enumeration {
                        enum ipv4                           { value 2; }
                        enum ipv6                           { value 3; }
                    }
                    description "IP family for LI";
                }

                ///nokia-li-conf/li/li-source/subscriber/intercept-id
                leaf intercept-id {
                    type types-services:li-interception-identifier;
                    description "Intercept ID of the traffic flow";
                }

                ///nokia-li-conf/li/li-source/subscriber/session-id
                leaf session-id {
                    type types-services:li-session-identifier;
                    description "Session ID of the traffic flow";
                }

                ///nokia-li-conf/li/li-source/subscriber/host-identification
                choice host-identification {
                    ///nokia-li-conf/li/li-source/subscriber/host-identification/sap-id
                    case sap-id {

                        ///nokia-li-conf/li/li-source/subscriber/host-identification/sap-id/sap-id
                        leaf sap-id {
                            type types-sros:sap;
                            description "SAP ID";
                        }

                        ///nokia-li-conf/li/li-source/subscriber/host-identification/sap-id/mac-address
                        leaf mac-address {
                            type yang:mac-address;
                            description "The source MAC address";
                        }

                        ///nokia-li-conf/li/li-source/subscriber/host-identification/sap-id/ip-address
                        leaf ip-address {
                            type types-sros:ipv4-address;
                            description "IP address of the subscriber";
                        }

                    }
                    ///nokia-li-conf/li/li-source/subscriber/host-identification/sla-profile
                    case sla-profile {

                        ///nokia-li-conf/li/li-source/subscriber/host-identification/sla-profile/sla-profile
                        leaf sla-profile {
                            type types-sros:external-named-item;
                            description "SLA profile";
                        }

                    }
                }
            } // list subscriber

        } // list li-source

        ///nokia-li-conf/li/log
        container log {
            description "Enable the log context";

            ///nokia-li-conf/li/log/log-id
            list log-id {
                key "name";
                max-elements 30;
                description "Enter the log-id list instance";

                ///nokia-li-conf/li/log/log-id/name
                leaf name {
                    type types-log:li-log-name;
                    description "Log ID";
                }

                ///nokia-li-conf/li/log/log-id/admin-state
                leaf admin-state {
                    type types-sros:admin-state;
                    default "enable";
                    description "The administrative state of the log";
                }

                ///nokia-li-conf/li/log/log-id/description
                leaf description {
                    type types-sros:description;
                    description "Text description";
                }

                ///nokia-li-conf/li/log/log-id/netconf-stream
                leaf netconf-stream {
                    type types-sros:named-item;
                    description "Destination NETCONF stream name";
                }

                ///nokia-li-conf/li/log/log-id/time-format
                leaf time-format {
                    type enumeration {
                        enum utc                            { value 1; }
                        enum local                          { value 2; }
                    }
                    default "utc";
                    description "Time zone to display date and time";
                }

                ///nokia-li-conf/li/log/log-id/filter
                leaf filter {
                    type types-log:log-filter-name;
                    description "Event filter ID to associate with log ID configuration";
                }

                ///nokia-li-conf/li/log/log-id/source
                container source {
                    description "Enter the source context";

                    ///nokia-li-conf/li/log/log-id/source/li
                    leaf li {
                        type boolean;
                        default "false";
                        description "Event stream for events configured for LI activities";
                    }

                } // container source

                ///nokia-li-conf/li/log/log-id/destination
                container destination {
                    description "Enter the destination context";

                    ///nokia-li-conf/li/log/log-id/destination/log-id-destination
                    choice log-id-destination {
                        ///nokia-li-conf/li/log/log-id/destination/log-id-destination/memory
                        case memory {

                            ///nokia-li-conf/li/log/log-id/destination/log-id-destination/memory/memory
                            container memory {
                                presence "Enable the memory context";
                                description "Enable the memory context";

                                ///nokia-li-conf/li/log/log-id/destination/log-id-destination/memory/memory/max-entries
                                leaf max-entries {
                                    type uint32 {
                                        range "50..1024";
                                    }
                                    sros-ext:immutable;
                                    default "100";
                                    description "Number of events stored in this memory log";
                                }

                            } // container memory

                        }
                        ///nokia-li-conf/li/log/log-id/destination/log-id-destination/snmp
                        case snmp {

                            ///nokia-li-conf/li/log/log-id/destination/log-id-destination/snmp/snmp
                            container snmp {
                                presence "Enable the snmp context";
                                description "Enable the snmp context";

                                ///nokia-li-conf/li/log/log-id/destination/log-id-destination/snmp/snmp/max-entries
                                leaf max-entries {
                                    type uint32 {
                                        range "50..1024";
                                    }
                                    sros-ext:immutable;
                                    default "100";
                                    description "Number of events stored in this snmp log";
                                }

                            } // container snmp

                        }
                        ///nokia-li-conf/li/log/log-id/destination/log-id-destination/netconf
                        case netconf {

                            ///nokia-li-conf/li/log/log-id/destination/log-id-destination/netconf/netconf
                            container netconf {
                                presence "Enable the netconf context";
                                description "Enable the netconf context";

                                ///nokia-li-conf/li/log/log-id/destination/log-id-destination/netconf/netconf/max-entries
                                leaf max-entries {
                                    type uint32 {
                                        range "50..1024";
                                    }
                                    sros-ext:immutable;
                                    default "100";
                                    description "Maximum number of events stored in the NETCONF log";
                                }

                            } // container netconf

                        }
                    }
                } // container destination

            } // list log-id

        } // container log

        ///nokia-li-conf/li/mirror-dest-reservation
        container mirror-dest-reservation {
            description "Enter the mirror-dest-reservation context";

            ///nokia-li-conf/li/mirror-dest-reservation/start
            leaf start {
                type uint32 {
                    range "1..2147483647";
                }
                description "Lower bound of the mirror destination ID";
            }

            ///nokia-li-conf/li/mirror-dest-reservation/end
            leaf end {
                type uint32 {
                    range "1..2147483647";
                }
                description "Upper bound of the mirror destination ID";
            }

        } // container mirror-dest-reservation

        ///nokia-li-conf/li/mirror-dest-template
        list mirror-dest-template {
            key "name";
            max-elements 8;
            description "Enter the mirror-dest-template list instance";

            ///nokia-li-conf/li/mirror-dest-template/name
            leaf name {
                type types-sros:named-item;
                description "Mirror destination template name";
            }

            ///nokia-li-conf/li/mirror-dest-template/type
            leaf type {
                type types-services:mirror-type;
                sros-ext:immutable;
                default "ether";
                description "Encapsulation type supported by the mirror service";
            }

            ///nokia-li-conf/li/mirror-dest-template/layer-3-encap
            container layer-3-encap {
                description "Enter the layer-3-encap context";

                ///nokia-li-conf/li/mirror-dest-template/layer-3-encap/router-instance
                leaf router-instance {
                    type types-sros:router-instance;
                    default "Base";
                    description "Virtual router instance to inject mirrored packets";
                }

                ///nokia-li-conf/li/mirror-dest-template/layer-3-encap/encap-type
                leaf encap-type {
                    type enumeration {
                        enum ip-udp-shim                    { value 1; }
                        enum ip-gre                         { value 2; }
                    }
                    sros-ext:immutable;
                    default "ip-udp-shim";
                    description "The header type of the layer 3 encapsulation.";
                }

                ///nokia-li-conf/li/mirror-dest-template/layer-3-encap/direction-bit
                leaf direction-bit {
                    type boolean;
                    default "false";
                    description "Use highest bit in interception ID for flow direction";
                }

                ///nokia-li-conf/li/mirror-dest-template/layer-3-encap/ip-source
                leaf ip-source {
                    type types-sros:ipv4-unicast-address;
                    description "Source IPv4 address for Layer 3 encapsulation";
                }

                ///nokia-li-conf/li/mirror-dest-template/layer-3-encap/udp
                container udp {
                    description "Enter the udp context";

                    ///nokia-li-conf/li/mirror-dest-template/layer-3-encap/udp/source
                    leaf source {
                        when "../../encap-type = 'ip-udp-shim'" {
                            description "header type must be ip-udp-shim";
                        }
                        type types-sros:tcp-udp-port-non-zero;
                        description "Source UDP port";
                    }

                    ///nokia-li-conf/li/mirror-dest-template/layer-3-encap/udp/destination
                    leaf destination {
                        when "../../encap-type = 'ip-udp-shim'" {
                            description "header type must be ip-udp-shim";
                        }
                        type types-sros:tcp-udp-port-non-zero;
                        description "Destination UDP port";
                    }

                } // container udp

            } // container layer-3-encap

        } // list mirror-dest-template

        ///nokia-li-conf/li/nat
        container nat {
            description "Enter the nat context";

            ///nokia-li-conf/li/nat/use-outside-ip-address
            leaf use-outside-ip-address {
                type boolean;
                default "false";
                description "Report outside IP address for L2-Aware NAT subscribers";
            }

        } // container nat

        ///nokia-li-conf/li/radius
        container radius {
            description "Enter the radius context";

            ///nokia-li-conf/li/radius/mirror-dest-template
            leaf mirror-dest-template {
                type leafref {
                    path "../../mirror-dest-template/name";
                }
                description "RADIUS triggered mirror destination template";
            }

        } // container radius



        ///nokia-li-conf/li/x-interfaces
        container x-interfaces {
            description "Enter the x-interfaces context";

            ///nokia-li-conf/li/x-interfaces/admin-state
            leaf admin-state {
                type types-sros:admin-state;
                default "disable";
                description "Administrative state of the x-interfaces";
            }

            ///nokia-li-conf/li/x-interfaces/ine-identifier
            leaf ine-identifier {
                type types-sros:named-item;
                description "Intercepting Network Element (INE) ID";
            }

            ///nokia-li-conf/li/x-interfaces/user-db
            leaf user-db {
                type types-sros:named-item;
                description "Location of the data-trigger host for the LIC";
            }

            ///nokia-li-conf/li/x-interfaces/correlation-id
            container correlation-id {
                description "Enter the correlation-id context";

                ///nokia-li-conf/li/x-interfaces/correlation-id/ipoe
                leaf ipoe {
                    type enumeration {
                        enum radius-host-acct-id            { value 1; }
                        enum radius-queue-acct-id           { value 2; }
                        enum radius-session-acct-id         { value 3; }
                    }
                    default "radius-host-acct-id";
                    description "RADIUS accounting ID type for subscriber correlation";
                }

                ///nokia-li-conf/li/x-interfaces/correlation-id/pppoe
                leaf pppoe {
                    type enumeration {
                        enum radius-host-acct-id            { value 1; }
                        enum radius-queue-acct-id           { value 2; }
                        enum radius-session-acct-id         { value 3; }
                    }
                    default "radius-host-acct-id";
                    description "RADIUS accounting ID type for subscriber correlation";
                }

            } // container correlation-id

            ///nokia-li-conf/li/x-interfaces/lic
            list lic {
                key "name";
                max-elements 18;
                description "Enter the lic list instance";

                ///nokia-li-conf/li/x-interfaces/lic/name
                leaf name {
                    type types-sros:named-item;
                    description "LIC name";
                }

                ///nokia-li-conf/li/x-interfaces/lic/description
                leaf description {
                    type types-sros:description;
                    description "Text description";
                }

                ///nokia-li-conf/li/x-interfaces/lic/identifier
                leaf identifier {
                    type types-sros:named-item;
                    description "LIC ID";
                }

                ///nokia-li-conf/li/x-interfaces/lic/port
                leaf port {
                    type inet:port-number;
                    description "TCP port associated with the LIC";
                }

                ///nokia-li-conf/li/x-interfaces/lic/router-instance
                leaf router-instance {
                    type types-sros:named-item-64-or-empty;
                    default "";
                    description "Virtual router instance used by the X-interfaces";
                }

                ///nokia-li-conf/li/x-interfaces/lic/ipv4
                container ipv4 {
                    description "Enter the ipv4 context";

                    ///nokia-li-conf/li/x-interfaces/lic/ipv4/ip-address
                    leaf ip-address {
                        type types-sros:ip-address;
                        description "IP address of the LIC";
                    }

                } // container ipv4

                ///nokia-li-conf/li/x-interfaces/lic/authentication
                container authentication {
                    description "Enter the authentication context";

                    ///nokia-li-conf/li/x-interfaces/lic/authentication/password
                    leaf password {
                        type types-sros:li-static-encrypted-leaf-hex {
                            length "1..50";
                        }
                        description "Password for the X1 and X2 interfaces";
                    }

                    ///nokia-li-conf/li/x-interfaces/lic/authentication/private-ki
                    leaf private-ki {
                        type types-sros:li-static-encrypted-leaf {
                            length "1..50";
                        }
                        description "Private Ki string for the X1 and X2 interfaces";
                    }

                    ///nokia-li-conf/li/x-interfaces/lic/authentication/sequence-group
                    leaf sequence-group {
                        type types-sros:li-static-encrypted-leaf {
                            length "1..42";
                        }
                        description "Sequence group for the X1 and X2 interfaces";
                    }

                } // container authentication

            } // list lic

            ///nokia-li-conf/li/x-interfaces/x1
            container x1 {
                description "Enter the x1 context";

                ///nokia-li-conf/li/x-interfaces/x1/lic-peer
                leaf lic-peer {
                    type leafref {
                        path "../../lic/name";
                    }
                    description "Peer LIC for the X1 interface";
                }

                ///nokia-li-conf/li/x-interfaces/x1/local-tcp-port
                leaf local-tcp-port {
                    type types-sros:tcp-udp-port-non-zero {
                        range "1..65535";
                    }
                    description "Local TCP port used for the X1 interface";
                }

                ///nokia-li-conf/li/x-interfaces/x1/ipv4
                container ipv4 {
                    description "Enter the ipv4 context";

                    ///nokia-li-conf/li/x-interfaces/x1/ipv4/local-address
                    leaf local-address {
                        type types-sros:ip-address;
                        description "X1 interface IP address";
                    }

                } // container ipv4

                ///nokia-li-conf/li/x-interfaces/x1/timeouts
                container timeouts {
                    description "Enter the timeouts context";

                    ///nokia-li-conf/li/x-interfaces/x1/timeouts/message-timeout
                    leaf message-timeout {
                        type uint32 {
                            range "180..300";
                        }
                        units "seconds";
                        default "180";
                        description "Maximum time for the LIC to reply to an X1 message";
                    }

                } // container timeouts

            } // container x1

            ///nokia-li-conf/li/x-interfaces/x2
            container x2 {
                description "Enter the x2 context";

                ///nokia-li-conf/li/x-interfaces/x2/lic-peer
                leaf lic-peer {
                    type leafref {
                        path "../../lic/name";
                    }
                    description "Peer LIC for the X2 interface";
                }

                ///nokia-li-conf/li/x-interfaces/x2/ipv4
                container ipv4 {
                    description "Enter the ipv4 context";

                    ///nokia-li-conf/li/x-interfaces/x2/ipv4/local-address
                    leaf local-address {
                        type types-sros:ip-address;
                        description "X2 interface IP address";
                    }

                } // container ipv4

                ///nokia-li-conf/li/x-interfaces/x2/timeouts
                container timeouts {
                    description "Enter the timeouts context";

                    ///nokia-li-conf/li/x-interfaces/x2/timeouts/keep-alive
                    leaf keep-alive {
                        type uint32 {
                            range "300..600";
                        }
                        units "seconds";
                        default "300";
                        description "Keep-alive timeout";
                    }

                    ///nokia-li-conf/li/x-interfaces/x2/timeouts/request
                    leaf request {
                        type uint32 {
                            range "5..30";
                        }
                        units "seconds";
                        default "5";
                        description "Tx2-normal timeout";
                    }

                } // container timeouts

            } // container x2

            ///nokia-li-conf/li/x-interfaces/x3
            container x3 {
                description "Enter the x3 context";

                ///nokia-li-conf/li/x-interfaces/x3/li-group
                leaf li-group {
                    type uint32 {
                        range "1..4";
                    }
                    description "ISA group of the X3 interface";
                }

                ///nokia-li-conf/li/x-interfaces/x3/session-limit
                leaf session-limit {
                    type uint32 {
                        range "1..32";
                    }
                    default "32";
                    description "Maximum number of X3 sessions initiated to the LIC";
                }

                ///nokia-li-conf/li/x-interfaces/x3/ipv4
                container ipv4 {
                    description "Enter the ipv4 context";

                    ///nokia-li-conf/li/x-interfaces/x3/ipv4/local-address-range
                    container local-address-range {
                        description "Enter the local-address-range context";

                        ///nokia-li-conf/li/x-interfaces/x3/ipv4/local-address-range/start
                        leaf start {
                            type types-sros:ipv4-unicast-address;
                            description "Lower bound of the range";
                        }

                        ///nokia-li-conf/li/x-interfaces/x3/ipv4/local-address-range/end
                        leaf end {
                            type types-sros:ipv4-unicast-address;
                            description "Upper bound of the range";
                        }

                    } // container local-address-range

                } // container ipv4

                ///nokia-li-conf/li/x-interfaces/x3/alarms
                container alarms {
                    description "Enter the alarms context";

                    ///nokia-li-conf/li/x-interfaces/x3/alarms/cpu-alarm
                    container cpu-alarm {
                        description "Enter the cpu-alarm context";

                        ///nokia-li-conf/li/x-interfaces/x3/alarms/cpu-alarm/low-threshold
                        leaf low-threshold {
                            type uint32 {
                                range "0..99";
                            }
                            units "percent";
                            default "0";
                            description "Low threshold value of the CPU usage alarm";
                        }

                        ///nokia-li-conf/li/x-interfaces/x3/alarms/cpu-alarm/high-threshold
                        leaf high-threshold {
                            type uint32 {
                                range "1..100";
                            }
                            units "percent";
                            description "High threshold value of the CPU usage alarm";
                        }

                    } // container cpu-alarm

                    ///nokia-li-conf/li/x-interfaces/x3/alarms/memory-alarm
                    container memory-alarm {
                        description "Enter the memory-alarm context";

                        ///nokia-li-conf/li/x-interfaces/x3/alarms/memory-alarm/low-threshold
                        leaf low-threshold {
                            type uint32 {
                                range "0..99";
                            }
                            units "percent";
                            default "0";
                            description "Low threshold of the packet buffer memory usage alarm";
                        }

                        ///nokia-li-conf/li/x-interfaces/x3/alarms/memory-alarm/high-threshold
                        leaf high-threshold {
                            type uint32 {
                                range "1..100";
                            }
                            units "percent";
                            description "High threshold of the packet buffer memory usage alarm";
                        }

                    } // container memory-alarm

                    ///nokia-li-conf/li/x-interfaces/x3/alarms/throughput-alarm
                    container throughput-alarm {
                        description "Enter the throughput-alarm context";

                        ///nokia-li-conf/li/x-interfaces/x3/alarms/throughput-alarm/low-threshold
                        leaf low-threshold {
                            type uint32 {
                                range "1..4294967295";
                            }
                            units "megabps";
                            description "Low threshold value of the throughput alarm";
                        }

                        ///nokia-li-conf/li/x-interfaces/x3/alarms/throughput-alarm/high-threshold
                        leaf high-threshold {
                            type uint32 {
                                range "1..4294967295";
                            }
                            units "megabps";
                            description "High threshold value of the throughput alarm";
                        }

                    } // container throughput-alarm

                } // container alarms

                ///nokia-li-conf/li/x-interfaces/x3/lic-peers
                list lic-peers {
                    key "name";
                    max-elements 16;
                    description "Add a list entry for lic-peers";

                    ///nokia-li-conf/li/x-interfaces/x3/lic-peers/name
                    leaf name {
                        type leafref {
                            path "../../../lic/name";
                        }
                        description "Peer LIC for the X3 interface";
                    }

                } // list lic-peers

                ///nokia-li-conf/li/x-interfaces/x3/timeouts
                container timeouts {
                    description "Enter the timeouts context";

                    ///nokia-li-conf/li/x-interfaces/x3/timeouts/keep-alive
                    leaf keep-alive {
                        type uint32 {
                            range "300..600";
                        }
                        units "seconds";
                        default "300";
                        description "Keep-alive timeout";
                    }

                    ///nokia-li-conf/li/x-interfaces/x3/timeouts/request
                    leaf request {
                        type uint32 {
                            range "5..30";
                        }
                        units "seconds";
                        default "5";
                        description "Tx3-normal timeout";
                    }

                    ///nokia-li-conf/li/x-interfaces/x3/timeouts/target-retry-wait
                    leaf target-retry-wait {
                        type uint32 {
                            range "300..1200";
                        }
                        units "seconds";
                        default "300";
                        description "Retry interval for target tunnel setup";
                    }

                } // container timeouts

            } // container x3

        } // container x-interfaces

    } // container li

}
