module nokia-sr-openconfig-vlan-deviations {

    namespace "urn:nokia.com:sros:ns:yang:sr:openconfig-vlan-deviations";

    prefix "nokia-oc-vlan-devs";

    import nokia-sros-yang-extensions     { prefix "sros-ext"; }
    import openconfig-extensions          { prefix "oc-ext"; }
    import openconfig-if-aggregate        { prefix "oc-lag"; }
    import openconfig-if-ethernet         { prefix "oc-eth"; }
    import openconfig-interfaces          { prefix "oc-if"; }
    import openconfig-vlan                { prefix "oc-vlan"; }
    import openconfig-vlan-types          { prefix "oc-vlan-types"; }

    sros-ext:sros-major-release "rel23";
    organization "Nokia";
    contact
        "Nokia SR OS Support
         Web: <http://www.nokia.com>";
    description
        "This module contains the list of deviations against the openconfig-vlan
          module for the Nokia SR OS based routers.

         Copyright 2016 Nokia. All rights reserved. Reproduction of this document
         is authorized on the condition that the foregoing copyright notice is included.

         This nokia-sr-openconfig-vlan-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2017-07-14";

    deviation /oc-if:interfaces/oc-if:interface/oc-if:subinterfaces/oc-if:subinterface/oc-vlan:vlan/oc-vlan:config/oc-vlan:vlan-id {
        deviate replace {
            type union {
                type uint16 {
                    range "0..4094";
                }
                type oc-vlan-types:qinq-id;
            }
        }
    }

    deviation /oc-if:interfaces/oc-if:interface/oc-if:subinterfaces/oc-if:subinterface/oc-vlan:vlan/oc-vlan:state/oc-vlan:vlan-id {
        deviate replace {
            type union {
                type uint16 {
                    range "0..4094";
                }
                type oc-vlan-types:qinq-id;
            }
        }
    }

    deviation /oc-if:interfaces/oc-if:interface/oc-vlan:routed-vlan {
        deviate not-supported;
    }

    deviation /oc-if:interfaces/oc-if:interface/oc-eth:ethernet/oc-vlan:switched-vlan {
        deviate not-supported;
    }

    deviation /oc-if:interfaces/oc-if:interface/oc-lag:aggregation/oc-vlan:switched-vlan {
        deviate not-supported;
    }

    deviation /oc-if:interfaces/oc-if:interface/oc-if:config/oc-vlan:tpid {
        deviate not-supported;
    }

    deviation /oc-if:interfaces/oc-if:interface/oc-if:state/oc-vlan:tpid {
        deviate not-supported;
    }

}
