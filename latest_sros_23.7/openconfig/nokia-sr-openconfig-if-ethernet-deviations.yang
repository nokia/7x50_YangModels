module nokia-sr-openconfig-if-ethernet-deviations {

    namespace "urn:nokia.com:sros:ns:yang:sr:openconfig-if-ethernet-deviations";

    prefix "nokia-oc-eth-devs";

    import nokia-sros-yang-extensions     { prefix "sros-ext"; }
    import openconfig-extensions          { prefix "oc-ext"; }
    import openconfig-if-ethernet         { prefix "oc-eth"; }
    import openconfig-interfaces          { prefix "oc-if"; }
    import openconfig-yang-types          { prefix "oc-yang"; }

    sros-ext:sros-major-release "rel23";
    organization "Nokia";
    contact
        "Nokia SR OS Support
         Web: <http://www.nokia.com>";
    description
        "This module contains the list of deviations against the openconfig-if-ethernet
          module for the Nokia SR OS based routers.

         Copyright 2016 Nokia. All rights reserved. Reproduction of this document
         is authorized on the condition that the foregoing copyright notice is included.

         This nokia-sr-openconfig-if-ethernet-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2021-07-20";

    deviation /oc-if:interfaces/oc-if:interface/oc-eth:ethernet/oc-eth:config/oc-eth:auto-negotiate {
        deviate delete {
            default "true";
        }
    }

    deviation /oc-if:interfaces/oc-if:interface/oc-eth:ethernet/oc-eth:config/oc-eth:standalone-link-training {
        deviate not-supported;
    }

    deviation /oc-if:interfaces/oc-if:interface/oc-eth:ethernet/oc-eth:config/oc-eth:enable-flow-control {
        deviate not-supported;
    }

    deviation /oc-if:interfaces/oc-if:interface/oc-eth:ethernet/oc-eth:config/oc-eth:fec-mode {
        deviate not-supported;
    }

    deviation /oc-if:interfaces/oc-if:interface/oc-eth:ethernet/oc-eth:state/oc-eth:auto-negotiate {
        deviate delete {
            default "true";
        }
    }

    deviation /oc-if:interfaces/oc-if:interface/oc-eth:ethernet/oc-eth:state/oc-eth:standalone-link-training {
        deviate not-supported;
    }

    deviation /oc-if:interfaces/oc-if:interface/oc-eth:ethernet/oc-eth:state/oc-eth:enable-flow-control {
        deviate not-supported;
    }

    deviation /oc-if:interfaces/oc-if:interface/oc-eth:ethernet/oc-eth:state/oc-eth:fec-mode {
        deviate not-supported;
    }

    deviation /oc-if:interfaces/oc-if:interface/oc-eth:ethernet/oc-eth:state/oc-eth:counters/oc-eth:in-mac-control-frames {
        deviate not-supported;
    }

    deviation /oc-if:interfaces/oc-if:interface/oc-eth:ethernet/oc-eth:state/oc-eth:counters/oc-eth:in-undersize-frames {
        deviate not-supported;
    }

    deviation /oc-if:interfaces/oc-if:interface/oc-eth:ethernet/oc-eth:state/oc-eth:counters/oc-eth:in-8021q-frames {
        deviate not-supported;
    }

    deviation /oc-if:interfaces/oc-if:interface/oc-eth:ethernet/oc-eth:state/oc-eth:counters/oc-eth:in-block-errors {
        deviate not-supported;
    }

    deviation /oc-if:interfaces/oc-if:interface/oc-eth:ethernet/oc-eth:state/oc-eth:counters/oc-eth:in-carrier-errors {
        deviate not-supported;
    }

    deviation /oc-if:interfaces/oc-if:interface/oc-eth:ethernet/oc-eth:state/oc-eth:counters/oc-eth:in-interrupted-tx {
        deviate not-supported;
    }

    deviation /oc-if:interfaces/oc-if:interface/oc-eth:ethernet/oc-eth:state/oc-eth:counters/oc-eth:in-late-collision {
        deviate not-supported;
    }

    deviation /oc-if:interfaces/oc-if:interface/oc-eth:ethernet/oc-eth:state/oc-eth:counters/oc-eth:in-mac-errors-rx {
        deviate not-supported;
    }

    deviation /oc-if:interfaces/oc-if:interface/oc-eth:ethernet/oc-eth:state/oc-eth:counters/oc-eth:in-single-collision {
        deviate not-supported;
    }

    deviation /oc-if:interfaces/oc-if:interface/oc-eth:ethernet/oc-eth:state/oc-eth:counters/oc-eth:in-symbol-error {
        deviate not-supported;
    }

    deviation /oc-if:interfaces/oc-if:interface/oc-eth:ethernet/oc-eth:state/oc-eth:counters/oc-eth:in-maxsize-exceeded {
        deviate not-supported;
    }

    deviation /oc-if:interfaces/oc-if:interface/oc-eth:ethernet/oc-eth:state/oc-eth:counters/oc-eth:out-mac-control-frames {
        deviate not-supported;
    }

    deviation /oc-if:interfaces/oc-if:interface/oc-eth:ethernet/oc-eth:state/oc-eth:counters/oc-eth:out-8021q-frames {
        deviate not-supported;
    }

    deviation /oc-if:interfaces/oc-if:interface/oc-eth:ethernet/oc-eth:state/oc-eth:counters/oc-eth:out-mac-errors-tx {
        deviate not-supported;
    }

}
