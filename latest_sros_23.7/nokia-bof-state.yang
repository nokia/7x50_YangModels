module nokia-bof-state {

    yang-version "1.1";

    namespace "urn:nokia.com:sros:ns:yang:sr:bof-state";

    prefix "bof-state";

    import nokia-sros-yang-extensions     { prefix "sros-ext"; }
    import nokia-state                    { prefix "state"; }
    import nokia-types-port               { prefix "types-port"; }
    import nokia-types-router             { prefix "types-router"; }
    import nokia-types-sros               { prefix "types-sros"; }

    sros-ext:sros-major-release "rel23";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-bof-state YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2023-04-27";

    augment /state:state {

        ///nokia-bof-state/bof
        container bof {
            config false;
            description "Enter the bof context";

            ///nokia-bof-state/bof/booted
            container booted {
                description "Enter the booted context";

                ///nokia-bof-state/bof/booted/auto-boot
                container auto-boot {
                    description "Enter the auto-boot context";

                    ///nokia-bof-state/bof/booted/auto-boot/port-mtu
                    leaf port-mtu {
                        type uint32 {
                            range "512..9800";
                        }
                        units "bytes";
                        description "Port MTU setting";
                    }

                    ///nokia-bof-state/bof/booted/auto-boot/timeout
                    leaf timeout {
                        type uint32 {
                            range "30..1440";
                        }
                        units "minutes";
                        description "Timeout of Auto-Boot";
                    }

                    ///nokia-bof-state/bof/booted/auto-boot/auto-boot-mode
                    choice auto-boot-mode {
                        ///nokia-bof-state/bof/booted/auto-boot/auto-boot-mode/dhcp
                        case dhcp {

                            ///nokia-bof-state/bof/booted/auto-boot/auto-boot-mode/dhcp/dhcp
                            container dhcp {
                                description "Enter the dhcp context";

                                ///nokia-bof-state/bof/booted/auto-boot/auto-boot-mode/dhcp/dhcp/client-id
                                leaf client-id {
                                    type union {
                                        type enumeration {
                                            enum use-chassis-mac-address        { value 0; }
                                        }
                                        type types-sros:hex-string {
                                            length "3..118";
                                        }
                                        type string {
                                            length "1..58";
                                        }
                                    }
                                    description "DHCP client ID";
                                }

                                ///nokia-bof-state/bof/booted/auto-boot/auto-boot-mode/dhcp/dhcp/management-port
                                leaf management-port {
                                    type boolean;
                                    description "Use auto boot on the management port";
                                }

                                ///nokia-bof-state/bof/booted/auto-boot/auto-boot-mode/dhcp/dhcp/ipv4
                                leaf ipv4 {
                                    type boolean;
                                    description "Use auto boot with IPv4";
                                }

                                ///nokia-bof-state/bof/booted/auto-boot/auto-boot-mode/dhcp/dhcp/ipv6
                                leaf ipv6 {
                                    type boolean;
                                    description "Use auto boot with IPv6";
                                }

                                ///nokia-bof-state/bof/booted/auto-boot/auto-boot-mode/dhcp/dhcp/include-user-class
                                leaf include-user-class {
                                    type boolean;
                                    description "Include user class in auto boot provisioning";
                                }

                                ///nokia-bof-state/bof/booted/auto-boot/auto-boot-mode/dhcp/dhcp/inband
                                container inband {
                                    description "Enter the inband context";

                                    ///nokia-bof-state/bof/booted/auto-boot/auto-boot-mode/dhcp/dhcp/inband/inband-options
                                    choice inband-options {
                                        ///nokia-bof-state/bof/booted/auto-boot/auto-boot-mode/dhcp/dhcp/inband/inband-options/specific-vlan
                                        case specific-vlan {

                                            ///nokia-bof-state/bof/booted/auto-boot/auto-boot-mode/dhcp/dhcp/inband/inband-options/specific-vlan/vlan
                                            leaf vlan {
                                                type types-sros:vlan-id;
                                                description "Inband VLAN ID";
                                            }

                                        }
                                        ///nokia-bof-state/bof/booted/auto-boot/auto-boot-mode/dhcp/dhcp/inband/inband-options/discovery-mode
                                        case discovery-mode {

                                            ///nokia-bof-state/bof/booted/auto-boot/auto-boot-mode/dhcp/dhcp/inband/inband-options/discovery-mode/vlan-discovery
                                            leaf vlan-discovery {
                                                type boolean;
                                                description "Use VLAN discovery";
                                            }

                                        }
                                        ///nokia-bof-state/bof/booted/auto-boot/auto-boot-mode/dhcp/dhcp/inband/inband-options/null-encapsulation
                                        case null-encapsulation {

                                            ///nokia-bof-state/bof/booted/auto-boot/auto-boot-mode/dhcp/dhcp/inband/inband-options/null-encapsulation/null-encapsulation
                                            leaf null-encapsulation {
                                                type boolean;
                                                description "Use null encapsulation";
                                            }

                                        }
                                        ///nokia-bof-state/bof/booted/auto-boot/auto-boot-mode/dhcp/dhcp/inband/inband-options/disabled
                                        case disabled {

                                            ///nokia-bof-state/bof/booted/auto-boot/auto-boot-mode/dhcp/dhcp/inband/inband-options/disabled/disabled
                                            leaf disabled {
                                                type boolean;
                                                description "Do not use inband ports";
                                            }

                                        }
                                    }
                                } // container inband

                            } // container dhcp

                        }
                        ///nokia-bof-state/bof/booted/auto-boot/auto-boot-mode/ospf
                        case ospf {

                            ///nokia-bof-state/bof/booted/auto-boot/auto-boot-mode/ospf/ospf
                            container ospf {
                                description "Enter the ospf context";

                                ///nokia-bof-state/bof/booted/auto-boot/auto-boot-mode/ospf/ospf/neid
                                leaf neid {
                                    type types-sros:hex-string {
                                        length "3";
                                    }
                                    description "Network Element ID";
                                }

                                ///nokia-bof-state/bof/booted/auto-boot/auto-boot-mode/ospf/ospf/neip-ipv4
                                leaf neip-ipv4 {
                                    type types-sros:ipv4-unicast-address;
                                    description "Network Element IPV4 Address";
                                }

                                ///nokia-bof-state/bof/booted/auto-boot/auto-boot-mode/ospf/ospf/neip-ipv6
                                leaf neip-ipv6 {
                                    type types-sros:ipv6-address;
                                    description "Network Element IPV6 Address";
                                }

                                ///nokia-bof-state/bof/booted/auto-boot/auto-boot-mode/ospf/ospf/mtu
                                leaf mtu {
                                    type types-router:ip-mtu;
                                    units "bytes";
                                    description "OSPF Mtu";
                                }

                                ///nokia-bof-state/bof/booted/auto-boot/auto-boot-mode/ospf/ospf/vendor-id
                                leaf vendor-id {
                                    type uint32 {
                                        range "1..254";
                                    }
                                    description "Vendor Id";
                                }

                            } // container ospf

                        }
                    }
                } // container auto-boot

                ///nokia-bof-state/bof/booted/auto-configure
                container auto-configure {
                    description "Enter the auto-configure context";

                    ///nokia-bof-state/bof/booted/auto-configure/ipv4
                    container ipv4 {
                        description "Enter the ipv4 context";

                        ///nokia-bof-state/bof/booted/auto-configure/ipv4/dhcp
                        container dhcp {
                            description "Enter the dhcp context";

                            ///nokia-bof-state/bof/booted/auto-configure/ipv4/dhcp/client-id
                            leaf client-id {
                                type union {
                                    type types-sros:hex-string {
                                        length "3..514";
                                    }
                                    type string {
                                        length "256";
                                    }
                                }
                                description "DHCP client ID";
                            }

                            ///nokia-bof-state/bof/booted/auto-configure/ipv4/dhcp/include-user-class
                            leaf include-user-class {
                                type boolean;
                                description "Include user class information";
                            }

                            ///nokia-bof-state/bof/booted/auto-configure/ipv4/dhcp/timeout
                            leaf timeout {
                                type uint32 {
                                    range "1..65535";
                                }
                                description "DHCP timeout";
                            }

                        } // container dhcp

                    } // container ipv4

                    ///nokia-bof-state/bof/booted/auto-configure/ipv6
                    container ipv6 {
                        description "Enter the ipv6 context";

                        ///nokia-bof-state/bof/booted/auto-configure/ipv6/dhcp
                        container dhcp {
                            description "Enter the dhcp context";

                            ///nokia-bof-state/bof/booted/auto-configure/ipv6/dhcp/client-type
                            leaf client-type {
                                type enumeration {
                                    enum duid-enterprise                { value 2; }
                                    enum duid-link-local                { value 3; }
                                }
                                description "DHCP client type";
                            }

                            ///nokia-bof-state/bof/booted/auto-configure/ipv6/dhcp/client-id
                            leaf client-id {
                                type union {
                                    type types-sros:hex-string {
                                        length "3..514";
                                    }
                                    type string {
                                        length "256";
                                    }
                                }
                                description "DHCP client ID";
                            }

                            ///nokia-bof-state/bof/booted/auto-configure/ipv6/dhcp/include-user-class
                            leaf include-user-class {
                                type boolean;
                                description "Include user class information";
                            }

                            ///nokia-bof-state/bof/booted/auto-configure/ipv6/dhcp/timeout
                            leaf timeout {
                                type uint32 {
                                    range "1..65535";
                                }
                                description "DHCP timeout";
                            }

                        } // container dhcp

                    } // container ipv6

                } // container auto-configure

                ///nokia-bof-state/bof/booted/configuration
                container configuration {
                    description "Enter the configuration context";

                    ///nokia-bof-state/bof/booted/configuration/primary-location
                    leaf primary-location {
                        type types-sros:cflash-and-url;
                        description "Primary configuration location";
                    }

                    ///nokia-bof-state/bof/booted/configuration/secondary-location
                    leaf secondary-location {
                        type types-sros:cflash-and-url;
                        description "Secondary configuration location";
                    }

                    ///nokia-bof-state/bof/booted/configuration/tertiary-location
                    leaf tertiary-location {
                        type types-sros:cflash-and-url;
                        description "Tertiary configuration location";
                    }

                    ///nokia-bof-state/bof/booted/configuration/encrypt
                    leaf encrypt {
                        type boolean;
                        description "Whether BOF configuration files are encrypted.";
                    }

                    ///nokia-bof-state/bof/booted/configuration/password
                    leaf password {
                        type binary {
                            length "1..32";
                        }
                        description "Password for encrypted BOF configuration files.";
                    }

                    ///nokia-bof-state/bof/booted/configuration/encryption-key
                    leaf encryption-key {
                        type binary {
                            length "1..32";
                        }
                        description "Key for encrypted BOF configuration files.";
                    }

                } // container configuration

                ///nokia-bof-state/bof/booted/console
                container console {
                    description "Enter the console context";

                    ///nokia-bof-state/bof/booted/console/speed
                    leaf speed {
                        type uint32 {
                            range "9600|19200|38400|57600|115200";
                        }
                        units "bps";
                        description "Console port speed";
                    }

                    ///nokia-bof-state/bof/booted/console/wait-time
                    leaf wait-time {
                        type uint32 {
                            range "1..10";
                        }
                        units "seconds";
                        description "Wait time for interrupt to change boot parameters";
                    }

                } // container console

                ///nokia-bof-state/bof/booted/dns
                container dns {
                    description "Enter the dns context";

                    ///nokia-bof-state/bof/booted/dns/domain
                    leaf domain {
                        type string {
                            length "1..178";
                        }
                        description "System DNS domain name for DNS address resolution";
                    }

                    ///nokia-bof-state/bof/booted/dns/primary-server
                    leaf primary-server {
                        type types-sros:ip-address;
                        description "Primary DNS server";
                    }

                    ///nokia-bof-state/bof/booted/dns/secondary-server
                    leaf secondary-server {
                        type types-sros:ip-address;
                        description "Secondary DNS server";
                    }

                    ///nokia-bof-state/bof/booted/dns/tertiary-server
                    leaf tertiary-server {
                        type types-sros:ip-address;
                        description "Tertiary DNS server";
                    }

                } // container dns

                ///nokia-bof-state/bof/booted/image
                container image {
                    description "Enter the image context";

                    ///nokia-bof-state/bof/booted/image/primary-location
                    leaf primary-location {
                        type types-sros:cflash-and-url;
                        description "Primary image location";
                    }

                    ///nokia-bof-state/bof/booted/image/secondary-location
                    leaf secondary-location {
                        type types-sros:cflash-and-url;
                        description "Secondary image location";
                    }

                    ///nokia-bof-state/bof/booted/image/tertiary-location
                    leaf tertiary-location {
                        type types-sros:cflash-and-url;
                        description "Tertiary image location";
                    }

                } // container image

                ///nokia-bof-state/bof/booted/li
                container li {
                    description "Enter the li context";

                    ///nokia-bof-state/bof/booted/li/local-save
                    leaf local-save {
                        type boolean;
                        description "Save the LI configuration locally";
                    }

                    ///nokia-bof-state/bof/booted/li/separate
                    leaf separate {
                        type boolean;
                        description "Separate access to the LI information";
                    }

                } // container li

                ///nokia-bof-state/bof/booted/license
                container license {
                    description "Enter the license context";

                    ///nokia-bof-state/bof/booted/license/primary-location
                    leaf primary-location {
                        type types-sros:cflash-and-url;
                        description "Primary license file location";
                    }

                } // container license

                ///nokia-bof-state/bof/booted/port
                list port {
                    key "router-name";
                    description "Enter the port list instance";

                    ///nokia-bof-state/bof/booted/port/router-name
                    leaf router-name {
                        type types-sros:named-item-64;
                        description "Administrative name for the virtual router";
                    }

                    ///nokia-bof-state/bof/booted/port/autonegotiate
                    leaf autonegotiate {
                        type enumeration {
                            enum false                          { value 0; }
                            enum true                           { value 1; }
                        }
                        description "Autonegotiate speed and duplex type on Ethernet port";
                    }

                    ///nokia-bof-state/bof/booted/port/duplex
                    leaf duplex {
                        type types-port:duplex-mode;
                        description "Duplex type for the Ethernet port";
                    }

                    ///nokia-bof-state/bof/booted/port/speed
                    leaf speed {
                        type uint32 {
                            range "10|100|1000";
                        }
                        units "megabps";
                        description "Speed of the Ethernet port";
                    }

                } // list port

                ///nokia-bof-state/bof/booted/router
                list router {
                    key "router-name";
                    description "Enter the router list instance";

                    ///nokia-bof-state/bof/booted/router/router-name
                    leaf router-name {
                        type types-sros:named-item-64;
                        description "Administrative name of the virtual router";
                    }

                    ///nokia-bof-state/bof/booted/router/interface
                    list interface {
                        key "interface-name";
                        description "Enter the interface list instance";

                        ///nokia-bof-state/bof/booted/router/interface/interface-name
                        leaf interface-name {
                            type types-sros:interface-name;
                            description "Router interface name";
                        }

                        ///nokia-bof-state/bof/booted/router/interface/ip-mtu
                        leaf ip-mtu {
                            type types-router:ip-mtu-ext;
                            units "bytes";
                            description "Interface IP MTU";
                        }

                        ///nokia-bof-state/bof/booted/router/interface/cpm
                        list cpm {
                            key "cpm-type";
                            description "Enter the cpm list instance";

                            ///nokia-bof-state/bof/booted/router/interface/cpm/cpm-type
                            leaf cpm-type {
                                type enumeration {
                                    enum active                         { value 0; }
                                    enum standby                        { value 1; }
                                    enum a                              { value 2; }
                                    enum b                              { value 3; }
                                    enum c                              { value 4; }
                                    enum d                              { value 5; }
                                }
                                description "CPM type";
                            }

                            ///nokia-bof-state/bof/booted/router/interface/cpm/ipv4
                            container ipv4 {
                                description "Enter the ipv4 context";

                                ///nokia-bof-state/bof/booted/router/interface/cpm/ipv4/ip-address
                                leaf ip-address {
                                    type types-sros:ipv4-unicast-address;
                                    description "IPv4 address assigned to the interface";
                                }

                                ///nokia-bof-state/bof/booted/router/interface/cpm/ipv4/prefix-length
                                leaf prefix-length {
                                    type uint32 {
                                        range "0..32";
                                    }
                                    description "IPv4 address prefix length";
                                }

                            } // container ipv4

                            ///nokia-bof-state/bof/booted/router/interface/cpm/ipv6
                            container ipv6 {
                                description "Enter the ipv6 context";

                                ///nokia-bof-state/bof/booted/router/interface/cpm/ipv6/ipv6-address
                                leaf ipv6-address {
                                    type types-sros:ipv6-address;
                                    description "IPv6 address assigned to the interface";
                                }

                                ///nokia-bof-state/bof/booted/router/interface/cpm/ipv6/prefix-length
                                leaf prefix-length {
                                    type uint32 {
                                        range "0..128";
                                    }
                                    description "IPv6 address prefix length";
                                }

                            } // container ipv6

                        } // list cpm

                    } // list interface

                    ///nokia-bof-state/bof/booted/router/static-routes
                    container static-routes {
                        description "Enter the static-routes context";

                        ///nokia-bof-state/bof/booted/router/static-routes/route
                        list route {
                            key "ip-prefix";
                            description "Enter the route list instance";

                            ///nokia-bof-state/bof/booted/router/static-routes/route/ip-prefix
                            leaf ip-prefix {
                                type types-sros:ip-prefix;
                                description "IP prefix for the static route";
                            }

                            ///nokia-bof-state/bof/booted/router/static-routes/route/next-hop
                            leaf next-hop {
                                type types-sros:ip-address;
                                description "Next-hop IP address";
                            }

                        } // list route

                    } // container static-routes

                } // list router

                ///nokia-bof-state/bof/booted/system
                container system {
                    description "Enter the system context";

                    ///nokia-bof-state/bof/booted/system/base-mac-address
                    leaf base-mac-address {
                        type types-sros:mac-unicast-address;
                        description "Base system MAC address";
                    }

                    ///nokia-bof-state/bof/booted/system/fips-140-2
                    leaf fips-140-2 {
                        type boolean;
                        description "Operate in FIPS-140.2 mode";
                    }

                    ///nokia-bof-state/bof/booted/system/persistent-indices
                    leaf persistent-indices {
                        type boolean;
                        description "Classic and mixed management mode persistent indicies";
                    }

                    ///nokia-bof-state/bof/booted/system/profile
                    leaf profile {
                        type enumeration {
                            enum profile-a                      { value 1; }
                            enum profile-b                      { value 2; }
                        }
                        description "System capabilities profile";
                    }

                } // container system

            } // container booted

        } // container bof

    }
}
