module nokia-types-ripng {

    yang-version "1.1";

    namespace "urn:nokia.com:sros:ns:yang:sr:types-ripng";

    prefix "types-ripng";

    import nokia-sros-yang-extensions     { prefix "sros-ext"; }

    sros-ext:sros-major-release "rel25";
    organization "Nokia";
    contact
        "Nokia SR OS Support
         Web: <http://www.nokia.com>";
    description
        "Common RIPng typedefs data types used in the SR OS management system.

         Copyright 2016 Nokia. All rights reserved. Reproduction of this document
         is authorized on the condition that the foregoing copyright notice is included.

         This nokia-types-ripng YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    typedef message-size {
        type uint32 {
            range "25..255";
        }
        description "The maximum number of routes that can be sent out per RIPng update message.";
    }

    typedef metric {
        type uint32 {
            range "1..16";
        }
        description "Represents the metric.";
    }

    typedef preference {
        type uint32 {
            range "1..255";
        }
        description "Router preference.";
    }

    typedef timer-flush {
        type uint32 {
            range "1..1200";
        }
        units "seconds";
        description "Flush timer.";
    }

    typedef timer-timeout {
        type uint32 {
            range "1..1200";
        }
        units "seconds";
        description "Timeout timer.";
    }

    typedef timer-update {
        type uint32 {
            range "1..600";
        }
        units "seconds";
        description "Update timer.";
    }

    typedef receive {
        type enumeration {
            enum none                           { value 4; }
            enum ripng                          { value 5; }
        }
        description "Acceptable RIPng version on received packets.";
    }

    typedef peer-version {
        type enumeration {
            enum none                           { value 0; }
            enum ripng-v1                       { value 3; }
        }
        description "The RIPng version in the header of a packet received from a peer.";
    }

}
