submodule nokia-state-port-sonet {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }


    sros-ext:sros-major-release "rel21";

    organization "Nokia";

    contact
        "Nokia SR OS Support
         Web: <http://www.nokia.com>";

    description
        "Nokia YANG Data model with operational state for SONET/SDH ports on SR OS based routers.

         Copyright 2016 Nokia. All rights reserved. Reproduction of this document
         is authorized on the condition that the foregoing copyright notice is included.

         This nokia-state-port-sonet YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-26";

    grouping state-port-sonet-sonet-sdh {
        container sonet-sdh {
            description "Enter the sonet-sdh context";

            leaf current-alarms {
                type types-port:sonet-report-alarms;
                description "Indicates the current alarms on the SONET port.";
            }

            leaf received-j0-string {
                type string {
                    length "0..32";
                }
                description "Indicates the contents of the j0 byte in the SONET Section Header.";
            }

            leaf received-k1-byte {
                type uint32 {
                    range "0..255";
                }
                description
                    "Indicates the Automatic Protection Switching(APS) signalling status from
                     the K1 byte in the SONET Line Overhead Header.";
            }

            leaf received-k2-byte {
                type uint32 {
                    range "0..255";
                }
                description
                    "Indicates the Automatic Protection Switching(APS) signalling status from
                     the K2 byte in the SONET Line Overhead Header.";
            }

            leaf received-s1-byte {
                type uint32 {
                    range "0..255";
                }
                description
                    "Indicates the Synchronization Status Message from the S1 byte in
                     the Line Overhead Header. A value of 0x00 indicates unknown quality.
                     A value of 0xF0 indicates `Do not use for synchronization`. Other
                     values are documented in Telcordia GR253 and ITU G.707.";
            }

            leaf transmitted-s1-byte {
                type uint32;
                description "Indicates the transmitted S1 Byte.";
            }

            list path {
                key "path-index";
                description "Enter the path list instance";

                leaf path-index {
                    type types-port:sonet-path-index;
                    description "Specifies the SONET/SDH path index.";
                }

                leaf oper-mtu {
                    type uint32;
                    units "bytes";
                    description
                        "Indicates the negotiated size of the largest packet which
                         can be sent on the path.";
                }

                leaf rx-signal-label {
                    type string;
                    description "Indicates what was received in the C2 header byte.";
                }

                container ppp {
                    description "Enter the ppp context";

                    leaf header-compression {
                        type bits {
                            bit acfc                           { position 0; }
                            bit pfc                            { position 1; }
                        }
                        description
                            "Indicates whether or not the ACFC or PFC protocols are requested
                             in config requests sent and accepted in config requests received.";
                    }

                    leaf line-monitor-method {
                        type enumeration {
                            enum "none"                         { value 1; }
                            enum "keepalive"                    { value 2; }
                            enum "lqm"                          { value 3; }
                        }
                        description
                            "Indicates the type of line monitoring packets being sent and received
                             on this PPP link";
                    }

                    leaf time-to-link-drop {
                        type types-sros:time-interval;
                        description
                            "Indicates the time remaining before the link will be declared dropped
                             if a keepalive echo reply packet is not received.";
                    }

                    container local {
                        description "Enter the local context";

                        leaf ipv4-address {
                            type types-sros:ipv4-address;
                            description "Indicates the IPv4 address of the local end of the PPP link.";
                        }

                        leaf ipv6-address {
                            type types-sros:ipv6-address;
                            description "Indicates the IPv6 address of the local end of the PPP link.";
                        }

                        leaf magic-number {
                            type uint32;
                            description
                                "Indicates the magic number to be sent to the peer.
                                 The magic number provides a method to detect loopbacks. If the
                                 value of local-magic-number is the same as the value of
                                 remote-magic-number, then it is possible that the link might
                                 be looped back. If the two magic numbers do not match, then the link
                                 is not looped back.";
                        }

                    } // container local

                    container remote {
                        description "Enter the remote context";

                        leaf ipv4-address {
                            type types-sros:ipv4-address;
                            description "Indicates the IPv4 address of the remote end of the PPP link.";
                        }

                        leaf ipv6-address {
                            type types-sros:ipv6-address;
                            description "Indicates the IPv6 address of the remote end of the PPP link.";
                        }

                        leaf mac-address {
                            type yang:mac-address;
                            description "Indicates the Ethernet MAC address sent by the remote end of the PPP link.";
                        }

                        leaf magic-number {
                            type uint32;
                            description
                                "Indicates the magic number sent by the peer.
                                 If the value of local-magic-number is the same as the value of
                                 remote-magic-number, then it is possible that the link might
                                 be looped back. If the two magic numbers do not match, then the link
                                 is not looped back.";
                        }

                    } // container remote

                    container statistics {
                        description "Enter the statistics context";

                        leaf last-cleared-time {
                            type yang:date-and-time;
                            description
                                "Indicates the last time that keepalive stats were cleared.
                                 Note that the keepalive stats are cleared when changing from
                                 LQM to keepalives or vice versa.";
                        }

                        leaf in-packets {
                            type yang:counter32;
                            description "Indicates the number of echo-reply packets received.";
                        }

                        leaf out-packets {
                            type yang:counter32;
                            description "Indicates the number of echo-request packets sent.";
                        }

                        leaf threshold-exceeded {
                            type yang:counter32;
                            description "Indicates the number of times that drop-count was reached.";
                        }

                    } // container statistics

                    list control-protocol {
                        key "protocol";
                        description "Enter the control-protocol list instance";

                        leaf protocol {
                            type enumeration {
                                enum "lcp"                          { value 1; }
                                enum "ipcp"                         { value 2; }
                                enum "mplscp"                       { value 3; }
                                enum "bcp"                          { value 4; }
                                enum "osicp"                        { value 5; }
                                enum "lqr"                          { value 6; }
                                enum "ipv6cp"                       { value 7; }
                            }
                            description "Indicates the control protocol type.";
                        }

                        leaf state {
                            type enumeration {
                                enum "initial"                      { value 1; }
                                enum "starting"                     { value 2; }
                                enum "closed"                       { value 3; }
                                enum "stopped"                      { value 4; }
                                enum "closing"                      { value 5; }
                                enum "stopping"                     { value 6; }
                                enum "request-sent"                 { value 7; }
                                enum "ack-received"                 { value 8; }
                                enum "ack-sent"                     { value 9; }
                                enum "opened"                       { value 10; }
                            }
                            description
                                "Indicates the current state of the PPP Control Protocol
                                 on this interface.";
                        }

                        leaf state-last-changed {
                            type yang:date-and-time;
                            description "Indicates the last time the value of state changed.";
                        }

                        leaf restart-count {
                            type yang:counter32;
                            description
                                "Indicates the number of times the control protocol has reached
                                 the 'opened' state.";
                        }

                        leaf restart-count-last-cleared {
                            type yang:date-and-time;
                            description "Indicates the last time restart-count has been reset to zero.";
                        }

                    } // list control-protocol

                } // container ppp

                container statistics {
                    description "Enter the statistics context";

                    leaf coding-violations {
                        type yang:counter32;
                        description "Indicates the number of Coding Violations (CV)";
                    }

                    leaf errored-seconds {
                        type yang:counter32;
                        description "Indicates the number of Errored Seconds (ES).";
                    }

                    leaf severely-errored-seconds {
                        type yang:counter32;
                        description "Indicates the number of Severely Errored Seconds (SES).";
                    }

                    leaf unavailable-seconds {
                        type yang:counter32;
                        description "Indicates the number of Unavailable Seconds (UAS).";
                    }

                    container far-end {
                        description "Enter the far-end context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                        leaf unavailable-seconds {
                            type yang:counter32;
                            description "Indicates the number of Unavailable Seconds (UAS).";
                        }

                    } // container far-end

                    container receive {
                        description "Enter the receive context";

                        leaf loss-of-pointer {
                            type yang:counter32;
                            description "Indicates the number of Loss Of Pointer path (LOP) occurrences.";
                        }

                        leaf alarm-indication-signal {
                            type yang:counter32;
                            description "Indicates the number of Alarm Indication Signal (AIS) occurrences.";
                        }

                        leaf remote-defect-indication {
                            type yang:counter32;
                            description "Indicates the number of Remote Defect Indication (RDI) occurrences.";
                        }

                        leaf payload-mismatch {
                            type yang:counter32;
                            description "Indicates the number of Payload Mismatch (PLM) occurrences.";
                        }

                        leaf loss-of-cell-delineation {
                            type yang:counter32;
                            description "Indicates the number of Loss of Cell Delineation (LCD) occurrences.";
                        }

                        leaf unequipped {
                            type yang:counter32;
                            description "Indicates the number of unequipped occurrences.";
                        }

                        leaf remote-error {
                            type yang:counter32;
                            description "Indicates the number of remote errors.";
                        }

                        leaf parity-error {
                            type yang:counter32;
                            description "Indicates the number of parity errors.";
                        }

                        leaf fifo-error {
                            type yang:counter32;
                            description "Indicates the number of FIFO errors.";
                        }

                        leaf max-packet-error {
                            type yang:counter32;
                            description "Indicates the number of maximum packet errors.";
                        }

                        leaf min-packet-error {
                            type yang:counter32;
                            description "Indicates the number of minimum packet errors.";
                        }

                        leaf fcs-error {
                            type yang:counter32;
                            description "Indicates the number of Frame Check Sequence (FCS) errors.";
                        }

                        leaf packet-abort-error {
                            type yang:counter32;
                            description "Indicates the number of packet abort errors.";
                        }

                        leaf address-control-invalid {
                            type yang:counter32;
                            description "Indicates the number of address control invalid occurrences.";
                        }

                    } // container receive

                    container transmit {
                        description "Enter the transmit context";

                        leaf loss-of-pointer {
                            type yang:counter32;
                            description "Indicates the number of Loss Of Pointer path (LOP) occurrences.";
                        }

                        leaf fifo-error {
                            type yang:counter32;
                            description "Indicates the number of FIFO errors.";
                        }

                        leaf max-packet-error {
                            type yang:counter32;
                            description "Indicates the number of maximum packet errors.";
                        }

                        leaf min-packet-error {
                            type yang:counter32;
                            description "Indicates the number of minimum packet errors.";
                        }

                        leaf llp-packet-error {
                            type yang:counter32;
                            description "Indicates the number of LLP packet errors.";
                        }

                        leaf fifo-underflow-error {
                            type yang:counter32;
                            description "Indicates the number of FIFO underflow errors.";
                        }

                    } // container transmit

                } // container statistics

            } // list path

            container statistics {
                description "Enter the statistics context";

                container line {
                    description "Enter the line context";

                    leaf coding-violations {
                        type yang:counter32;
                        description "Indicates the number of Coding Violations (CV)";
                    }

                    leaf errored-seconds {
                        type yang:counter32;
                        description "Indicates the number of Errored Seconds (ES).";
                    }

                    leaf severely-errored-seconds {
                        type yang:counter32;
                        description "Indicates the number of Severely Errored Seconds (SES).";
                    }

                    leaf unavailable-seconds {
                        type yang:counter32;
                        description "Indicates the number of Unavailable Seconds (UAS).";
                    }

                    leaf alarm-indication-signal {
                        type yang:counter32;
                        description "Indicates the number of Alarm Indication Signal (AIS) occurrences.";
                    }

                    leaf remote-defect-indication {
                        type yang:counter32;
                        description "Indicates the number of Remote Defect Indication (RDI) occurrences.";
                    }

                    leaf b2-error {
                        type yang:counter32;
                        description "Indicates the number of B2 errors.";
                    }

                    leaf s1-error {
                        type yang:counter32;
                        description "Indicates the number of S1 errors.";
                    }

                    leaf m1-error {
                        type yang:counter32;
                        description "Indicates the number of M1 errors.";
                    }

                    container far-end {
                        description "Enter the far-end context";

                        leaf coding-violations {
                            type yang:counter32;
                            description "Indicates the number of Coding Violations (CV)";
                        }

                        leaf errored-seconds {
                            type yang:counter32;
                            description "Indicates the number of Errored Seconds (ES).";
                        }

                        leaf severely-errored-seconds {
                            type yang:counter32;
                            description "Indicates the number of Severely Errored Seconds (SES).";
                        }

                        leaf unavailable-seconds {
                            type yang:counter32;
                            description "Indicates the number of Unavailable Seconds (UAS).";
                        }

                    } // container far-end

                } // container line

                container section {
                    description "Enter the section context";

                    leaf coding-violations {
                        type yang:counter32;
                        description "Indicates the number of Coding Violations (CV)";
                    }

                    leaf errored-seconds {
                        type yang:counter32;
                        description "Indicates the number of Errored Seconds (ES).";
                    }

                    leaf severely-errored-seconds {
                        type yang:counter32;
                        description "Indicates the number of Severely Errored Seconds (SES).";
                    }

                    leaf severely-errored-frame-seconds {
                        type yang:counter32;
                        description "Indicates the number of Severely Errored Frame Seconds (SEFS).";
                    }

                    leaf loss-of-signal {
                        type yang:counter32;
                        description "Indicates the number of loss of signal (LOS) occurrences.";
                    }

                    leaf loss-of-clock {
                        type yang:counter32;
                        description "Indicates the number of loss of clock (LOC) occurrences.";
                    }

                    leaf loss-of-frame {
                        type yang:counter32;
                        description "Indicates the number of loss of frame (LOF) occurrences.";
                    }

                    leaf out-of-frame {
                        type yang:counter32;
                        description "Indicates the number of out of frame (OOF) occurrences.";
                    }

                    leaf b1-error {
                        type yang:counter32;
                        description "Indicates the number of B1 errors.";
                    }

                } // container section

            } // container statistics

        } // container sonet-sdh

    } // grouping state-port-sonet-sonet-sdh

}
