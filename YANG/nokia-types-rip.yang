module nokia-types-rip {

    yang-version "1.1";

    namespace "urn:nokia.com:sros:ns:yang:sr:types-rip";

    prefix "types-rip";

    import nokia-sros-yang-extensions     { prefix "sros-ext"; }

    sros-ext:sros-major-release "rel25";
    organization "Nokia";
    contact
        "Nokia SR OS Support
         Web: <http://www.nokia.com>";
    description
        "Common RIP typedefs data types used in the SR OS management system.

         Copyright 2016 Nokia. All rights reserved. Reproduction of this document
         is authorized on the condition that the foregoing copyright notice is included.

         This nokia-types-rip YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    typedef auth-type {
        type enumeration {
            enum none                           { value 1; }
            enum password                       { value 2; }
            enum md5                            { value 3; }
            enum md20                           { value 4; }
        }
        description "The method of authentication used to verify the authenticity of packets.";
    }

    typedef message-size {
        type uint32 {
            range "25..255";
        }
        description "The maximum number of routes that can be sent out per RIP update message.";
    }

    typedef metric {
        type uint32 {
            range "1..16";
        }
        description "Represents the metric.";
    }

    typedef preference {
        type uint32 {
            range "1..255";
        }
        description "Router preference.";
    }

    typedef timer-flush {
        type uint32 {
            range "1..1200";
        }
        units "seconds";
        description "Flush timer.";
    }

    typedef timer-timeout {
        type uint32 {
            range "1..1200";
        }
        units "seconds";
        description "Timeout timer.";
    }

    typedef timer-update {
        type uint32 {
            range "1..600";
        }
        units "seconds";
        description "Update timer.";
    }

    typedef receive {
        type enumeration {
            enum version-1                      { value 1; }
            enum version-2                      { value 2; }
            enum both                           { value 3; }
            enum none                           { value 4; }
        }
        description "Acceptable RIP version on received packets.";
    }

    typedef peer-version {
        type enumeration {
            enum rip-v1                         { value 1; }
            enum rip-v2                         { value 2; }
        }
        description "The RIP version in the header of a packet received from a peer.";
    }

}
