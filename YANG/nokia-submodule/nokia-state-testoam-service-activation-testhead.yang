submodule nokia-state-testoam-service-activation-testhead {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-log                { prefix "types-log"; }
    import nokia-types-oam                { prefix "types-oam"; }
    import nokia-types-sros               { prefix "types-sros"; }

    include nokia-state-eth-cfm;

    sros-ext:sros-major-release "rel25";
    organization "Nokia";
    contact
        "Nokia SR OS Support
         Web: <http://www.nokia.com>";
    description
        "Nokia YANG Data model with operational state for OAM Service Activation Tests (Y.1564) on SR OS based routers.

         Copyright 2016 Nokia. All rights reserved. Reproduction of this document
         is authorized on the condition that the foregoing copyright notice is included.

         This nokia-state-testoam-service-activation-testhead YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-testoam-service-activation-testhead {
        container service-activation-testhead {
            description "Enter the service-activation-testhead context";

            list service-test {
                key "test-name";
                description "Enter the service-test list instance";

                leaf test-name {
                    type types-sros:named-item-64;
                    description "Name of the service-test";
                }

            } // list service-test

            container statistics {
                description "Enter the statistics context";

                list service-test {
                    key "test-name test-run";
                    description "Enter the service-test list instance";

                    leaf test-name {
                        type types-sros:named-item-64;
                        description "Name of the service-test";
                    }

                    leaf test-run {
                        type uint32 {
                            range "1..4294967295";
                        }
                        description "Run number of the service-test run to be read";
                    }

                    leaf description {
                        type types-sros:description;
                        description "Description of the run";
                    }

                    leaf accounting-policy {
                        type types-log:log-policy-id;
                        description "Accounting policy used to record results for the service-test run";
                    }

                    leaf oper-state {
                        type types-oam:sath-statistics-test-run-oper-state;
                        description "Operational state of the service-test run";
                    }

                    leaf accounting-oper-state {
                        type enumeration {
                            enum none                           { value 1; }
                            enum ready-to-send                  { value 2; }
                            enum sent                           { value 3; }
                            enum unable-to-send                 { value 4; }
                        }
                        description
                            "Operational state of the transfer of the service-test run's results
                             to the accounting log";
                    }

                    leaf time-start {
                        type types-oam:sath-test-time-start;
                        description "Start time of the service-test run";
                    }

                    leaf time-end {
                        type types-oam:sath-test-time-end;
                        description "End time of the service-test run";
                    }

                    leaf service-test-completion-notification {
                        type boolean;
                        description "Optional generation of an SNMP trap when the service-test run completes";
                    }

                    leaf stream-run-type {
                        type enumeration {
                            enum sequential                     { value 1; }
                            enum parallel                       { value 2; }
                        }
                        description "Run ordering for the service-test runs owned by the service-test's service streams";
                    }

                    container test-duration {
                        description "Enter the test-duration context";

                        container cir {
                            description "Enter the cir context";

                            leaf minutes-seconds {
                                type types-oam:sath-mm-ss-string;
                                description "Duration of CIR tests owned by the service test";
                            }

                        } // container cir

                        container cir-pir {
                            description "Enter the cir-pir context";

                            leaf minutes-seconds {
                                type types-oam:sath-mm-ss-string;
                                description "Duration of CIR-PIR tests owned by the service test";
                            }

                        } // container cir-pir

                        container policing {
                            description "Enter the policing context";

                            leaf minutes-seconds {
                                type types-oam:sath-mm-ss-string;
                                description "Duration of policing tests owned by the service test";
                            }

                        } // container policing

                        container performance {
                            description "Enter the performance context";

                            leaf hours-minutes-seconds {
                                type types-oam:sath-hh-mm-ss-string;
                                description "Duration of performance tests owned by the service test";
                            }

                        } // container performance

                    } // container test-duration

                    list service-stream {
                        key "stream-id";
                        description "Enter the service-stream list instance";

                        leaf stream-id {
                            type uint32 {
                                range "1..8";
                            }
                            description "Number of the service-stream to be read";
                        }

                        leaf description {
                            type types-sros:description;
                            description "Description of the run";
                        }

                        leaf oper-state {
                            type types-oam:sath-statistics-test-run-oper-state;
                            description "Operational state of the service-stream run";
                        }

                        leaf sap {
                            type string {
                                length "0..32";
                            }
                            description
                                "Service Access Point (SAP) which hosts the Eth-CFM MEP, Domain, and
                                 Association for the service-stream run";
                        }

                        leaf router-instance {
                            type types-sros:named-item-or-empty;
                            description
                                "Router which hosts the Eth-CFM MEP, Domain, and
                                 Association for the service-stream run";
                        }

                        leaf router-interface {
                            type types-sros:named-item-or-empty;
                            description
                                "Router interface which hosts the Eth-CFM MEP, Domain, and
                                 Association for the service-stream run";
                        }

                        leaf source-port {
                            type types-sros:named-item-or-empty;
                            description
                                "Port which hosts the Eth-CFM MEP, Domain, and
                                 Association for the service-stream run";
                        }

                        leaf src-mac {
                            type yang:mac-address;
                            description
                                "Source MAC address for the service-stream run

                                 00:00:00:00:00:00 is returned if a source MAC address is not available";
                        }

                        leaf acceptance-criteria-template {
                            type types-sros:named-item-64;
                            description "Acceptance criteria template for the service-stream run";
                        }

                        leaf rate-cir {
                            type uint32 {
                                range "0..400000000";
                            }
                            units "kilobps";
                            description "CIR transmit rate for the service-stream run";
                        }

                        leaf rate-pir {
                            type uint32 {
                                range "0..400000000";
                            }
                            units "kilobps";
                            description "PIR transmit rate for the service-stream run";
                        }

                        leaf service-stream-completion-notification {
                            type boolean;
                            description "Optional generation of an SNMP trap when the service-stream run completes";
                        }

                        leaf size-a {
                            type uint32 {
                                range "64..9212";
                            }
                            units "bytes";
                            description "Y.1564 'size a' for the service-stream run";
                        }

                        leaf size-b {
                            type uint32 {
                                range "64..9212";
                            }
                            units "bytes";
                            description "Y.1564 'size b' for the service-stream run";
                        }

                        leaf size-c {
                            type uint32 {
                                range "64..9212";
                            }
                            units "bytes";
                            description "Y.1564 'size c' for the service-stream run";
                        }

                        leaf size-d {
                            type uint32 {
                                range "64..9212";
                            }
                            units "bytes";
                            description "Y.1564 'size d' for the service-stream run";
                        }

                        leaf size-e {
                            type uint32 {
                                range "64..9212";
                            }
                            units "bytes";
                            description "Y.1564 'size e' for the service-stream run";
                        }

                        leaf size-f {
                            type uint32 {
                                range "64..9212";
                            }
                            units "bytes";
                            description "Y.1564 'size f' for the service-stream run";
                        }

                        leaf size-g {
                            type uint32 {
                                range "64..9212";
                            }
                            units "bytes";
                            description "Y.1564 'size g' for the service-stream run";
                        }

                        leaf size-h {
                            type uint32 {
                                range "64..9212";
                            }
                            units "bytes";
                            description "Y.1564 'size h' for the service-stream run";
                        }

                        leaf size-u {
                            type uint32 {
                                range "64..9212";
                            }
                            units "bytes";
                            description "Y.1564 'size u' for the service-stream run";
                        }

                        leaf cir-threshold {
                            type uint32 {
                                range "0..400000000";
                            }
                            units "kilobps";
                            description "Acceptance criteria template's CIR threshold for the service-stream run";
                        }

                        leaf pir-threshold {
                            type uint32 {
                                range "0..400000000";
                            }
                            units "kilobps";
                            description "Acceptance criteria template's PIR threshold for the service-stream run";
                        }

                        leaf loss-threshold {
                            type types-oam:sath-loss-percent-union;
                            description "Acceptance criteria template's loss threshold for the service-stream run";
                        }

                        leaf loss-threshold-policing {
                            type types-oam:sath-loss-percent-union;
                            description "Acceptance criteria template's policing loss threshold for the service-stream run";
                        }

                        leaf delay-threshold {
                            type uint32 {
                                range "0..100000000";
                            }
                            units "microseconds";
                            description "Acceptance criteria template's delay threshold for the service-stream run";
                        }

                        leaf delay-var-threshold {
                            type uint32 {
                                range "0..100000000";
                            }
                            units "microseconds";
                            description "Acceptance criteria template's delay variation threshold for the service-stream run";
                        }

                        leaf m-factor {
                            type uint32 {
                                range "0..400000000";
                            }
                            units "kilobps";
                            description "Acceptance criteria template's throughput margin for the service-stream run";
                        }

                        container frame-mix {
                            description "Enter the frame-mix context";

                            leaf frame-size-template {
                                type types-sros:named-item-64;
                                description "Frame size template for the service-stream run";
                            }

                            leaf sequence {
                                type string {
                                    length "1..16";
                                }
                                description "Sequence of frame sizes for the service-stream run";
                            }

                        } // container frame-mix

                        container test-types {
                            description "Enter the test-types context";

                            leaf cir {
                                type boolean;
                                description "Committed Information Rate (CIR) test requested for the service-stream run";
                            }

                            leaf cir-pir {
                                type boolean;
                                description "CIR-PIR test requested for the service-stream run";
                            }

                            leaf policing {
                                type boolean;
                                description "Policing test requested for the service-stream run";
                            }

                            leaf performance {
                                type boolean;
                                description "Performance test requested for the service-stream run";
                            }

                        } // container test-types

                        container frame-payload {
                            description "Enter the frame-payload context";

                            container data-pattern {
                                description "Enter the data-pattern context";

                                leaf repeat {
                                    type types-sros:hex-string-or-uint;
                                    description "Repeated padding bytes for frames launched for the service-stream run";
                                }

                            } // container data-pattern

                            container ethernet {
                                description "Enter the ethernet context";

                                leaf dst-mac {
                                    type types-sros:mac-unicast-address-no-zero;
                                    description
                                        "Destination MAC address of the Ethernet frames launched for
                                         the service-stream run";
                                }

                                container eth-cfm {
                                    description "Enter the eth-cfm context";

                                    container source {
                                        description "Enter the source context";

                                        leaf mep-id {
                                            type types-eth-cfm:mep-id-type;
                                            description "Source Ethernet Maintenance association End Point (MEP) identifier";
                                        }

                                        leaf md-admin-name {
                                            type leafref {
                                                path "../../../../../../../../../../eth-cfm/domain/md-admin-name";
                                            }
                                            description "Source Ethernet Maintenance Domain (MD) name";
                                        }

                                        leaf ma-admin-name {
                                            type leafref {
                                                path "../../../../../../../../../../eth-cfm/domain[md-admin-name=current()/../md-admin-name]/association/ma-admin-name";
                                            }
                                            description "Source Ethernet Maintenance Association (MA) name";
                                        }

                                    } // container source

                                } // container eth-cfm

                                container s-tag {
                                    description "Enter the s-tag context";

                                    leaf dot1p {
                                        type uint32 {
                                            range "0..7";
                                        }
                                        description
                                            "Priority Code Point (PCP) of the Ethernet frames launched for the
                                             service-stream run";
                                    }

                                    leaf discard-eligible {
                                        type boolean;
                                        description
                                            "Discard Eligibility Indicator (DEI) of the Ethernet frames launched
                                             for the service-stream run";
                                    }

                                } // container s-tag

                                container c-tag {
                                    description "Enter the c-tag context";

                                    leaf dot1p {
                                        type uint32 {
                                            range "0..7";
                                        }
                                        description
                                            "Priority Code Point (PCP) of the Ethernet frames launched for the
                                             service-stream run";
                                    }

                                    leaf discard-eligible {
                                        type boolean;
                                        description
                                            "Discard Eligibility Indicator (DEI) of the Ethernet frames launched
                                             for the service-stream run";
                                    }

                                } // container c-tag

                            } // container ethernet

                        } // container frame-payload

                        list test-results {
                            key "test-type";
                            description "Enter the test-results list instance";

                            leaf test-type {
                                type enumeration {
                                    enum cir                            { value 1; }
                                    enum cir-pir                        { value 2; }
                                    enum policing                       { value 3; }
                                    enum performance                    { value 4; }
                                }
                                description "Test type to be read";
                            }

                            leaf oper-state {
                                type types-oam:sath-statistics-test-run-oper-state;
                                description "Operational state of the test run";
                            }

                            leaf time-start {
                                type types-oam:sath-test-time-start;
                                description "Start time of the test run";
                            }

                            leaf time-end {
                                type types-oam:sath-test-time-end;
                                description "End time of the test run";
                            }

                            leaf time-left {
                                type uint32;
                                units "seconds";
                                description "Execution time remaining for the test run";
                            }

                            leaf oper-status-throughput {
                                type types-oam:sath-statistics-test-oper-state;
                                description
                                    "Test run's operational status, with respect to the throughput
                                     acceptance criteria";
                            }

                            leaf oper-status-frame-loss-ratio {
                                type types-oam:sath-statistics-test-oper-state;
                                description
                                    "Test run's operational status, with respect to the FLR acceptance
                                     criteria";
                            }

                            leaf oper-status-delay {
                                type types-oam:sath-statistics-test-oper-state;
                                description
                                    "Test run's operational status, with respect to the delay acceptance
                                     criteria";
                            }

                            leaf oper-status-delay-var {
                                type types-oam:sath-statistics-test-oper-state;
                                description
                                    "Test run's operational status, with respect to the delay variation
                                     acceptance criteria";
                            }

                            leaf measured-delay-min {
                                type int32;
                                units "microseconds";
                                description "Minimum delay measured for the service-stream run";
                            }

                            leaf measured-delay-max {
                                type int32;
                                units "microseconds";
                                description "Maximum delay measured for the service-stream run";
                            }

                            leaf measured-delay-avg {
                                type int32;
                                units "microseconds";
                                description "Average delay measured for the service-stream run";
                            }

                            leaf measured-delay-var-min {
                                type int32;
                                units "microseconds";
                                description "Minimum delay variation measured for the service-stream run";
                            }

                            leaf measured-delay-var-max {
                                type int32;
                                units "microseconds";
                                description "Maximum delay variation measured for the service-stream run";
                            }

                            leaf measured-delay-var-avg {
                                type int32;
                                units "microseconds";
                                description "Average delay variation measured for the service-stream run";
                            }

                            leaf measured-throughput {
                                type uint32;
                                units "kilobps";
                                description "Throughput measured for the service-stream run";
                            }

                            leaf measured-frame-loss-ratio {
                                type types-oam:sath-loss-percent-decimal64;
                                units "percent";
                                description "FLR measured for the service-stream run";
                            }

                            leaf measured-frame-tx {
                                type yang:counter64;
                                units "frames";
                                description "Number of frames transmitted during the service-stream run";
                            }

                            leaf measured-frame-rx {
                                type yang:counter64;
                                units "frames";
                                description "Number of frames received during the service-stream run";
                            }

                        } // list test-results

                    } // list service-stream

                } // list service-test

            } // container statistics

        } // container service-activation-testhead

    } // grouping state-testoam-service-activation-testhead

}
