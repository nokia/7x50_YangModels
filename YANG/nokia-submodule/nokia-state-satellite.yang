submodule nokia-state-satellite {

    yang-version "1.1";

    belongs-to nokia-state { prefix "state"; }

    import ietf-yang-types                { prefix "yang"; }
    import nokia-sros-yang-extensions     { prefix "sros-ext"; }
    import nokia-types-chassis            { prefix "types-chassis"; }
    import nokia-types-sros               { prefix "types-sros"; }
    import nokia-types-system             { prefix "types-system"; }

    sros-ext:sros-major-release "rel26";
    organization "Nokia";
    contact
        "Nokia SR OS Support
         Web: <http://www.nokia.com>";
    description
        "Nokia YANG Data model with operational state for satellite parameters on SR OS based routers.

         Copyright 2016 Nokia. All rights reserved. Reproduction of this document
         is authorized on the condition that the foregoing copyright notice is included.

         This nokia-state-satellite YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping state-satellite {
        container satellite {
            description "Enter the satellite context";

            list ethernet-satellite {
                key "satellite-id";
                description "Enter the ethernet-satellite list instance";

                leaf satellite-id {
                    type types-chassis:sat-id;
                    description "The unique index identifying this satellite";
                }

                leaf console-access-status {
                    type enumeration {
                        enum disabled                       { value 1; }
                        enum requested                      { value 2; }
                        enum enabled                        { value 3; }
                        enum not-applicable                 { value 4; }
                    }
                    description "The status of console access for this satellite.";
                }


                container central-frequency-clock {
                    description "Enter the central-frequency-clock context";

                    leaf ql-selection {
                        type boolean;
                        description "Reference selection based on quality level";
                    }

                    leaf clock-state {
                        type types-system:sets-clock-state;
                        description "Indicates the present status of the synchronous timing equipment subsystem (SETS)";
                    }

                    leaf quality-level {
                        type types-system:ssm-quality-level;
                        description "The QL of the system timing reference";
                    }

                    leaf current-frequency-offset {
                        type int32;
                        units "parts per million";
                        description "Current PLL frequency offset";
                    }

                    leaf operating-mode {
                        type enumeration {
                            enum automatic                      { value 0; }
                            enum manual                         { value 1; }
                        }
                        description "Indicates control of the central-frequency-clock configuration";
                    }

                    leaf selector-b {
                        type enumeration {
                            enum reference1 {
                                value 1;
                                description "line reference 1";
                            }
                            enum reference2 {
                                value 2;
                                description "line reference 2";
                            }
                            enum no-reference {
                                value 6;
                                description "Currently no input selected";
                            }
                        }
                        description "Setting for selector b (input to SETG)";
                    }

                    container reference-1 {
                        description "Enter the reference-1 context";

                        leaf input-state {
                            type types-system:reference-input-state;
                            description "State of this input";
                        }

                        leaf-list alarms {
                            type types-system:reference-input-alarm;
                            description "Active alarms for this input";
                        }

                        leaf qualified-for-use {
                            type boolean;
                            description "Indicates the input is qualified for use";
                        }

                        leaf selected-for-use {
                            type boolean;
                            description "Indicates the input is selected for use";
                        }

                        leaf rx-quality-level {
                            type types-system:ssm-quality-level;
                            description "Received QL for this input";
                        }

                        leaf control-state {
                            type types-sros:enabled-disabled;
                            description "Reflects the state of this timing reference with respect to its use in reference selection.";
                        }

                        leaf source-port {
                            type types-sros:port;
                            description "Source port for this timing reference within the satellite.";
                        }

                    } // container reference-1

                    container reference-2 {
                        description "Enter the reference-2 context";

                        leaf input-state {
                            type types-system:reference-input-state;
                            description "State of this input";
                        }

                        leaf-list alarms {
                            type types-system:reference-input-alarm;
                            description "Active alarms for this input";
                        }

                        leaf qualified-for-use {
                            type boolean;
                            description "Indicates the input is qualified for use";
                        }

                        leaf selected-for-use {
                            type boolean;
                            description "Indicates the input is selected for use";
                        }

                        leaf rx-quality-level {
                            type types-system:ssm-quality-level;
                            description "Received QL for this input";
                        }

                        leaf control-state {
                            type types-sros:enabled-disabled;
                            description "Reflects the state of this timing reference with respect to its use in reference selection.";
                        }

                        leaf source-port {
                            type types-sros:port;
                            description "Source port for this timing reference within the satellite.";
                        }

                    } // container reference-2

                } // container central-frequency-clock


                list event {
                    key "type";
                    description "Enter the event list instance";

                    leaf type {
                        type enumeration {
                            enum soft-error                     { value 1; }
                        }
                        description "The unique value which identifies the satellite event type to be monitored.";
                    }

                    leaf occurrences {
                        type yang:counter64;
                        description "Indicates the number of times this event has been detected.";
                    }

                    leaf last-occurrence {
                        type yang:date-and-time;
                        description "Indicates the timestamp of the last time the event was detected.";
                    }

                } // list event

            } // list ethernet-satellite

        } // container satellite

    } // grouping state-satellite

}
