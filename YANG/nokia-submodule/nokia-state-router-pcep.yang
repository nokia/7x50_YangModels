submodule nokia-state-router-pcep {

    yang-version "1.1";

    belongs-to nokia-state { prefix "state"; }

    import ietf-yang-types                { prefix "yang"; }
    import nokia-sros-yang-extensions     { prefix "sros-ext"; }
    import nokia-types-router             { prefix "types-router"; }
    import nokia-types-sros               { prefix "types-sros"; }

    sros-ext:sros-major-release "rel26";
    organization "Nokia";
    contact
        "Nokia SR OS Support
         Web: <http://www.nokia.com>";
    description
        "Nokia YANG Data model with operational state for pcep protocol on SR OS based routers.

         Copyright 2016 Nokia. All rights reserved. Reproduction of this document
         is authorized on the condition that the foregoing copyright notice is included.

         This nokia-state-router-pcep YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-router-pcep {
        container pcep {
            description "Enter the pcep context";

            container pcc {
                description "Enter the pcc context";

                leaf-list capabilities {
                    type types-router:pcep-capabilities;
                    description "This value specifies the capabilities supported by this PCEP";
                }

                leaf oper-state {
                    type enumeration {
                        enum up                             { value 1; }
                        enum down                           { value 2; }
                        enum going-up                       { value 3; }
                        enum going-down                     { value 4; }
                        enum failed                         { value 5; }
                        enum failed-perm                    { value 6; }
                    }
                    description
                        "The value indicates the operational status of this PCEP:
                         up        (1) - the PCEP entity is active.
                         down      (2) - the PCEP entity is inactive.
                         going-up   (3) - the PCEP entity is activating.
                         going-down (4) - the PCEP entity is deactivating.
                         failed   (5) - the PCEP entity has failed and will
                         recover when possible.
                         failed-perm   (6) - the PCEP entity has failed and
                         will not recover without operator intervention.";
                }

                leaf open-wait-timer {
                    type uint32 {
                        range "1..65535";
                    }
                    units "seconds";
                    description
                        "The time that the PCEP entity will wait to receive an Open
                         message from a peer after the TCP connection has come up.
                         If no Open message is received within this time, then PCEP
                         terminates the TCP connection.";
                }

                leaf keep-wait-timer {
                    type uint32 {
                        range "1..65535";
                    }
                    units "seconds";
                    description
                        "The time that the PCEP entity will wait to receive a
                         Keepalive or PCErr message from a peer during session
                         initialization after receiving an Open message.  If no
                         Keepalive or PCErr message is received within this time,
                         then PCEP terminates the TCP connection.";
                }

                leaf sync-timer {
                    type uint32 {
                        range "1..65535";
                    }
                    units "seconds";
                    description
                        "The value is used in the case of a synchronized
                         path computation request using the SVEC object.";
                }

                leaf request-timer {
                    type uint32 {
                        range "1..65535";
                    }
                    units "seconds";
                    description
                        "The maximum time that the PCEP entity will wait for a
                         response to a PCReq message.";
                }

                leaf connect-timer {
                    type uint32 {
                        range "1..65535";
                    }
                    units "seconds";
                    description
                        "The time that the PCEP entity will wait to establish a TCP
                         connection with a peer.  If a TCP connection is not
                         established within this time, then PCEP aborts the session
                         setup attempt.";
                }

                leaf allow-negotiation {
                    type boolean;
                    description
                        "Whether the PCEP entity will permit negotiation of session
                         parameters.";
                }

                leaf max-sessions {
                    type uint32;
                    description
                        "The maximum number of sessions involving this PCEP entity
                         that can exist at any time.";
                }

                leaf max-unknown-reqs {
                    type uint32;
                    description
                        "The maximum number of unrecognized requests and replies that
                         any session on this PCEP entity is willing to accept per
                         minute before terminating the session.";
                }

                leaf oper-local-address {
                    type types-sros:ipv4-unicast-address;
                    description "The value indicates the internet address being used by this PCEP PCC.";
                }

                leaf oper-local-address-ipv6 {
                    type types-sros:ipv6-unicast-address;
                    description "The value indicates the internet Ipv6 ss being used by this PCEP PCC.";
                }


                list peer {
                    key "ip-address";
                    description "Enter the peer list instance";

                    leaf ip-address {
                        type types-sros:ip-unicast-address;
                        description "This value specifies the address of the PCE peer";
                    }

                    leaf oper-state {
                        type types-sros:oper-state;
                        description "Operational state.";
                    }

                    leaf speaker-id {
                        type string {
                            length "0..48";
                        }
                        description
                            "The value indicates a unique speaker identifier for the peer
                             that does change during lifetime of the speaker";
                    }

                    leaf-list capabilities {
                        type types-router:pcep-capabilities;
                        description "This value specifies the capabilities supported by this peer";
                    }

                    leaf sync-state {
                        type types-router:pcep-sync-state;
                        description "The value of indicates the synchronization state of this peer.";
                    }

                    leaf sess-establish-time {
                        type yang:date-and-time;
                        description
                            "The value indicates the time at which the session with the peer moved
                             to the established state";
                    }

                    leaf oper-keepalive {
                        type uint32;
                        units "seconds";
                        description
                            "The value indicates the operational value of keep alive interval in
                             use by this entity's peer.This is the maximum time between two
                             consecutive messages sent to a peer";
                    }

                    leaf oper-dead-timer {
                        type uint32;
                        units "seconds";
                        description
                            "The value indicates the operational value of dead timer interval in
                             use by this peer.This is the time after which a peer should declare
                             a session down if it is does not receive any PCEP messages";
                    }

                    leaf is-overloaded {
                        type boolean;
                        description
                            "The value indicates whether this peer is overloaded with the processing
                             of existing requests and is unable to handle new requests leading
                             to unacceptable response times";
                    }

                    container statistics {
                        description "Enter the statistics context";

                        leaf num-pcrpt-sent {
                            type yang:counter32;
                            description "The value indicates the number of PCRpt messages sent to this peer.";
                        }

                        leaf num-pcrpt-rcvd {
                            type yang:counter32;
                            description "The value indicates the number of PCRpt messages received from this peer";
                        }

                        leaf num-pcupd-sent {
                            type yang:counter32;
                            description "The value indicates the number of PCUpd messages sent to this peer.";
                        }

                        leaf num-pcupd-rcvd {
                            type yang:counter32;
                            description "The value indicates the number of PCUpd messages received from this peer";
                        }

                        leaf num-rpt-sent {
                            type yang:counter32;
                            description
                                "The value indicates the number of report messages sent to this peer.
                                 This might be greater that num-pcrpt-sent because multiple
                                 requests can be batched into a single PCRpt messages.";
                        }

                        leaf num-rpt-rcvd {
                            type yang:counter32;
                            description
                                "The value indicates the number pf report messages received from
                                 this peer.This might be greater that num-pcrpt-rcvd because
                                 multiple requests can be batched into a single PCRpt message.";
                        }

                        leaf num-pcreq-sent {
                            type yang:counter32;
                            description "The number of PCReq messages sent to this peer";
                        }

                        leaf num-pcreq-rcvd {
                            type yang:counter32;
                            description "The number of PCReq messages received from this peer";
                        }

                        leaf num-pcrep-sent {
                            type yang:counter32;
                            description "The number of PCRep messages sent to this peer";
                        }

                        leaf num-pcrep-rcvd {
                            type yang:counter32;
                            description "The number of PCRep messages received from this peer";
                        }

                        leaf num-pcerr-sent {
                            type yang:counter32;
                            description "The number of PCErr messages sent to this peer";
                        }

                        leaf num-pcerr-rcvd {
                            type yang:counter32;
                            description "The number of PCErr messages received from this peer";
                        }

                        leaf num-pcntf-sent {
                            type yang:counter32;
                            description "The number of PCNtf messages sent to this peer";
                        }

                        leaf num-pcntf-rcvd {
                            type yang:counter32;
                            description "The number of PCNtf messages received from this peer";
                        }

                        leaf num-keepalive-sent {
                            type yang:counter32;
                            description "The number of Keepalive messages sent to this peer";
                        }

                        leaf num-keepalive-rcvd {
                            type yang:counter32;
                            description "The number of Keepalive messages received from this peer";
                        }

                        leaf num-req-rcvd {
                            type yang:counter32;
                            description
                                "The number of requests received from this peer.  A request
                                 corresponds 1:1 with an RP object in a PCReq message";
                        }

                        leaf num-sess-setup-ok {
                            type yang:counter32;
                            description
                                "The number of PCEP sessions successfully established with
                                 the peer, including any current session.  This counter is
                                 incremented each time a session with this peer is
                                 successfully established";
                        }

                        leaf num-sess-setup-fail {
                            type yang:counter32;
                            description
                                "The number of PCEP sessions with the peer that have been
                                 attempted but failed before being fully established.
                                 This counter is incremented each time a session retry to
                                 this peer fails";
                        }

                        leaf num-pcinit-sent {
                            type yang:counter32;
                            description "The number of PC initiated messages sent to this peer.";
                        }

                        leaf num-pcinit-rcvd {
                            type yang:counter32;
                            description "The number of PC initiated messages received from this peer.";
                        }

                        leaf num-req-sent {
                            type yang:counter32;
                            description
                                "The number of requests sent to this peer.  A request
                                 corresponds 1:1 with an RP object in a PCReq message";
                        }

                    } // container statistics

                } // list peer

                list lsp-update {
                    key "pce-id";
                    description "Enter the lsp-update list instance";

                    leaf pce-id {
                        type types-router:pce-id;
                        description "The value indicates the unique identifier for PCE.";
                    }

                    leaf lsp-id {
                        type uint32;
                        description "The value indicates the unique identifier for LSP.";
                    }

                    leaf lsp-type {
                        type types-router:pcep-lsp-type;
                        description "The value indicates the type of LSP connection.";
                    }

                    leaf tunnel-id {
                        type uint32 {
                            range "1..65535";
                        }
                        description
                            "The value indicates the unique tunnel identifier that remains constant over
                             the life time of a tunnel";
                    }

                    leaf ext-tunnel-id {
                        type types-sros:ip-address;
                        description "The value indicates the extended tunnel identifier.";
                    }

                    leaf name {
                        type types-sros:named-item-64;
                        description
                            "The value indicates the LSP path name that is unique in the PCC and remains
                             constant throughout a path's life time.";
                    }

                    leaf sender-address {
                        type types-sros:ip-address;
                        description "The value indicates the sender node's address.";
                    }

                    leaf source-address {
                        type types-sros:ip-address;
                        description "The value indicates the sender address of the LSP.";
                    }

                    leaf destination-address {
                        type types-sros:ip-address;
                        description "The value indicates the destination address of the LSP.";
                    }

                    leaf delegated {
                        type boolean;
                        description "The value indicates whether the PCC is delegating the LSP to the PCE";
                    }

                    leaf delegated-peer-address {
                        type types-sros:ip-address;
                        description
                            "The value indicates the peer address to which the PCC has delegated the
                             LSP";
                    }

                    leaf oper-state {
                        type enumeration {
                            enum down                           { value 0; }
                            enum up                             { value 1; }
                            enum active                         { value 2; }
                            enum going-down                     { value 3; }
                            enum going-up                       { value 4; }
                        }
                        description
                            "The value indicates the operational status of the LSP:
                             down      (0) - LSP is not active.
                             up        (1) - LSP has been signaled.
                             active    (2) - LSP is up and carrying traffic.
                             going-down (3) - LSP is being torn down, resources are being
                             released.
                             going-up   (4) - LSP is being signaled.";
                    }

                    leaf error {
                        type enumeration {
                            enum not-applicable                 { value 0; }
                            enum unknown-reason                 { value 1; }
                            enum limit-rchd-for-pce-lsp         { value 2; }
                            enum many-pending-lsp-update        { value 3; }
                            enum unacceptable-parameters        { value 4; }
                            enum internal-error                 { value 5; }
                            enum lsp-admin-down                 { value 6; }
                            enum lsp-preempted                  { value 7; }
                            enum rsvp-signaling-error           { value 8; }
                        }
                        description
                            "The value indicates the error information containing the reason
                             for LSP update failure :
                             not-applicable         (0) - Not Applicable.
                             unknown-reason         (1) - Unknown reason.
                             limit-rchd-for-pce-lsp    (2) - Limit reached for PCE-controlled LSPs.
                             many-pending-lsp-update  (3) - Too many pending LSP update requests.
                             unacceptable-parameters(4) - Unacceptable parameters.
                             internal-error         (5) - Internal error.
                             lsp-admin-down          (6) - LSP administratively brought down.
                             lsp-preempted          (7) - LSP preempted.
                             rsvp-signaling-error    (8) - RSVP signaling error.";
                    }

                    leaf state {
                        type enumeration {
                            enum not-applicable                 { value 0; }
                            enum mbb-in-progress                { value 1; }
                            enum mbb-fail                       { value 2; }
                            enum mbb-success                    { value 3; }
                            enum update-delegation              { value 4; }
                            enum lsp-down                       { value 5; }
                        }
                        description
                            "The value indicates the state of LSP
                             not-applicable    (0) - Make-Before-Break (MBB) is not-applicable
                             or is not in progress.
                             mbb-in-progress   (1) - MBB procedure is in progress.
                             mbb-fail          (2) - MBB procedure failed.
                             mbb-success       (3) - MBB procedure succeeded.
                             update-delegation (4) - delegation update is being processed.
                             lsp-down          (5) - LSP down update is being processed.";
                    }

                } // list lsp-update

                list path-request {
                    key "request-id";
                    description "Enter the path-request list instance";

                    leaf request-id {
                        type uint32 {
                            range "1..max";
                        }
                        description
                            "The value specifies the unique path computation request identifier
                             represented in PCReq message";
                    }

                    leaf lsp-type {
                        type types-router:pcep-lsp-type;
                        description "The value indicates the type of LSP connection.";
                    }

                    leaf tunnel-id {
                        type uint32;
                        description
                            "The value indicates the unique tunnel identifier that remains
                             constant  over the life time of a tunnel.";
                    }

                    leaf lsp-id {
                        type uint32;
                        description "The value indicates the unique identifier for LSP";
                    }

                    leaf ext-tunnel-id {
                        type types-sros:ip-address;
                        description "The value indicates the extended tunnel identifier";
                    }

                    leaf lsp-name {
                        type types-sros:named-item-64;
                        description
                            "The value indicates the LSP path name that is unique in the PCC and remains
                             constant throughout a path's life time.";
                    }

                    leaf source-address {
                        type types-sros:ip-address;
                        description
                            "The value indicates the source address of the path for which path computation
                             is requested. It is the END-POINTS object used in PCReq message.";
                    }

                    leaf destination-address {
                        type types-sros:ip-address;
                        description
                            "The value indicates the destination address of the path for which the path
                             computation is requested. It is the END-POINTS object used in PCReq message.";
                    }

                    leaf msg-state {
                        type enumeration {
                            enum unknown                        { value 0; }
                            enum request-parameter              { value 1; }
                            enum sent-for-compute               { value 2; }
                            enum error-received                 { value 3; }
                            enum notify-received                { value 4; }
                            enum cancel                         { value 5; }
                            enum compute-received               { value 6; }
                        }
                        description
                            "The value indicates the state of PCReq message:
                             unknown             (0) - The state of PCReq message is unknown.
                             request-parameter   (1) - Request Parameter (RP) object is included in
                                                       the PCReq message.
                             sent-for-compute    (2) - PCReq message has been sent for path
                                                       computation.
                             error-received      (3) - Path Computation Error (PCErr) message is
                                                       received by the PCC.
                             notify-received     (4) - Path Computation Notification (PCNtf)
                                                       message is received by the PCC.
                             cancel              (5) - PCReq message has been cancelled.
                             compute-received    (6) - Path computation is received by the PCC.";
                    }

                    leaf sync-vector-id {
                        type yang:counter64;
                        description
                            "The value indicates the Synchronization Vector (svec) identifier for
                             Synchronized Dependent Path Computations.";
                    }

                    leaf igp-metric {
                        type uint32;
                        description
                            "The value indicates Interior Gateway Protocol (IGP) metric that must be
                             optimized by the path computation algorithm for providing the cost of
                             computed path. It is the METRIC object used in PCReq message.";
                    }

                    leaf te-metric {
                        type uint32;
                        description
                            "The value indicates Traffic Engineering (TE) metric that must be optimized
                             by the path computation algorithm for providing the cost of computed path.
                             It is the METRIC object used in PCReq messages.";
                    }

                    leaf delay-metric {
                        type uint32;
                        description
                            "The value indicates Delay metric that must be optimized
                             by the path computation algorithm for providing the cost of computed path.
                             It is the METRIC object used in PCReq messages.";
                    }

                    leaf hop-count {
                        type uint32;
                        description
                            "The value indicates the number of hops that traversed.It is the METRIC
                             object in PCReq message.";
                    }

                    leaf-list metric-bound {
                        type types-router:metric-value;
                        description
                            "The value indicates  whether the
                             metric-value specifies a bound (a maximum) for the path metric that
                             must not be exceeded for the PCC to consider the computed path
                             as acceptable. It is the METRIC object used in PCReq message.";
                    }

                    leaf-list metric-compute {
                        type types-router:metric-value;
                        description
                            "The value indicates whether PCE must provide the computed path metric value
                             in Path Computation Response (PCRep) message for the corresponding metric.
                             It is the METRIC object used in PCReq message.";
                    }

                    leaf local-prot-desired {
                        type boolean;
                        description
                            "The value indicates whether local protection is desired or not.It is the
                             LSPA (LSP Attribute) object used in PCReq message.

                             When the value of this object is set to 'true', it indicates that
                             the computed path must include links protected with Fast Reroute as
                             defined in the maximum number of hops to be transversed that must not
                             be exceeded to consider computed path as acceptable.";
                    }

                    leaf setup-priority {
                        type uint32 {
                            range "0..7";
                        }
                        description
                            "The value indicates the priority of the TE LSP with respect to holding resource.
                             The value of 0 represents highest priority. The holding priority indicates
                             whether this session can be in PCReq message.";
                    }

                    leaf holding-priority {
                        type uint32 {
                            range "0..7";
                        }
                        description
                            "The value indicates the priority of the TE LSP with respect to
                             holding resources. The value of 0 represents highest priority.The holding
                             priority indicates whether this session can be preempted by another session.
                             It is the LSPA object used in PCReq message.";
                    }

                    leaf exclude-any {
                        type uint32;
                        description
                            " This value indicates a set of attributes filters associated with a tunnel
                             any of which renders a link unacceptable. It is the LSPA object used
                             in PCReq message.";
                    }

                    leaf include-any {
                        type uint32;
                        description
                            "The value indicates a set of attribute
                             filters associated with a tunnel any of which renders a link
                             acceptable. It is the LSPA object used in PCReq message.";
                    }

                    leaf include-all {
                        type uint32;
                        description
                            " The value indicates a set of attribute
                             filters associated with a tunnel all of which much be present for a
                             link to be acceptable. It is the LSPA object used in PCReq message.";
                    }

                    leaf msg-priority {
                        type uint32;
                        description
                            " The value indicates the priority of the PCReq message.It is RP object used
                             in PCReq message.";
                    }

                    leaf reoptimization {
                        type boolean;
                        description
                            "This value indicates whether the PCReq message relates to the reoptimization of
                             an existing TE LSP. It is the RP object used in PCReq message.";
                    }

                    leaf strict-loose {
                        type boolean;
                        description
                            "The value indicates whether the path is strict or loose. It is the RP object
                             used in PCReq message.

                             When the value of this object is set to 'true', it indicates that
                             a loose path is acceptable.

                             When the value of this object is set to 'false', it indicates that
                             a path exclusively made of strict hops is required.";
                    }

                    leaf bidirectional {
                        type boolean;
                        description
                            "The value indicates whether the PCReq message relates to a bi-directional TE
                             LSP that has the same traffic engineering requirements including fate sharing,
                             protection and restoration, LSRs, TE links, and resource requirements
                             (e.g., latency and jitter) in each direction. It is the RP object used
                             in PCReq message.";
                    }

                    leaf lsp-bandwidth {
                        type uint32;
                        units "megabps";
                        description "The value indicates the bandwidth that is being requested by the LSP.";
                    }

                    leaf max-lsr-labels {
                        type uint32 {
                            range "1..10";
                        }
                        description "The value indicates maximum segment routing label stack size for this LSP.";
                    }

                    leaf-list profiles {
                        type uint32;
                        description "The value indicates the path profile identifier";
                    }

                    leaf-list extended-profiles {
                        type uint32;
                        description
                            "The value indicates the extended identifier associated
                             with the path profile identifier.";
                    }

                } // list path-request

            } // container pcc

            container pce {
                description "Enter the pce context";

                leaf-list capabilities {
                    type types-router:pcep-capabilities;
                    description "This value specifies the capabilities supported by this PCEP";
                }

                leaf oper-state {
                    type enumeration {
                        enum up                             { value 1; }
                        enum down                           { value 2; }
                        enum going-up                       { value 3; }
                        enum going-down                     { value 4; }
                        enum failed                         { value 5; }
                        enum failed-perm                    { value 6; }
                    }
                    description
                        "The value indicates the operational status of this PCEP:
                         up        (1) - the PCEP entity is active.
                         down      (2) - the PCEP entity is inactive.
                         going-up   (3) - the PCEP entity is activating.
                         going-down (4) - the PCEP entity is deactivating.
                         failed   (5) - the PCEP entity has failed and will
                         recover when possible.
                         failed-perm   (6) - the PCEP entity has failed and
                         will not recover without operator intervention.";
                }

                leaf open-wait-timer {
                    type uint32 {
                        range "1..65535";
                    }
                    units "seconds";
                    description
                        "The time that the PCEP entity will wait to receive an Open
                         message from a peer after the TCP connection has come up.
                         If no Open message is received within this time, then PCEP
                         terminates the TCP connection.";
                }

                leaf keep-wait-timer {
                    type uint32 {
                        range "1..65535";
                    }
                    units "seconds";
                    description
                        "The time that the PCEP entity will wait to receive a
                         Keepalive or PCErr message from a peer during session
                         initialization after receiving an Open message.  If no
                         Keepalive or PCErr message is received within this time,
                         then PCEP terminates the TCP connection.";
                }

                leaf sync-timer {
                    type uint32 {
                        range "1..65535";
                    }
                    units "seconds";
                    description
                        "The value is used in the case of a synchronized
                         path computation request using the SVEC object.";
                }

                leaf request-timer {
                    type uint32 {
                        range "1..65535";
                    }
                    units "seconds";
                    description
                        "The maximum time that the PCEP entity will wait for a
                         response to a PCReq message.";
                }

                leaf connect-timer {
                    type uint32 {
                        range "1..65535";
                    }
                    units "seconds";
                    description
                        "The time that the PCEP entity will wait to establish a TCP
                         connection with a peer.  If a TCP connection is not
                         established within this time, then PCEP aborts the session
                         setup attempt.";
                }

                leaf allow-negotiation {
                    type boolean;
                    description
                        "Whether the PCEP entity will permit negotiation of session
                         parameters.";
                }

                leaf max-sessions {
                    type uint32;
                    description
                        "The maximum number of sessions involving this PCEP entity
                         that can exist at any time.";
                }

                leaf max-unknown-reqs {
                    type uint32;
                    description
                        "The maximum number of unrecognized requests and replies that
                         any session on this PCEP entity is willing to accept per
                         minute before terminating the session.";
                }

                leaf is-overloaded {
                    type boolean;
                    description
                        "The value indicates whether this is overloaded with the processing
                         of existing requests and is unable to handle new requests leading
                         to unacceptable response times";
                }

                list peer {
                    key "ip-address";
                    description "Enter the peer list instance";

                    leaf ip-address {
                        type types-sros:ip-unicast-address;
                        description "This value specifies the address of the PCE peer";
                    }

                    leaf speaker-id {
                        type string {
                            length "0..48";
                        }
                        description
                            "The value indicates a unique speaker identifier for the peer
                             that does change during lifetime of the speaker";
                    }

                    leaf-list capabilities {
                        type types-router:pcep-capabilities;
                        description "This value specifies the capabilities supported by this peer";
                    }

                    leaf sync-state {
                        type types-router:pcep-sync-state;
                        description "The value of indicates the synchronization state of this peer.";
                    }

                    leaf sess-establish-time {
                        type yang:date-and-time;
                        description
                            "The value indicates the time at which the session with the peer moved
                             to the established state";
                    }

                    leaf oper-keepalive {
                        type uint32;
                        units "seconds";
                        description
                            "The value indicates the operational value of keep alive interval in
                             use by this entity's peer.This is the maximum time between two
                             consecutive messages sent to a peer";
                    }

                    leaf oper-dead-timer {
                        type uint32;
                        units "seconds";
                        description
                            "The value indicates the operational value of dead timer interval in
                             use by this peer.This is the time after which a peer should declare
                             a session down if it is does not receive any PCEP messages";
                    }

                    leaf port {
                        type types-sros:tcp-udp-port;
                        description "The value indicates PCE peer's port number.";
                    }

                    container statistics {
                        description "Enter the statistics context";

                        leaf num-pcrpt-sent {
                            type yang:counter32;
                            description "The value indicates the number of PCRpt messages sent to this peer.";
                        }

                        leaf num-pcrpt-rcvd {
                            type yang:counter32;
                            description "The value indicates the number of PCRpt messages received from this peer";
                        }

                        leaf num-pcupd-sent {
                            type yang:counter32;
                            description "The value indicates the number of PCUpd messages sent to this peer.";
                        }

                        leaf num-pcupd-rcvd {
                            type yang:counter32;
                            description "The value indicates the number of PCUpd messages received from this peer";
                        }

                        leaf num-rpt-sent {
                            type yang:counter32;
                            description
                                "The value indicates the number of report messages sent to this peer.
                                 This might be greater that num-pcrpt-sent because multiple
                                 requests can be batched into a single PCRpt messages.";
                        }

                        leaf num-rpt-rcvd {
                            type yang:counter32;
                            description
                                "The value indicates the number pf report messages received from
                                 this peer.This might be greater that num-pcrpt-rcvd because
                                 multiple requests can be batched into a single PCRpt message.";
                        }

                        leaf num-pcreq-sent {
                            type yang:counter32;
                            description "The number of PCReq messages sent to this peer";
                        }

                        leaf num-pcreq-rcvd {
                            type yang:counter32;
                            description "The number of PCReq messages received from this peer";
                        }

                        leaf num-pcrep-sent {
                            type yang:counter32;
                            description "The number of PCRep messages sent to this peer";
                        }

                        leaf num-pcrep-rcvd {
                            type yang:counter32;
                            description "The number of PCRep messages received from this peer";
                        }

                        leaf num-pcerr-sent {
                            type yang:counter32;
                            description "The number of PCErr messages sent to this peer";
                        }

                        leaf num-pcerr-rcvd {
                            type yang:counter32;
                            description "The number of PCErr messages received from this peer";
                        }

                        leaf num-pcntf-sent {
                            type yang:counter32;
                            description "The number of PCNtf messages sent to this peer";
                        }

                        leaf num-pcntf-rcvd {
                            type yang:counter32;
                            description "The number of PCNtf messages received from this peer";
                        }

                        leaf num-keepalive-sent {
                            type yang:counter32;
                            description "The number of Keepalive messages sent to this peer";
                        }

                        leaf num-keepalive-rcvd {
                            type yang:counter32;
                            description "The number of Keepalive messages received from this peer";
                        }

                        leaf num-req-rcvd {
                            type yang:counter32;
                            description
                                "The number of requests received from this peer.  A request
                                 corresponds 1:1 with an RP object in a PCReq message";
                        }

                        leaf num-sess-setup-ok {
                            type yang:counter32;
                            description
                                "The number of PCEP sessions successfully established with
                                 the peer, including any current session.  This counter is
                                 incremented each time a session with this peer is
                                 successfully established";
                        }

                        leaf num-sess-setup-fail {
                            type yang:counter32;
                            description
                                "The number of PCEP sessions with the peer that have been
                                 attempted but failed before being fully established.
                                 This counter is incremented each time a session retry to
                                 this peer fails";
                        }

                        leaf num-pcinit-sent {
                            type yang:counter32;
                            description "The number of PC initiated messages sent to this peer.";
                        }

                        leaf num-pcinit-rcvd {
                            type yang:counter32;
                            description "The number of PC initiated messages received from this peer.";
                        }

                        leaf num-req-sent {
                            type yang:counter32;
                            description
                                "The number of requests sent to this peer.  A request
                                 corresponds 1:1 with an RP object in a PCReq message";
                        }

                    } // container statistics

                } // list peer

            } // container pce

        } // container pcep

    } // grouping state-router-pcep

}
