submodule nokia-conf-system-security-management-access-filter {

    yang-version "1.1";

    belongs-to nokia-conf { prefix "conf"; }

    import ietf-yang-types                { prefix "yang"; }
    import nokia-sros-yang-extensions     { prefix "sros-ext"; }
    import nokia-types-filter             { prefix "types-filter"; }
    import nokia-types-services           { prefix "types-services"; }
    import nokia-types-sros               { prefix "types-sros"; }

    include nokia-conf-filter;
    include nokia-conf-groups;

    sros-ext:sros-major-release "rel25";
    organization "Nokia";
    contact
        "Nokia SR OS Support
         Web: <http://www.nokia.com>";
    description
        "Nokia YANG Data model to configure System security management access filter configuration. on SR OS based routers.

         Copyright 2016 Nokia. All rights reserved. Reproduction of this document
         is authorized on the condition that the foregoing copyright notice is included.

         This nokia-conf-system-security-management-access-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-08-12";

    grouping conf-system-security-management-access-filter {
        container management-access-filter {
            description "Enter the management-access-filter context";

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container ip-filter {
                description "Enter the ip-filter context";

                leaf admin-state {
                    type types-sros:admin-state;
                    default "enable";
                    description "Administrative state of management-access filters";
                }

                leaf default-action {
                    type types-filter:maf-action;
                    default "ignore-match";
                    description "Default action for the management access filter";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list entry {
                    key "entry-id";
                    description "Enter the entry list instance";

                    leaf entry-id {
                        type uint32 {
                            range "1..9999";
                        }
                        description "Entry ID to identify the match criteria and the action";
                    }

                    leaf action {
                        type types-filter:maf-action;
                        default "ignore-match";
                        description "Action associated with the management access filter";
                    }

                    leaf description {
                        type types-sros:description;
                        description "Text description";
                    }

                    leaf log-events {
                        type boolean;
                        default "false";
                        description "Enable match logging";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container match {
                        description "Enter the match context";

                        leaf router-instance {
                            type string;
                            description "Router instance as the match criterion";
                        }

                        leaf protocol {
                            type types-sros:match-ip-protocol;
                            description "IP protocol as the match criterion";
                        }

                        container src-ip {
                            description "Enter the src-ip context";

                            choice src-ip {
                                case address {

                                    leaf address {
                                        type union {
                                            type types-sros:ipv4-prefix;
                                            type types-sros:ipv4-address;
                                        }
                                        description "IP address or IP prefix as the match criterion";
                                    }

                                    leaf mask {
                                        type types-sros:ipv4-address;
                                        description "IP address mask as the match criterion";
                                    }

                                }
                                case ip-prefix-list {

                                    leaf ip-prefix-list {
                                        type leafref {
                                            path "../../../../../../../../filter/match-list/ip-prefix-list/prefix-list-name";
                                        }
                                        description "IP prefix list as the match criterion";
                                    }

                                }
                            }
                        } // container src-ip

                        container mgmt-port {
                            description "Enter the mgmt-port context";

                            choice mgmt-port {
                                case port-id {

                                    leaf port-id {
                                        type types-sros:port;
                                        description "Port ID as the match criterion";
                                    }

                                }
                                case cpm {

                                    leaf cpm {
                                        type empty;
                                        description "Match any traffic received on any Ethernet port";
                                    }

                                }
                                case lag-id {

                                    leaf lag-id {
                                        status obsolete;
                                        type types-sros:lag-interface;
                                        description "LAG ID for the source interface";
                                    }

                                    leaf lag {
                                        type types-sros:lag-interface;
                                        description "LAG ID as the match criterion";
                                    }

                                }
                            }
                        } // container mgmt-port

                        container dst-port {
                            presence "Enable the dst-port context";
                            description "Enable the dst-port context";

                            leaf port {
                                type uint16 {
                                    range "1..65535";
                                }
                                mandatory true;
                                description "TCP or UDP port number as the match criterion";
                            }

                            leaf mask {
                                type uint16 {
                                    range "1..65535";
                                }
                                default "65535";
                                description "IP address mask as the match criterion";
                            }

                        } // container dst-port

                        container src-port {
                            presence "Enable the src-port context";
                            description "Enable the src-port context";

                            leaf port {
                                type uint16 {
                                    range "1..65535";
                                }
                                mandatory true;
                                description "TCP or UDP port number as the match criterion";
                            }

                            leaf mask {
                                type uint16 {
                                    range "1..65535";
                                }
                                default "65535";
                                description "IP address mask as the match criterion";
                            }

                        } // container src-port

                    } // container match

                } // list entry

            } // container ip-filter

            container ipv6-filter {
                description "Enter the ipv6-filter context";

                leaf admin-state {
                    type types-sros:admin-state;
                    default "enable";
                    description "Administrative state of management-access filters";
                }

                leaf default-action {
                    type types-filter:maf-action;
                    default "ignore-match";
                    description "Default action for the management access filter";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list entry {
                    key "entry-id";
                    description "Enter the entry list instance";

                    leaf entry-id {
                        type uint32 {
                            range "1..9999";
                        }
                        description "Entry ID to identify the match criteria and the action";
                    }

                    leaf action {
                        type types-filter:maf-action;
                        default "ignore-match";
                        description "Action associated with the management access filter";
                    }

                    leaf description {
                        type types-sros:description;
                        description "Text description";
                    }

                    leaf log-events {
                        type boolean;
                        default "false";
                        description "Enable match logging";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container match {
                        description "Enter the match context";

                        leaf router-instance {
                            type string;
                            description "Router instance as the match criterion";
                        }

                        leaf next-header {
                            type types-sros:match-ip-protocol;
                            description "IP protocol to match";
                        }

                        leaf flow-label {
                            type types-filter:filter-match-flow-label;
                            description "Flow identifier used to discriminate traffic flows";
                        }

                        container src-ip {
                            description "Enter the src-ip context";

                            choice src-ip {
                                case address {

                                    leaf address {
                                        type union {
                                            type types-sros:ipv6-prefix;
                                            type types-sros:ipv6-address;
                                        }
                                        description "IPv6 address or IPv6 prefix to match";
                                    }

                                    leaf mask {
                                        type types-sros:ipv6-address;
                                        description "IP address mask as the match criterion";
                                    }

                                }
                                case ipv6-prefix-list {

                                    leaf ipv6-prefix-list {
                                        type leafref {
                                            path "../../../../../../../../filter/match-list/ipv6-prefix-list/prefix-list-name";
                                        }
                                        description "IPv6 prefix list as the match criterion";
                                    }

                                }
                            }
                        } // container src-ip

                        container mgmt-port {
                            description "Enter the mgmt-port context";

                            choice mgmt-port {
                                case port-id {

                                    leaf port-id {
                                        type types-sros:port;
                                        description "Port ID as the match criterion";
                                    }

                                }
                                case cpm {

                                    leaf cpm {
                                        type empty;
                                        description "Match any traffic received on any Ethernet port";
                                    }

                                }
                                case lag-id {

                                    leaf lag-id {
                                        status obsolete;
                                        type types-sros:lag-interface;
                                        description "LAG ID for the source interface";
                                    }

                                    leaf lag {
                                        type types-sros:lag-interface;
                                        description "LAG ID as the match criterion";
                                    }

                                }
                            }
                        } // container mgmt-port

                        container dst-port {
                            presence "Enable the dst-port context";
                            description "Enable the dst-port context";

                            leaf port {
                                type uint16 {
                                    range "1..65535";
                                }
                                mandatory true;
                                description "TCP or UDP port number as the match criterion";
                            }

                            leaf mask {
                                type uint16 {
                                    range "1..65535";
                                }
                                default "65535";
                                description "IP address mask as the match criterion";
                            }

                        } // container dst-port

                        container src-port {
                            presence "Enable the src-port context";
                            description "Enable the src-port context";

                            leaf port {
                                type uint16 {
                                    range "1..65535";
                                }
                                mandatory true;
                                description "TCP or UDP port number as the match criterion";
                            }

                            leaf mask {
                                type uint16 {
                                    range "1..65535";
                                }
                                default "65535";
                                description "IP address mask as the match criterion";
                            }

                        } // container src-port

                    } // container match

                } // list entry

            } // container ipv6-filter

            container mac-filter {
                description "Enter the mac-filter context";

                leaf admin-state {
                    type types-sros:admin-state;
                    default "enable";
                    description "Administrative state of management access MAC filter";
                }

                leaf default-action {
                    type types-filter:maf-mac-action;
                    default "ignore-match";
                    description "Default action for the management access filter";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list entry {
                    key "entry-id";
                    description "Enter the entry list instance";

                    leaf entry-id {
                        type uint32 {
                            range "1..9999";
                        }
                        description "Entry ID to identify the match criteria and the action";
                    }

                    leaf action {
                        type types-filter:maf-mac-action;
                        default "ignore-match";
                        description "Action associated with the management access filter";
                    }

                    leaf description {
                        type types-sros:description;
                        description "Text description";
                    }

                    leaf log-events {
                        type boolean;
                        default "false";
                        description "Enable match logging";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                    container match {
                        description "Enter the match context";

                        leaf service {
                            type types-services:service-name;
                            description "Service ID used as the match condition";
                        }

                        leaf frame-type {
                            type enumeration {
                                enum 802dot3                        { value 0; }
                                enum 802dot2-llc                    { value 1; }
                                enum 802dot2-snap                   { value 2; }
                                enum ethernet-ii                    { value 3; }
                                enum 802dot1-ag                     { value 4; }
                            }
                            default "802dot3";
                            description "MAC frame type as the match criterion";
                        }

                        leaf etype {
                            type types-services:etype-value;
                            description "Ethernet type II Ethertype value as the match criterion";
                        }

                        leaf snap-pid {
                            type int32 {
                                range "0..65535";
                            }
                            description "IEEE 802.3 LLC SNAP Ethernet Frame PID as the match";
                        }

                        leaf snap-oui {
                            type enumeration {
                                enum zero                           { value 2; }
                                enum non-zero                       { value 3; }
                            }
                            description "IEEE 802.3 LLC SNAP Ethernet Frame OUI value for match";
                        }

                        container src-mac {
                            presence "Enable the src-mac context";
                            description "Enable the src-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container src-mac

                        container dst-mac {
                            presence "Enable the dst-mac context";
                            description "Enable the dst-mac context";

                            leaf address {
                                type yang:mac-address;
                                mandatory true;
                                description "MAC address used as the match criterion";
                            }

                            leaf mask {
                                type yang:mac-address;
                                default "ff:ff:ff:ff:ff:ff";
                                description "MAC address mask as the match criterion";
                            }

                        } // container dst-mac

                        container dot1p {
                            presence "Enable the dot1p context";
                            description "Enable the dot1p context";

                            leaf priority {
                                type int32 {
                                    range "0..7";
                                }
                                mandatory true;
                                description "IEEE 802.1p value as the match criterion";
                            }

                            leaf mask {
                                type int32 {
                                    range "1..7";
                                }
                                default "7";
                                description "3-bit mask as the match criterion";
                            }

                        } // container dot1p

                        container llc-ssap {
                            presence "Enable the llc-ssap context";
                            description "Enable the llc-ssap context";

                            leaf ssap {
                                type int32 {
                                    range "0..255";
                                }
                                mandatory true;
                                description "8-bit SSAP as the match criterion";
                            }

                            leaf mask {
                                type int32 {
                                    range "1..255";
                                }
                                default "255";
                                description "Mask for SSAP value as the match criterion";
                            }

                        } // container llc-ssap

                        container llc-dsap {
                            presence "Enable the llc-dsap context";
                            description "Enable the llc-dsap context";

                            leaf dsap {
                                type int32 {
                                    range "0..255";
                                }
                                mandatory true;
                                description "8-bit DSAP as the match criterion";
                            }

                            leaf mask {
                                type int32 {
                                    range "1..255";
                                }
                                default "255";
                                description "Mask for DSAP value as the match criterion";
                            }

                        } // container llc-dsap

                        container cfm-opcode {
                            description "Enter the cfm-opcode context";

                            choice match-cfm-opcode {
                                case operator-eq {

                                    leaf eq {
                                        type uint32 {
                                            range "0..255";
                                        }
                                        description "Equal to comparison operator for the CFM opcode";
                                    }

                                }
                                case operator-lt {

                                    leaf lt {
                                        type uint32 {
                                            range "1..255";
                                        }
                                        description "Less than comparison operator for the CFM opcode";
                                    }

                                }
                                case operator-gt {

                                    leaf gt {
                                        type uint32 {
                                            range "0..254";
                                        }
                                        description "Greater than comparison operator for the CFM opcode";
                                    }

                                }
                                case opcode-range {

                                    container range {
                                        presence "Enable the range context";
                                        description "Enable the range context";

                                        leaf start {
                                            type uint32 {
                                                range "0..254";
                                            }
                                            mandatory true;
                                            description "Lower bound of the range for the OpCode to match";
                                        }

                                        leaf end {
                                            type uint32 {
                                                range "1..255";
                                            }
                                            mandatory true;
                                            description "Upper bound of the range for the OpCode to match";
                                        }

                                    } // container range

                                }
                            }
                        } // container cfm-opcode

                    } // container match

                } // list entry

            } // container mac-filter

        } // container management-access-filter

    } // grouping conf-system-security-management-access-filter

}
