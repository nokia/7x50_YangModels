submodule nokia-state-system-bootup {

    yang-version "1.1";

    belongs-to nokia-state { prefix "state"; }

    import nokia-sros-yang-extensions     { prefix "sros-ext"; }
    import nokia-types-sros               { prefix "types-sros"; }

    sros-ext:sros-major-release "rel25";
    organization "Nokia";
    contact
        "Nokia SR OS Support
         Web: <http://www.nokia.com>";
    description
        "Nokia YANG Data model with operational state for system bootup informations on SR OS based routers.

         Copyright 2016 Nokia. All rights reserved. Reproduction of this document
         is authorized on the condition that the foregoing copyright notice is included.

         This nokia-state-system-bootup YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    grouping state-system-bootup {
        container bootup {
            description "Enter the bootup context";

            leaf bof-source {
                type types-sros:display-string-or-empty;
                description
                    "The compact flash slot where the Boot Options File (BOF) file
                     was found when the system last rebooted.";
            }

            leaf image-source {
                type enumeration {
                    enum unknown                        { value 0; }
                    enum primary                        { value 1; }
                    enum secondary                      { value 2; }
                    enum tertiary                       { value 3; }
                }
                description
                    "The location in the BOF where the software image file was found
                     when the system last rebooted.";
            }

            leaf config-source {
                type enumeration {
                    enum unknown                        { value 0; }
                    enum primary                        { value 1; }
                    enum secondary                      { value 2; }
                    enum tertiary                       { value 3; }
                }
                description
                    "The location in the BOF where the configuration file was found
                     when the system last rebooted.";
            }

            leaf last-booted-config-file {
                type types-sros:display-string-or-empty;
                description
                    "The location and name of the configuration file from which
                     the system last rebooted.";
            }

            leaf last-boot-config-version {
                type types-sros:description-or-empty;
                description
                    "The version of the configuration file from which the system
                     last rebooted.";
            }

            leaf last-boot-config-header {
                type string {
                    length "1..512";
                }
                description
                    "The header of the configuration file from which the system
                     last rebooted.";
            }

            leaf last-boot-index-version {
                type types-sros:description-or-empty;
                description
                    "The version of the index file read when this CPM card was
                     last rebooted.";
            }

            leaf last-boot-index-header {
                type string {
                    length "1..512";
                }
                description
                    "The header of the index file from which the system
                     last rebooted.";
            }

            leaf config-status {
                type enumeration {
                    enum config-read                    { value 1; }
                    enum config-ok                      { value 2; }
                    enum default-booted                 { value 3; }
                    enum boot-config-failed             { value 4; }
                    enum boot-restore-failed            { value 5; }
                    enum auto-provisioning              { value 6; }
                }
                description
                    "Indicates the result of the last attempt to execute
                     the configuration file upon reboot of the system.";
            }

            leaf persist-status {
                type enumeration {
                    enum persist-ok                     { value 1; }
                    enum no-persist-file                { value 2; }
                    enum persist-mismatch               { value 3; }
                    enum persist-index-failure          { value 4; }
                    enum persist-disabled               { value 5; }
                    enum persist-invalid                { value 6; }
                    enum persist-boot                   { value 7; }
                    enum persist-init                   { value 8; }
                    enum persist-in-progress            { value 9; }
                }
                description
                    "Indicates the state of the rebuild of the SNMP persistent index
                     database upon reboot of the system.";
            }

            leaf persist-index {
                type boolean;
                description
                    "When index has a value of 'true', the SNMP persistent index
                     database was rebuilt when the system was rebooted.
                     When index has a value of 'false' the system was reconfigured
                     without maintaining persistent SNMP index values and the SNMP
                     daemon was enabled.";
            }

        } // container bootup

    } // grouping state-system-bootup

}
