submodule nokia-conf-system-security-pki {

    yang-version "1.1";

    belongs-to nokia-conf { prefix "conf"; }

    import nokia-sros-yang-extensions     { prefix "sros-ext"; }
    import nokia-types-security           { prefix "types-security"; }
    import nokia-types-services           { prefix "types-services"; }
    import nokia-types-sros               { prefix "types-sros"; }
    import nokia-types-system             { prefix "types-system"; }

    include nokia-conf-groups;
    include nokia-conf-system;

    sros-ext:sros-major-release "rel26";
    organization "Nokia";
    contact
        "Nokia SR OS Support
         Web: <http://www.nokia.com>";
    description
        "Nokia YANG Data model to configure system security pki parameters. on SR OS based routers.

         Copyright 2016 Nokia. All rights reserved. Reproduction of this document
         is authorized on the condition that the foregoing copyright notice is included.

         This nokia-conf-system-security-pki YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping conf-system-security-pki {
        container pki {
            description "Enter the pki context";

            leaf certificate-display-format {
                type enumeration {
                    enum ascii                          { value 1; }
                    enum utf8                           { value 2; }
                }
                default "ascii";
                description "Display format for Certificates and CRLs";
            }

            leaf dynamic-ca {
                type boolean;
                default "false";
                description "Enable the dynamic sub-CA support for IPsec";
            }

            leaf imported-format {
                type enumeration {
                    enum any                            { value 1; }
                    enum secure                         { value 2; }
                }
                default "any";
                description "The supported encrypted file formats";
            }

            leaf maximum-cert-chain-depth {
                type uint32 {
                    range "1..7";
                }
                default "7";
                description "Maximum depth of certificate chain verification";
            }

            leaf-list apply-groups {
                type leafref {
                    path "../../../../groups/group/name";
                }
                max-elements 8;
                ordered-by user;
                description "Apply a configuration group at this level";
            }

            leaf-list apply-groups-exclude {
                type leafref {
                    path "../../../../groups/group/name";
                }
                max-elements 8;
                ordered-by user;
                description "Exclude a configuration group at this level";
            }

            container certificate-expiration-warning {
                description "Enter the certificate-expiration-warning context";

                leaf hours {
                    type int32 {
                        range "0..8760";
                    }
                    units "hours";
                    description "Time before system generates certificate warning trap";
                }

                leaf repeat-hours {
                    type int32 {
                        range "0..8760";
                    }
                    units "hours";
                    default "0";
                    description "Time system repeats certificate expiration warning trap";
                }

            } // container certificate-expiration-warning

            container crl-expiration-warning {
                description "Enter the crl-expiration-warning context";

                leaf hours {
                    type int32 {
                        range "0..8760";
                    }
                    units "hours";
                    description "Time before system generates CRL expiration warning trap";
                }

                leaf repeat-hours {
                    type int32 {
                        range "0..8760";
                    }
                    units "hours";
                    default "0";
                    description "Time system repeats CRL expiration warning trap";
                }

            } // container crl-expiration-warning

            list ca-profile {
                key "ca-profile-name";
                max-elements 128;
                description "Enter the ca-profile list instance";

                leaf ca-profile-name {
                    type types-sros:named-item;
                    description "CA profile name";
                }

                leaf admin-state {
                    type types-sros:admin-state;
                    default "disable";
                    description "Administrative state of the CA profile";
                }

                leaf description {
                    type types-sros:description;
                    description "Text description";
                }

                leaf cert-file {
                    type types-security:pki-file-name;
                    sros-ext:auto-restart-to-modify;
                    description "Certificate file name";
                }

                leaf crl-file {
                    type types-security:pki-file-name;
                    sros-ext:auto-restart-to-modify;
                    description "Certificate Revocation List (CRL) file name";
                }

                leaf revocation-check {
                    type enumeration {
                        enum crl                            { value 1; }
                        enum crl-optional                   { value 2; }
                    }
                    sros-ext:auto-restart-to-modify;
                    default "crl";
                    description "Revocation method to check status of CA certificates";
                }

                leaf-list apply-groups {
                    type leafref {
                        path "../../../../../groups/group/name";
                    }
                    max-elements 8;
                    ordered-by user;
                    sros-ext:auto-restart-to-modify;
                    description "Apply a configuration group at this level";
                }

                leaf-list apply-groups-exclude {
                    type leafref {
                        path "../../../../../groups/group/name";
                    }
                    max-elements 8;
                    ordered-by user;
                    sros-ext:auto-restart-to-modify;
                    description "Exclude a configuration group at this level";
                }

                container ocsp {
                    sros-ext:auto-restart-to-modify;
                    description "Enter the ocsp context";

                    leaf responder-url {
                        type union {
                            type types-sros:http-optional-url-loose;
                        }
                        sros-ext:auto-restart-to-modify;
                        description "HTTP URL of the OCSP responder for the CA";
                    }

                    leaf service-name {
                        type types-services:service-name;
                        sros-ext:auto-restart-to-modify;
                        description "Administrative service name";
                    }

                    leaf transmission-profile {
                        type leafref {
                            path "../../../../../transmission-profile/name";
                        }
                        sros-ext:auto-restart-to-modify;
                        description "Transmission profile for the OCSP";
                    }

                } // container ocsp

                container cmpv2 {
                    sros-ext:auto-restart-to-modify;
                    description "Enter the cmpv2 context";

                    leaf always-set-sender-for-ir {
                        type boolean;
                        sros-ext:auto-restart-to-modify;
                        default "false";
                        description "Set subject name in CMPv2 header for all IR messages";
                    }

                    leaf same-recipient-nonce-for-poll-request {
                        type boolean;
                        sros-ext:auto-restart-to-modify;
                        default "false";
                        description "Use same recipNonce as last CMPv2 response";
                    }

                    leaf signing-cert-subject {
                        type string {
                            length "1..256";
                        }
                        sros-ext:auto-restart-to-modify;
                        description "Subject DN attributes to identify signing certificate";
                    }

                    choice response-signing {
                        default "response-signing-cert";
                        case response-signing-use-extracert {

                            leaf response-signing-use-extracert {
                                type empty;
                                sros-ext:auto-restart-to-modify;
                                description "Use extraCerts certificate to verify response signature";
                            }

                        }
                        case response-signing-cert {

                            leaf response-signing-cert {
                                type types-security:pki-file-name;
                                sros-ext:auto-restart-to-modify;
                                description "File name of the certificate to verify CMPv2 responses";
                            }

                        }
                    }
                    choice recipient {
                        default "use-ca-subject";
                        case use-ca-subject {

                            leaf use-ca-subject {
                                type empty;
                                sros-ext:auto-restart-to-modify;
                                description "Use subject DN in CA certificate as CMPv2 request recipient";
                            }

                        }
                        case recipient-subject {

                            leaf recipient-subject {
                                type string {
                                    length "1..256";
                                }
                                sros-ext:auto-restart-to-modify;
                                description "DN attributes for recipient subject of CMPv2 requests";
                            }

                        }
                    }
                    container accept-unprotected-message {
                        sros-ext:auto-restart-to-modify;
                        description "Enter the accept-unprotected-message context";

                        leaf error-message {
                            type boolean;
                            sros-ext:auto-restart-to-modify;
                            default "false";
                            description "Accept unprotected error messages";
                        }

                        leaf pkiconf-message {
                            type boolean;
                            sros-ext:auto-restart-to-modify;
                            default "false";
                            description "Accept unprotected PKI confirmation messages";
                        }

                    } // container accept-unprotected-message

                    container http {
                        sros-ext:auto-restart-to-modify;
                        description "Enter the http context";

                        leaf response-timeout {
                            type uint32 {
                                range "1..3600";
                            }
                            units "seconds";
                            sros-ext:auto-restart-to-modify;
                            default "30";
                            description "HTTP response timeout";
                        }

                        leaf version {
                            type types-system:http-version-type;
                            sros-ext:auto-restart-to-modify;
                            description "HTTP version for CMPv2 messages";
                        }

                    } // container http

                    container url {
                        sros-ext:auto-restart-to-modify;
                        description "Enter the url context";

                        leaf url-string {
                            type union {
                                type types-sros:http-optional-url-loose;
                            }
                            sros-ext:auto-restart-to-modify;
                            description "URL for CMPv2";
                        }

                        choice transport {
                            case service {

                                leaf service-name {
                                    type types-services:service-name;
                                    sros-ext:auto-restart-to-modify;
                                    description "Administrative service name";
                                }

                            }
                            case transmission {

                                leaf transmission-profile {
                                    type leafref {
                                        path "../../../../../../transmission-profile/name";
                                    }
                                    sros-ext:auto-restart-to-modify;
                                    description "Transmission profile for CMPv2";
                                }

                            }
                        }
                    } // container url

                    container key-list {
                        sros-ext:auto-restart-to-modify;
                        description "Enter the key-list context";

                        list key {
                            key "reference-number";
                            max-elements 128;
                            description "Enter the key list instance";

                            leaf reference-number {
                                type types-sros:display-string {
                                    length "1..64";
                                    pattern ".*\\S.*" {
                                        error-message "'reference-number' must not be all spaces";
                                    }
                                }
                                description "Unique identifier for the CA initial authentication key";
                            }

                            leaf password {
                                type types-sros:encrypted-leaf {
                                    length "1..166";
                                }
                                description "Shared secret for this CA initial authentication key";
                            }

                            leaf-list apply-groups {
                                type leafref {
                                    path "../../../../../../../../groups/group/name";
                                }
                                max-elements 8;
                                ordered-by user;
                                description "Apply a configuration group at this level";
                            }

                            leaf-list apply-groups-exclude {
                                type leafref {
                                    path "../../../../../../../../groups/group/name";
                                }
                                max-elements 8;
                                ordered-by user;
                                description "Exclude a configuration group at this level";
                            }

                        } // list key

                    } // container key-list

                } // container cmpv2

                container auto-crl-update {
                    presence "Enable the auto-crl-update context";
                    description "Enable the auto-crl-update context";

                    leaf admin-state {
                        type types-sros:admin-state;
                        default "disable";
                        description "Administrative state of the automatic CRL update";
                    }

                    leaf periodic-update-interval {
                        type types-sros:time-duration {
                            range "3600..31622400";
                        }
                        units "seconds";
                        sros-ext:auto-restart-to-modify;
                        default "86400";
                        description "Interval between two consecutive CRL updates";
                    }

                    leaf pre-update-time {
                        type types-sros:time-duration {
                            range "0..31622400";
                        }
                        units "seconds";
                        sros-ext:auto-restart-to-modify;
                        default "3600";
                        description "Time prior to the next update time of the current CRL";
                    }

                    leaf retry-interval {
                        type types-sros:time-duration {
                            range "0..31622400";
                        }
                        units "seconds";
                        sros-ext:auto-restart-to-modify;
                        default "3600";
                        description "Interval before retrying to update CRL";
                    }

                    leaf schedule-type {
                        type enumeration {
                            enum next-update-based              { value 1; }
                            enum periodic                       { value 2; }
                        }
                        sros-ext:auto-restart-to-modify;
                        default "next-update-based";
                        description "Time scheduler type for an automated CRL update";
                    }

                    leaf-list apply-groups {
                        type leafref {
                            path "../../../../../../groups/group/name";
                        }
                        max-elements 8;
                        ordered-by user;
                        sros-ext:auto-restart-to-modify;
                        description "Apply a configuration group at this level";
                    }

                    leaf-list apply-groups-exclude {
                        type leafref {
                            path "../../../../../../groups/group/name";
                        }
                        max-elements 8;
                        ordered-by user;
                        sros-ext:auto-restart-to-modify;
                        description "Exclude a configuration group at this level";
                    }

                    container crl-urls {
                        sros-ext:auto-restart-to-modify;
                        description "Enter the crl-urls context";

                        list url-entry {
                            key "entry-id";
                            description "Enter the url-entry list instance";

                            leaf entry-id {
                                type uint32 {
                                    range "1..8";
                                }
                                description "URL on this system";
                            }

                            leaf transmission-profile {
                                type leafref {
                                    path "../../../../../../../transmission-profile/name";
                                }
                                description "File transmission profile to update CRL";
                            }

                            leaf url {
                                type union {
                                    type types-sros:http-url-path-loose;
                                }
                                description "Location of updated CRL";
                            }

                            leaf-list apply-groups {
                                type leafref {
                                    path "../../../../../../../../groups/group/name";
                                }
                                max-elements 8;
                                ordered-by user;
                                description "Apply a configuration group at this level";
                            }

                            leaf-list apply-groups-exclude {
                                type leafref {
                                    path "../../../../../../../../groups/group/name";
                                }
                                max-elements 8;
                                ordered-by user;
                                description "Exclude a configuration group at this level";
                            }

                        } // list url-entry

                    } // container crl-urls

                } // container auto-crl-update

            } // list ca-profile

            list common-name-list {
                key "cn-list-name";
                max-elements 64;
                description "Enter the common-name-list list instance";

                leaf cn-list-name {
                    type types-sros:named-item;
                    description "CN list name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                list common-name {
                    key "cn-index";
                    description "Enter the common-name list instance";

                    leaf cn-index {
                        type uint32 {
                            range "1..128";
                        }
                        description "Common name index";
                    }

                    leaf cn-type {
                        type enumeration {
                            enum ip-address                     { value 1; }
                            enum domain-name                    { value 2; }
                        }
                        mandatory true;
                        description "Common name type";
                    }

                    leaf cn-value {
                        type types-sros:regular-expression-not-all-spaces;
                        mandatory true;
                        description "Common name value";
                    }

                    leaf-list apply-groups {
                        type leafref {
                            path "../../../../../../groups/group/name";
                        }
                        max-elements 8;
                        ordered-by user;
                        description "Apply a configuration group at this level";
                    }

                    leaf-list apply-groups-exclude {
                        type leafref {
                            path "../../../../../../groups/group/name";
                        }
                        max-elements 8;
                        ordered-by user;
                        description "Exclude a configuration group at this level";
                    }

                } // list common-name

            } // list common-name-list



            list est-profile {
                key "name";
                max-elements 128;
                description "Enter the est-profile list instance";

                leaf name {
                    type types-sros:named-item;
                    description "Enrollment over Secured Transport profile name";
                }

                leaf transmission-profile {
                    type types-sros:named-item;
                    description "Transmission profile name for EST";
                }

                leaf client-tls-profile {
                    type types-sros:named-item;
                    description "TLS client profile assigned to applications";
                }

                leaf check-id-kp-cmcra-only {
                    type boolean;
                    default "false";
                    description "Check id-kp-cmcra in the EST certificate";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                container server {
                    description "Enter the server context";

                    leaf port {
                        type types-sros:tcp-udp-port-non-zero;
                        default "443";
                        description "Port number of the EST server";
                    }

                    choice address {
                        case ipv4 {

                            leaf ipv4 {
                                type types-sros:ipv4-unicast-address;
                                description "IPv4 address of the EST server";
                            }

                        }
                        case ipv6 {

                            leaf ipv6 {
                                type types-sros:ip-address;
                                description "IPv6 address of the EST server";
                            }

                        }
                        case fqdn {

                            leaf fqdn {
                                type types-sros:fully-qualified-domain-name;
                                description "Fully Qualified Domain Name (FQDN) of the EST server";
                            }

                        }
                    }
                    container path {
                        description "Enter the path context";

                        leaf cacerts {
                            type string {
                                length "1..255";
                                pattern "/.*" {
                                    error-message "'cacerts' must start with / (e.g. /path)";
                                }
                            }
                            description "Server path to request CA certificates";
                        }

                        leaf simpleenroll {
                            type string {
                                length "1..255";
                                pattern "/.*" {
                                    error-message "'simpleenroll' must start with / (e.g. /path)";
                                }
                            }
                            description "Server path to request simple certificate enrollment";
                        }

                        leaf simplereenroll {
                            type string {
                                length "1..255";
                                pattern "/.*" {
                                    error-message "'simplereenroll' must start with / (e.g. /path)";
                                }
                            }
                            description "Server path for the reenrollment of clients";
                        }

                    } // container path

                } // container server

                container http-authentication {
                    description "Enter the http-authentication context";

                    leaf username {
                        type string {
                            length "1..32";
                        }
                        description "Username for the EST authentication";
                    }

                    leaf password {
                        type types-sros:encrypted-leaf {
                            length "1..166";
                        }
                        description "Password for EST authentication";
                    }

                } // container http-authentication

            } // list est-profile

            list certificate-update-profile {
                key "name";
                max-elements 256;
                description "Enter the certificate-update-profile list instance";

                leaf name {
                    type types-sros:named-item;
                    description "Certificate update profile name";
                }

                leaf hash-algorithm {
                    type types-security:hash-algorithm;
                    default "sha256";
                    description "Hash algorithm for a certificate request";
                }

                leaf retry-interval {
                    type uint32 {
                        range "60..36000";
                    }
                    units "seconds";
                    default "3600";
                    description "Retry interval after a failed update";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

                choice protocol {
                    default "cmpv2";
                    case cmpv2 {

                        container cmpv2 {
                            description "Enter the cmpv2 context";

                            leaf ca-profile {
                                type leafref {
                                    path "../../../ca-profile/ca-profile-name";
                                }
                                description "CA profile name";
                            }

                        } // container cmpv2

                    }
                    case est {

                        container est {
                            description "Enter the est context";

                            leaf est-profile {
                                type leafref {
                                    path "../../../est-profile/name";
                                }
                                description "EST profile name";
                            }

                        } // container est

                    }
                }
                choice key-generation {
                    default "same-as-existing-key";
                    case same-as-existing-key {

                        leaf same-as-existing-key {
                            type empty;
                            description "Generate the new key to same type and key length";
                        }

                    }
                    case rsa {

                        container rsa {
                            description "Enter the rsa context";

                            leaf key-size {
                                type uint32 {
                                    range "512..8192";
                                }
                                default "2048";
                                description "Length of the generated RSA key";
                            }

                        } // container rsa

                    }
                    case dsa {

                        container dsa {
                            description "Enter the dsa context";

                            leaf key-size {
                                type uint32 {
                                    range "512..8192";
                                }
                                default "2048";
                                description "Length of the generated DSA key";
                            }

                        } // container dsa

                    }
                    case ecdsa {

                        container ecdsa {
                            description "Enter the ecdsa context";

                            leaf curve {
                                type types-security:ecdsa-curve;
                                default "secp256r1";
                                description "Elliptic curve to be used in ECDSA key generation";
                            }

                        } // container ecdsa

                    }
                }
                choice schedule {
                    default "before-expiry";
                    case before-expiry {

                        leaf before-expiry {
                            type uint32 {
                                range "3600..157680000";
                            }
                            units "seconds";
                            default "86400";
                            description "Time scheduler updates before certificate expiry";
                        }

                    }
                    case after-issue {

                        leaf after-issue {
                            type uint32 {
                                range "864000..157680000";
                            }
                            units "seconds";
                            description "Time for scheduler updates after certificate issuance";
                        }

                    }
                }
            } // list certificate-update-profile

            list certificate-auto-update {
                key "certificate-file-name";
                max-elements 256;
                description "Enter the certificate-auto-update list instance";

                leaf certificate-file-name {
                    type types-security:pki-file-name;
                    description "Certificate file name";
                }

                leaf key-file-name {
                    type types-security:pki-file-name;
                    description "Imported key filename";
                }

                leaf profile {
                    type leafref {
                        path "../../certificate-update-profile/name";
                    }
                    description "Certificate update profile name";
                }

                leaf-list apply-groups {
                    type leafref {
                        path "../../../../../groups/group/name";
                    }
                    max-elements 8;
                    ordered-by user;
                    description "Apply a configuration group at this level";
                }

                leaf-list apply-groups-exclude {
                    type leafref {
                        path "../../../../../groups/group/name";
                    }
                    max-elements 8;
                    ordered-by user;
                    description "Exclude a configuration group at this level";
                }

            } // list certificate-auto-update

        } // container pki

    } // grouping conf-system-security-pki

}
