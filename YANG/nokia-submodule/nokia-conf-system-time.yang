submodule nokia-conf-system-time {

    yang-version "1.1";

    belongs-to nokia-conf { prefix "conf"; }

    import nokia-sros-yang-extensions     { prefix "sros-ext"; }
    import nokia-types-router             { prefix "types-router"; }
    import nokia-types-sros               { prefix "types-sros"; }
    import nokia-types-system             { prefix "types-system"; }

    include nokia-conf-groups;
    include nokia-conf-router;
    include nokia-conf-system;
    include nokia-conf-system-security;

    sros-ext:sros-major-release "rel26";
    organization "Nokia";
    contact
        "Nokia SR OS Support
         Web: <http://www.nokia.com>";
    description
        "Nokia YANG Data model to configure system time parameters on SR OS based routers.

         Copyright 2016 Nokia. All rights reserved. Reproduction of this document
         is authorized on the condition that the foregoing copyright notice is included.

         This nokia-conf-system-time YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-system-time {
        container time {
            description "Enter the time context";

            leaf prefer-local-time {
                type boolean;
                default "false";
                description "Use local time over UTC time in the system";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container zone {
                description "Enter the zone context";

                choice time-zone {
                    default "standard-zone";
                    case standard-zone {

                        container standard {
                            description "Enter the standard context";

                            leaf name {
                                type enumeration {
                                    enum hst                            { value 1; }
                                    enum akst                           { value 2; }
                                    enum pst                            { value 3; }
                                    enum mst                            { value 4; }
                                    enum cst                            { value 5; }
                                    enum est                            { value 6; }
                                    enum ast                            { value 7; }
                                    enum nst                            { value 8; }
                                    enum utc                            { value 9; }
                                    enum gmt                            { value 10; }
                                    enum wet                            { value 11; }
                                    enum cet                            { value 12; }
                                    enum eet                            { value 13; }
                                    enum msk                            { value 14; }
                                    enum msd                            { value 15; }
                                    enum awst                           { value 16; }
                                    enum acst                           { value 17; }
                                    enum aest                           { value 18; }
                                    enum nzst                           { value 19; }
                                }
                                default "utc";
                                description "Standard time zone name";
                            }

                        } // container standard

                    }
                    case non-standard-zone {

                        container non-standard {
                            description "Enter the non-standard context";

                            leaf name {
                                type string {
                                    length "1..5";
                                    pattern "([0-9]|[a-z])+" {
                                        error-message "'name' must contain only lowercase letters and digits (e.g. utc5)";
                                    }
                                }
                                description "Non-standard time zone name";
                            }

                            leaf offset {
                                type types-system:hours-minutes-with-range;
                                description "Offset from UTC";
                            }

                        } // container non-standard

                    }
                }
            } // container zone

            list dst-zone {
                status obsolete;
                key "summer-time-zone";
                max-elements 1;
                description "Enter the dst-zone list instance";

                leaf summer-time-zone {
                    status obsolete;
                    type string {
                        length "1..5";
                    }
                    description "Summer time zone name";
                }

                leaf offset {
                    status obsolete;
                    type uint32 {
                        range "0..60";
                    }
                    units "minutes";
                    default "60";
                    description "Offset for Daylight Savings Time";
                }

                leaf-list apply-groups {
                    status obsolete;
                    type leafref {
                        path "../../../../groups/group/name";
                    }
                    max-elements 8;
                    ordered-by user;
                    description "Apply a configuration group at this level";
                }

                leaf-list apply-groups-exclude {
                    status obsolete;
                    type leafref {
                        path "../../../../groups/group/name";
                    }
                    max-elements 8;
                    ordered-by user;
                    description "Exclude a configuration group at this level";
                }

                container end {
                    status obsolete;
                    description "Enter the end context";

                    leaf week {
                        status obsolete;
                        type types-system:week;
                        default "first";
                        description "Week of the month when summer time ends";
                    }

                    leaf day {
                        status obsolete;
                        type types-system:day-of-week-name-long;
                        default "sunday";
                        description "Day of the week when summer time ends";
                    }

                    leaf month {
                        status obsolete;
                        type types-system:month-name-long;
                        default "january";
                        description "Month when summer time ends";
                    }

                    leaf hours-minutes {
                        status obsolete;
                        type types-system:hours-minutes-twenty-four;
                        default "00:00";
                        description "Time when summer time ends, in hh:mm format";
                    }

                } // container end

                container start {
                    status obsolete;
                    description "Enter the start context";

                    leaf week {
                        status obsolete;
                        type types-system:week;
                        default "first";
                        description "Week of the month when summer time starts";
                    }

                    leaf day {
                        status obsolete;
                        type types-system:day-of-week-name-long;
                        default "sunday";
                        description "Day of the week when summer time starts";
                    }

                    leaf month {
                        status obsolete;
                        type types-system:month-name-long;
                        default "january";
                        description "Month when summer time starts";
                    }

                    leaf hours-minutes {
                        status obsolete;
                        type types-system:hours-minutes-twenty-four;
                        default "00:00";
                        description "Time when summer time starts, in hh:mm format";
                    }

                } // container start

            } // list dst-zone

            container daylight-saving-time-zone {
                description "Enter the daylight-saving-time-zone context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice time-zone {
                    default "standard-zone";
                    case standard-zone {

                        container standard {
                            description "Enter the standard context";

                            leaf name {
                                type enumeration {
                                    enum adt {
                                        value 1;
                                        description "Atlantic Daylight Time";
                                    }
                                    enum ndt {
                                        value 2;
                                        description "Newfoundland Daylight Time";
                                    }
                                    enum akdt {
                                        value 3;
                                        description "Alaska Daylight Time";
                                    }
                                    enum cdt {
                                        value 4;
                                        description "Central Daylight Time";
                                    }
                                    enum cest {
                                        value 5;
                                        description "Central European Summer Time";
                                    }
                                    enum edt {
                                        value 6;
                                        description "Eastern Daylight Time";
                                    }
                                    enum eest {
                                        value 7;
                                        description "Eastern European Summer Time";
                                    }
                                    enum mdt {
                                        value 8;
                                        description "Mountain Daylight Time";
                                    }
                                    enum nzdt {
                                        value 9;
                                        description "New Zealand Daylight Time";
                                    }
                                    enum pdt {
                                        value 10;
                                        description "Pacific Daylight Time";
                                    }
                                    enum west {
                                        value 11;
                                        description "Western European Summer Time";
                                    }
                                }
                                description "Standard time zone name";
                            }

                        } // container standard

                    }
                    case non-standard-zone {

                        container non-standard {
                            description "Enter the non-standard context";

                            leaf name {
                                type string {
                                    length "1..5";
                                    pattern "([0-9]|[a-z])+" {
                                        error-message "'name' must contain only lowercase letters and digits (e.g. utc5)";
                                    }
                                }
                                description "Nonstandard summer time zone name";
                            }

                            leaf offset {
                                type uint32 {
                                    range "0..60";
                                }
                                units "minutes";
                                default "60";
                                description "Summer time offset";
                            }

                            container end {
                                description "Enter the end context";

                                leaf week {
                                    type types-system:week;
                                    default "first";
                                    description "Week of the month when summer time ends";
                                }

                                leaf day {
                                    type types-system:day-of-week-name-long;
                                    default "sunday";
                                    description "Day of the week when summer time ends";
                                }

                                leaf month {
                                    type types-system:month-name-long;
                                    default "january";
                                    description "Month when summer time ends";
                                }

                                leaf hours-minutes {
                                    type types-system:hours-minutes-twenty-four;
                                    default "00:00";
                                    description "Time when summer time ends, in hh:mm format";
                                }

                            } // container end

                            container start {
                                description "Enter the start context";

                                leaf week {
                                    type types-system:week;
                                    default "first";
                                    description "Week of the month when summer time starts";
                                }

                                leaf day {
                                    type types-system:day-of-week-name-long;
                                    default "sunday";
                                    description "Day of the week when summer time starts";
                                }

                                leaf month {
                                    type types-system:month-name-long;
                                    default "january";
                                    description "Month when summer time starts";
                                }

                                leaf hours-minutes {
                                    type types-system:hours-minutes-twenty-four;
                                    default "00:00";
                                    description "Time when summer time starts, in hh:mm format";
                                }

                            } // container start

                        } // container non-standard

                    }
                }
            } // container daylight-saving-time-zone

            container ntp {
                presence "Enable the ntp context";
                description "Enable the ntp context";

                leaf authentication-check {
                    type boolean;
                    default "true";
                    description "Authenticate NTP PDUs and reject mismatches";
                }

                leaf admin-state {
                    type types-sros:admin-state;
                    default "disable";
                    description "Administrative state of NTP execution";
                }

                leaf authentication-keychain {
                    type leafref {
                        path "../../../security/keychains/keychain/keychain-name";
                    }
                    description "Authentication keychain for unsolicited traffic";
                }

                leaf max-poll {
                    type types-system:log2seconds {
                        range "4..10";
                    }
                    default "6";
                    description "Value for the maximum polling interval as a power of 2";
                }

                leaf min-poll {
                    type types-system:log2seconds {
                        range "4..10";
                    }
                    default "6";
                    description "Value for the minimum polling interval as a power of 2";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container ntp-server {
                    presence "Enable the ntp-server context";
                    description "Enable the ntp-server context";

                    leaf authenticate {
                        type boolean;
                        default "false";
                        description "Authentication of NTP PDUs when acting as a server";
                    }

                } // container ntp-server

                list server {
                    key "ip-address router-instance";
                    description "Enter the server list instance";

                    leaf ip-address {
                        type union {
                            type types-sros:ip-address;
                            type enumeration {
                                enum ptp                            { value 1; }
                            }
                        }
                        description "IP address of an external NTP server";
                    }

                    leaf router-instance {
                        type string;
                        description "Router name or VPRN service name";
                    }

                    leaf version {
                        type uint32 {
                            range "2..4";
                        }
                        default "4";
                        description "NTP version number generated by the node";
                    }

                    leaf prefer {
                        type boolean;
                        default "false";
                        description "Set NTP server as preferred to receive time";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice key-or-keychain {
                        case key {

                            leaf key-id {
                                type leafref {
                                    path "../../authentication-key/key-id";
                                }
                                description "Authentication key and type used by the node";
                            }

                        }
                        case keychain {

                            leaf authentication-keychain {
                                type leafref {
                                    path "../../../../security/keychains/keychain/keychain-name";
                                }
                                description "Keychain used to authenticate broadcast messages";
                            }

                        }
                    }
                } // list server

                list peer {
                    key "ip-address router-instance";
                    description "Enter the peer list instance";

                    leaf ip-address {
                        type types-sros:ip-address;
                        description "IP address of the peer for a peering relationship";
                    }

                    leaf router-instance {
                        type string;
                        description "Router name or VPRN service name";
                    }

                    leaf version {
                        type uint32 {
                            range "2..4";
                        }
                        default "4";
                        description "NTP version number generated by the node";
                    }

                    leaf prefer {
                        type boolean;
                        default "false";
                        description "Set NTP server as preferred to receive time";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice key-or-keychain {
                        case key {

                            leaf key-id {
                                type leafref {
                                    path "../../authentication-key/key-id";
                                }
                                description "Authentication key and type used by the node";
                            }

                        }
                        case keychain {

                            leaf authentication-keychain {
                                type leafref {
                                    path "../../../../security/keychains/keychain/keychain-name";
                                }
                                description "Keychain used to authenticate broadcast messages";
                            }

                        }
                    }
                } // list peer

                list broadcast {
                    key "router-instance interface-name";
                    description "Enter the broadcast list instance";

                    leaf router-instance {
                        type leafref {
                            path "../../../../../router/router-name";
                        }
                        description "Router name";
                    }

                    leaf interface-name {
                        type types-sros:interface-name;
                        description "Interface to transmit or receive NTP broadcast packets";
                    }

                    leaf version {
                        type uint32 {
                            range "2..4";
                        }
                        default "4";
                        description "NTP version number generated by the node";
                    }

                    leaf ttl {
                        type uint32 {
                            range "1..255";
                        }
                        default "127";
                        description "TTL of messages transmitted by the broadcast address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice key-or-keychain {
                        case key {

                            leaf key-id {
                                type leafref {
                                    path "../../authentication-key/key-id";
                                }
                                description "Authentication key and type used by the node";
                            }

                        }
                        case keychain {

                            leaf authentication-keychain {
                                type leafref {
                                    path "../../../../security/keychains/keychain/keychain-name";
                                }
                                description "Keychain used to authenticate broadcast messages";
                            }

                        }
                    }
                } // list broadcast

                list broadcast-client {
                    key "router-instance interface-name";
                    description "Enter the broadcast-client list instance";

                    leaf router-instance {
                        type string;
                        description "Router name or VPRN service name";
                    }

                    leaf interface-name {
                        type types-sros:interface-name;
                        description "Interface to transmit or receive NTP broadcast packets";
                    }

                    leaf authenticate {
                        type boolean;
                        default "false";
                        description "Enforce authentication of NTP PDUs";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list broadcast-client

                container multicast {
                    presence "Enable the multicast context";
                    description "Enable the multicast context";

                    leaf version {
                        type uint32 {
                            range "2..4";
                        }
                        default "4";
                        description "NTP version number generated by the node";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice key-or-keychain {
                        case key {

                            leaf key-id {
                                type leafref {
                                    path "../../authentication-key/key-id";
                                }
                                description "Authentication key and type used by the node";
                            }

                        }
                        case keychain {

                            leaf authentication-keychain {
                                type leafref {
                                    path "../../../../security/keychains/keychain/keychain-name";
                                }
                                description "Keychain used to authenticate broadcast messages";
                            }

                        }
                    }
                } // container multicast

                container multicast-client {
                    presence "Enable the multicast-client context";
                    description "Enable the multicast-client context";

                    leaf authenticate {
                        type boolean;
                        default "false";
                        description "Enforce authentication of NTP PDUs";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container multicast-client

                list authentication-key {
                    key "key-id";
                    description "Enter the authentication-key list instance";

                    leaf key-id {
                        type uint32 {
                            range "1..255";
                        }
                        description "Authentication key ID used for NTP packets";
                    }

                    leaf key {
                        type types-sros:encrypted-leaf {
                            length "1..126";
                        }
                        mandatory true;
                        description "Key to authenticate NTP packets";
                    }

                    leaf type {
                        type enumeration {
                            enum des                            { value 1; }
                            enum message-digest                 { value 2; }
                        }
                        mandatory true;
                        description "Authentication method to authenticate NTP packet";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list authentication-key

            } // container ntp

            container sntp {
                description "Enter the sntp context";

                leaf sntp-state {
                    type types-router:unicast-broadcast;
                    default "unicast";
                    description "Mode for Simple Network Time Protocol (SNTP)";
                }

                leaf admin-state {
                    type types-sros:admin-state;
                    default "disable";
                    description "Administrative state of SNTP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list server {
                    key "ip-address";
                    description "Enter the server list instance";

                    leaf ip-address {
                        type types-sros:ipv4-address;
                        description "IP address of the SNTP server";
                    }

                    leaf version {
                        type int32 {
                            range "1..3";
                        }
                        default "3";
                        description "SNTP version supported by this server";
                    }

                    leaf prefer {
                        type boolean;
                        default "false";
                        description "Preference value for this SNTP server";
                    }

                    leaf interval {
                        type uint32 {
                            range "64..1024";
                        }
                        units "seconds";
                        default "64";
                        description "Frequency of querying the server";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list server

            } // container sntp

        } // container time

    } // grouping conf-system-time

}
