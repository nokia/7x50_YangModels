submodule nokia-conf-port-dwdm {

    yang-version "1.1";

    belongs-to nokia-conf { prefix "conf"; }

    import nokia-sros-yang-extensions     { prefix "sros-ext"; }
    import nokia-types-port               { prefix "types-port"; }

    include nokia-conf-groups;
    include nokia-conf-port-dwdm-coherent;

    sros-ext:sros-major-release "rel26";
    organization "Nokia";
    contact
        "Nokia SR OS Support
         Web: <http://www.nokia.com>";
    description
        "Nokia YANG Data model to configure dense wavelength division multiplexing ports on SR OS based routers.

         Copyright 2016 Nokia. All rights reserved. Reproduction of this document
         is authorized on the condition that the foregoing copyright notice is included.

         This nokia-conf-port-dwdm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-port-dwdm {
        container dwdm {
            description "Enter the dwdm context";

            leaf channel {
                status obsolete;
                type types-port:optical-dwdm-channel;
                description "DWDM ITU channel number";
            }

            leaf frequency {
                type types-port:optical-dwdm-frequency;
                description "Center frequency for tunable DWDM optical interface";
            }

            leaf rxdtv-adjust {
                status obsolete;
                type boolean;
                description "Adjust the Receive Decision Threshold Voltage (RxDTV)";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container wavetracker {
                status obsolete;
                description "Enter the wavetracker context";

                leaf-list apply-groups {
                    status obsolete;
                    type leafref {
                        path "../../../../groups/group/name";
                    }
                    max-elements 8;
                    ordered-by user;
                    description "Apply a configuration group at this level";
                }

                leaf-list apply-groups-exclude {
                    status obsolete;
                    type leafref {
                        path "../../../../groups/group/name";
                    }
                    max-elements 8;
                    ordered-by user;
                    description "Exclude a configuration group at this level";
                }

                container encode {
                    status obsolete;
                    presence "Enable the encode context";
                    description "Enable the encode context";

                    leaf key1 {
                        status obsolete;
                        type uint32 {
                            range "1..4095";
                        }
                        mandatory true;
                        description "Wavetracker key 1 value";
                    }

                    leaf key2 {
                        status obsolete;
                        type uint32 {
                            range "1..4095";
                        }
                        mandatory true;
                        description "Wavetracker key 2 value";
                    }

                } // container encode

                container power-control {
                    status obsolete;
                    presence "Enable the power-control context";
                    description "Enable the power-control context";

                    leaf target-power {
                        status obsolete;
                        type decimal64 {
                            range "-22..3";
                            fraction-digits 2;
                        }
                        units "decibel-milliwatts";
                        default "-20";
                        description "Desired average output launch power for the DWDM";
                    }

                } // container power-control

                container report-alarm {
                    status obsolete;
                    description "Enter the report-alarm context";

                    leaf encoder-failure {
                        status obsolete;
                        type boolean;
                        default "true";
                        description "Enable the Encoder failure alarm";
                    }

                    leaf encoder-degrade {
                        status obsolete;
                        type boolean;
                        default "true";
                        description "Enable the Encoder degrade alarm";
                    }

                    leaf power-control-failure {
                        status obsolete;
                        type boolean;
                        default "true";
                        description "Enable the Power control failure alarm";
                    }

                    leaf power-control-degrade {
                        status obsolete;
                        type boolean;
                        default "true";
                        description "Enble the Power control degrade alarm";
                    }

                    leaf power-control-high-limit {
                        status obsolete;
                        type boolean;
                        default "true";
                        description "Enable the Power control high limit alarm";
                    }

                    leaf power-control-low-limit {
                        status obsolete;
                        type boolean;
                        default "true";
                        description "Enable the Power control low limit alarm";
                    }

                    leaf missing-pluggable-voa {
                        status obsolete;
                        type boolean;
                        default "true";
                        description "Enable the wavelength or Wavetracker missing alarm";
                    }

                } // container report-alarm

            } // container wavetracker

            uses conf-port-dwdm-coherent;
        } // container dwdm

    } // grouping conf-port-dwdm

}
