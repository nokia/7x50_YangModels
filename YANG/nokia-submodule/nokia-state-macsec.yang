submodule nokia-state-macsec {

    yang-version "1.1";

    belongs-to nokia-state { prefix "state"; }

    import ietf-yang-types                { prefix "yang"; }
    import nokia-sros-yang-extensions     { prefix "sros-ext"; }
    import nokia-types-security           { prefix "types-security"; }
    import nokia-types-sros               { prefix "types-sros"; }

    sros-ext:sros-major-release "rel26";
    organization "Nokia";
    contact
        "Nokia SR OS Support
         Web: <http://www.nokia.com>";
    description
        "Nokia YANG Data model with operational state for MACsec connectivity-association configuration on SR OS based routers.

         Copyright 2016 Nokia. All rights reserved. Reproduction of this document
         is authorized on the condition that the foregoing copyright notice is included.

         This nokia-state-macsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping state-macsec {
        container macsec {
            description "Enter the macsec context";

            list connectivity-association {
                key "ca-name";
                description "Enter the connectivity-association list instance";

                leaf ca-name {
                    type string {
                        length "1..32";
                    }
                    description "The name of the connectivity association.";
                }

                list port {
                    key "port-id sub-port-id";
                    description "Enter the port list instance";

                    leaf port-id {
                        type types-sros:port;
                        description "Port identifier.";
                    }

                    leaf sub-port-id {
                        type int32 {
                            range "1..1023";
                        }
                        description "Sub-port ID on the port.";
                    }

                    list psk-history-entry {
                        key "entry-index";
                        description "Enter the psk-history-entry list instance";

                        leaf entry-index {
                            type uint32;
                            description "The index of a recently used PSK.";
                        }

                        leaf start-time {
                            type yang:date-and-time;
                            description "UTC date and time when the PSK became active.";
                        }

                        leaf psk-source {
                            type types-security:psk-source;
                            description "The source of the PSK.";
                        }

                        leaf cak-name {
                            type string {
                                length "2..64";
                            }
                            description "CAK name for the PSK.";
                        }

                        leaf encrypted-distributed-cak {
                            type string;
                            description "AES Key Wrap of the Distributed CAK as transmitted or received on the wire.";
                        }

                    } // list psk-history-entry

                    container auto-gen-psk {
                        description "Enter the auto-gen-psk context";

                        leaf next-psk-generate-time {
                            type yang:date-and-time;
                            description "UTC date and time when the next PSK will be generated.";
                        }

                    } // container auto-gen-psk

                } // list port

                list anysec-peer {
                    key "encryption-group-name peer-ip-address";
                    description "Enter the anysec-peer list instance";

                    leaf encryption-group-name {
                        type types-sros:named-item;
                        description "Encryption group name.";
                    }

                    leaf peer-ip-address {
                        type types-sros:ip-unicast-address;
                        description "Peer IP address.";
                    }

                    list psk-history-entry {
                        key "entry-index";
                        description "Enter the psk-history-entry list instance";

                        leaf entry-index {
                            type uint32;
                            description "The index of a recently used PSK.";
                        }

                        leaf start-time {
                            type yang:date-and-time;
                            description "UTC date and time when the PSK became active.";
                        }

                        leaf psk-source {
                            type types-security:psk-source;
                            description "The source of the PSK.";
                        }

                        leaf cak-name {
                            type string {
                                length "2..64";
                            }
                            description "CAK name for the PSK.";
                        }

                        leaf encrypted-distributed-cak {
                            type string;
                            description "AES Key Wrap of the Distributed CAK as transmitted or received on the wire.";
                        }

                    } // list psk-history-entry

                    container auto-gen-psk {
                        description "Enter the auto-gen-psk context";

                        leaf next-psk-generate-time {
                            type yang:date-and-time;
                            description "UTC date and time when the next PSK will be generated.";
                        }

                    } // container auto-gen-psk

                } // list anysec-peer

            } // list connectivity-association

        } // container macsec

    } // grouping state-macsec

}
