submodule nokia-state-esa {

    yang-version "1.1";

    belongs-to nokia-state { prefix "state"; }

    import ietf-yang-types                { prefix "yang"; }
    import nokia-sros-yang-extensions     { prefix "sros-ext"; }
    import nokia-types-esa                { prefix "types-esa"; }
    import nokia-types-services           { prefix "types-services"; }
    import nokia-types-sros               { prefix "types-sros"; }

    sros-ext:sros-major-release "rel26";
    organization "Nokia";
    contact
        "Nokia SR OS Support
         Web: <http://www.nokia.com>";
    description
        "Nokia YANG Data model with operational state for ESA configuration on SR OS based routers.

         Copyright 2016 Nokia. All rights reserved. Reproduction of this document
         is authorized on the condition that the foregoing copyright notice is included.

         This nokia-state-esa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-esa {
        list esa {
            key "esa-id";
            description "Enter the esa list instance";

            leaf esa-id {
                type types-esa:esa-id;
                description "The ID of the ESA.";
            }

            leaf oper-state {
                type enumeration {
                    enum unknown                        { value 1; }
                    enum in-service                     { value 2; }
                    enum out-of-service                 { value 3; }
                    enum booting                        { value 4; }
                    enum failed                         { value 5; }
                    enum provisioned                    { value 6; }
                    enum unprovisioned                  { value 7; }
                    enum upgrade                        { value 8; }
                    enum fw-upgrade                     { value 9; }
                    enum fw-upgrade-nic                 { value 10; }
                    enum fw-upgrade-sps                 { value 11; }
                    enum fw-upgrade-system-rom          { value 12; }
                    enum fw-upgrade-setting             { value 13; }
                    enum fw-upgrade-bmc                 { value 14; }
                    enum fw-upgrade-bmc-setting         { value 15; }
                    enum fw-upgrade-ie                  { value 16; }
                }
                description "Indicates the operational state of the ESA.";
            }

            leaf oper-flags {
                type bits {
                    bit admin-down                     { position 0; }
                    bit esa-sw-mismatch                { position 1; }
                    bit esa-mismatch                   { position 2; }
                    bit connect-failed                 { position 3; }
                    bit fw-update-failed               { position 4; }
                    bit boot-failed                    { position 5; }
                    bit fw-update-required             { position 6; }
                    bit unexpected-fw-version          { position 7; }
                }
                description
                    "Indicates the operational flags that determine the status
                     of the ESA.";
            }

            leaf cores-available {
                type yang:gauge32;
                description "Indicates the total number of available cores on the ESA.";
            }

            leaf cores-allocated {
                type yang:gauge32;
                description "Indicates the total number of allocated cores on the ESA.";
            }

            leaf memory-available {
                type yang:gauge32;
                units "gigabytes";
                description
                    "Indicates the total amount of available memory (in GigaBytes)
                     on the ESA.";
            }

            leaf memory-allocated {
                type yang:gauge32;
                units "gigabytes";
                description
                    "Indicates the total amount of allocated memory (in GigaBytes)
                     on the ESA.";
            }

            leaf software-version {
                type string {
                    length "0..255";
                }
                description "Indicates the software version currently running on the ESA.";
            }

            leaf time-of-boot {
                type yang:date-and-time;
                description
                    "Indicates date and time the software running on this
                     ESA was last rebooted.";
            }

            leaf system-manufacturer {
                type string {
                    length "0..255";
                }
                description "Indicates the system manufacturer of the ESA.";
            }

            leaf system-product-name {
                type string {
                    length "0..255";
                }
                description "Indicates the system product name of the ESA.";
            }

            leaf system-serial-number {
                type string {
                    length "0..255";
                }
                description "Indicates the system serial number of the ESA.";
            }

            leaf performance-mode {
                type boolean;
                description
                    "Indicates whether the ESA is in performance (true)
                     or functional (false) mode.";
            }

            leaf export-restricted {
                type boolean;
                description
                    "Indicates whether the ESA is in export restricted mode or not.
                     In this mode, some restrictions apply to certain vm types.";
            }

            leaf hardware-status {
                type enumeration {
                    enum unknown                        { value 1; }
                    enum ok                             { value 2; }
                    enum degraded                       { value 3; }
                    enum critical                       { value 4; }
                    enum unsupported                    { value 5; }
                }
                description "Indicates the hardware status reported by the ESA.";
            }

            leaf power-supply-1-status {
                type types-esa:esa-device-state;
                description "Indicates the status of power supply 1 as reported by the ESA.";
            }

            leaf power-supply-2-status {
                type types-esa:esa-device-state;
                description "Indicates the status of power supply 2 as reported by the ESA.";
            }

            leaf power-supply-1-temp {
                type int32;
                units "degrees celsius";
                description
                    "Indicates the temperature of power supply 1 as reported by the ESA.
                     This is only supported on ESA-100G.
                     A temperature of 0 means that this is not supported and
                     not possible to retrieve on the ESA.";
            }

            leaf power-supply-2-temp {
                type int32;
                units "degrees celsius";
                description
                    "Indicates the temperature of power supply 2 as reported by the ESA.
                     This is only supported on ESA-100G.
                     A temperature of 0 means that this is not supported and
                     not possible to retrieve on the ESA.";
            }

            leaf fan-redundancy {
                type types-esa:esa-device-redundancy-state;
                description "Indicates the fan redundancy status as reported by the ESA.";
            }

            leaf fan-status {
                type types-esa:esa-device-state;
                description "Indicates the fan status as reported by the ESA.";
            }

            leaf power-supply-mismatch-status {
                type types-esa:esa-device-mismatch-state;
                description "Indicates the mismatch status of power supplies as reported by the ESA.";
            }

            leaf power-supply-redundancy {
                type types-esa:esa-device-redundancy-state;
                description "Indicates the redundancy status of power supplies as reported by the ESA.";
            }

            leaf temperature-status {
                type types-esa:esa-device-state;
                description
                    "Indicates the temperature status as reported by the ESA, as follows:
                        - Ok      : Temperature within normal operating range.
                        - Degraded: Temperature is outside the normal operating range.
                                    Depending on the system configuration, this system
                                    might be shut down.
                        - Failed  : Temperature exceeded on the ESA.";
            }

            leaf cpu-1-temperature {
                type int32;
                units "degrees celsius";
                description
                    "Indicates the CPU temperature as reported by the ESA.
                     A temperature of 0 means that this is not supported and
                     not possible to retrieve on the ESA. ";
            }

            leaf cpu-2-temperature {
                type int32;
                units "degrees celsius";
                description
                    "Indicates the CPU temperature as reported by the ESA.
                     A temperature of 0 means that this is not supported and
                     not possible to retrieve on the ESA. ";
            }

            leaf system-part-number {
                type string {
                    length "0..255";
                }
                description "Indicates the system part number of the ESA.";
            }

            leaf power-supply-1-voltage {
                type int32;
                units "volts";
                description
                    "Indicates the voltage of power supply 1 as reported by the ESA.
                     A voltage of 0 means that this is not supported and
                     not possible to retrieve on the ESA.";
            }

            leaf power-supply-2-voltage {
                type int32;
                units "volts";
                description
                    "Indicates the voltage of power supply 2 as reported by the ESA.
                     A voltage of 0 means that this is not supported and
                     not possible to retrieve on the ESA.";
            }

            leaf power-supply-1-output-power {
                type int32;
                units "watts";
                description
                    "Indicates the output power of power supply 1 as reported by the ESA.
                     An output power of 0 means that this is not supported and
                     not possible to retrieve on the ESA.";
            }

            leaf power-supply-2-output-power {
                type int32;
                units "watts";
                description
                    "Indicates the output power of power supply 2 as reported by the ESA.
                     An output power of 0 means that this is not supported and
                     not possible to retrieve on the ESA.";
            }

            leaf power-supply-1-maximum-power {
                type int32;
                units "watts";
                description
                    "Indicates the maximum power used by power supply 1 as reported by the ESA.
                     A maximum power of 0 means that this is not supported and
                     not possible to retrieve on the ESA.";
            }

            leaf power-supply-2-maximum-power {
                type int32;
                units "watts";
                description
                    "Indicates the maximum power used by power supply 2 as reported by the ESA.
                     A maximum power of 0 means that this is not supported and
                     not possible to retrieve on the ESA.";
            }

            leaf cpu-1-temperature-threshold {
                type int32;
                units "degrees celsius";
                description
                    "Indicates the temperature caution threshold for cpu 1 as reported by the ESA.
                     A temperature threshold of 0 means that this is not supported and
                     not possible to retrieve on the ESA.";
            }

            leaf cpu-2-temperature-threshold {
                type int32;
                units "degrees celsius";
                description
                    "Indicates the temperature caution threshold for cpu 2 as reported by the ESA.
                     A temperature threshold of 0 means that this is not supported and
                     not possible to retrieve on the ESA.";
            }

            leaf nic-1-temperature {
                type int32;
                units "degrees celsius";
                description
                    "Indicates the temperature of nic 1 as reported by the ESA.
                     A temperature of 0 means that this is not supported and
                     not possible to retrieve on the ESA. ";
            }

            leaf nic-2-temperature {
                type int32;
                units "degrees celsius";
                description
                    "Indicates the temperature of nic 2 as reported by the ESA.
                     A temperature of 0 means that this is not supported and
                     not possible to retrieve on the ESA. ";
            }

            leaf nic-1-temperature-threshold {
                type int32;
                units "degrees celsius";
                description
                    "Indicates the temperature caution threshold for nic 1 as reported by the ESA.
                     A temperature threshold of 0 means that this is not supported and
                     not possible to retrieve on the ESA.";
            }

            leaf nic-2-temperature-threshold {
                type int32;
                units "degrees celsius";
                description
                    "Indicates the temperature caution threshold for nic 2 as reported by the ESA.
                     A temperature threshold of 0 means that this is not supported and
                     not possible to retrieve on the ESA.";
            }

            list host-port {
                key "host-port";
                description "Enter the host-port list instance";

                leaf host-port {
                    type types-sros:port;
                    description "Host port IDs for this ESA.";
                }

                leaf socket-id {
                    type uint32;
                    description "Indicates the socket number that the ESA host port resides on.";
                }

                leaf nic-if-name {
                    type types-sros:display-string;
                    description "Indicates the nic interface name that the ESA host port is connected to.";
                }

                leaf transceiver-type {
                    type enumeration {
                        enum unknown                        { value 0; }
                        enum gbic                           { value 1; }
                        enum mod-connector-soldered-motherboard { value 2; }
                        enum sfp-transceiver                { value 3; }
                        enum xbi-transceiver                { value 4; }
                        enum xenpak-transceiver             { value 5; }
                        enum xfp-transceiver                { value 6; }
                        enum xff-transceiver                { value 7; }
                        enum xfpe-transceiver               { value 8; }
                        enum xpak-transceiver               { value 9; }
                        enum x2-transceiver                 { value 10; }
                        enum dwdm-sfp-transceiver           { value 11; }
                        enum qsfp-transceiver               { value 12; }
                        enum qsfp-plus-transceiver          { value 13; }
                        enum cfp-transceiver                { value 14; }
                        enum cxp-transceiver                { value 15; }
                        enum oif-msa100g-lh                 { value 16; }
                        enum cfp2-or-qsfp28-transceiver     { value 17; }
                        enum cfp4-transceiver               { value 18; }
                        enum cdfp-transceiver               { value 19; }
                        enum cfp2-aco-transceiver           { value 20; }
                        enum cfp8-transceiver               { value 21; }
                        enum cdfp3-transceiver              { value 22; }
                        enum micro-qsfp-transceiver         { value 23; }
                        enum qsfp-dd-transceiver            { value 24; }
                        enum cfp2-dco-transceiver           { value 25; }
                        enum sfp-dd-transceiver             { value 26; }
                        enum dsfp-transceiver               { value 27; }
                        enum x4-mini-link-transceiver       { value 28; }
                        enum x8-mini-link-transceiver       { value 29; }
                        enum qsfp-plus-or-later-cmis-transceiver { value 30; }
                        enum sfp-dd-with-cmis-transceiver   { value 31; }
                        enum sfp-plus-or-later-cmis-transceiver { value 32; }
                    }
                    description "The container of type of the transceiver.";
                }

                leaf transceiver-model-number {
                    type types-sros:named-item-255-or-empty;
                    description
                        "Indicates the model information for the transceiver,
                         as read from the transceiver EEPROM.";
                }

                leaf transceiver-laser-wave-length {
                    type uint32;
                    description
                        "The light wavelength transmitted by the transceiver's laser.
                         A value of zero indicates that the port is not equipped with
                         the transceiver.";
                }

                leaf sfp-num-lanes {
                    type uint32;
                    description "Indicates the total number of lanes supported by the CSFP/QSFP.";
                }

                leaf sfp-connector-code {
                    type enumeration {
                        enum unknown                        { value 0; }
                        enum sc                             { value 1; }
                        enum fiber-channel-style1-copper-connector { value 2; }
                        enum fiber-channel-style2-copper-connector { value 3; }
                        enum bncortnc                       { value 4; }
                        enum fiber-channel-coaxial-headers  { value 5; }
                        enum fiber-jack                     { value 6; }
                        enum lc                             { value 7; }
                        enum mt-rj                          { value 8; }
                        enum mu                             { value 9; }
                        enum sg                             { value 10; }
                        enum optical-pigtail                { value 11; }
                        enum mpo1x12                        { value 12; }
                        enum mpo2x16                        { value 13; }
                        enum hssdc-ii                       { value 32; }
                        enum copper-pigtail                 { value 33; }
                        enum rj45                           { value 34; }
                        enum no-sep-conn                    { value 35; }
                        enum mxc2x16                        { value 36; }
                        enum cs                             { value 37; }
                        enum sn-opt-conn                    { value 38; }
                        enum mpo2x12                        { value 39; }
                        enum mpo1x16                        { value 40; }
                        enum optical-transceiver            { value 51; }
                        enum copper-gige                    { value 128; }
                        enum rjp5                           { value 129; }
                    }
                    description "The external connector provided on the interface.";
                }

                leaf sfp-vendor-oui {
                    type string;
                    description
                        "The vendor organizationally unique identifier field (OUI)
                         contains the IEEE company identifier for the vendor.
                         A value of all zero indicates that the vendor OUI
                         is unspecified.";
                }

                leaf sfp-vendor-manufacture-date {
                    type types-sros:date-time;
                    description "The vendor's date code.";
                }

                leaf sfp-media {
                    type enumeration {
                        enum not-applicable                 { value 0; }
                        enum ethernet                       { value 1; }
                        enum sonetsdh                       { value 2; }
                    }
                    description "Indicates the media supported for the SFF (Small Form Factor).";
                }

                leaf sfp-vendor-serial-number {
                    type types-sros:named-item-255-or-empty;
                    description
                        "Indicates the transceiver's vendor serial number in ASCII characters,
                         as read from the transceiver EEPROM.";
                }

                leaf sfp-vendor-part-number {
                    type types-sros:named-item-255-or-empty;
                    description
                        "Indicates the transceiver's vendor part number (or product name) in ASCII
                         characters, as read from the transceiver EEPROM.";
                }

                leaf optical-compliance {
                    type string {
                        length "23";
                    }
                    description "Indicates the 64 bytes of optical compliance bits stored in SFF EEPROMs.";
                }

                leaf optical-compliance-extension {
                    type int32;
                    description "Indicates the optical compliance extension stored in SFF EEPROMs.";
                }

                leaf link-length-info {
                    type binary {
                        length "6";
                    }
                    description "Indicates the link length info stored in SFF EEPROMs.";
                }

                container ddm-temperature {
                    description "Enter the ddm-temperature context";

                    leaf current {
                        type decimal64 {
                            fraction-digits 1;
                        }
                        units "degrees celsius";
                        description "Indicates the current temperature of the SFF in 1/256th degrees Celsius.";
                    }

                    leaf high-alarm {
                        type decimal64 {
                            fraction-digits 1;
                        }
                        units "degrees celsius";
                        description "Indicates the temperature of the SFF that triggers a hi-alarm.";
                    }

                    leaf high-warning {
                        type decimal64 {
                            fraction-digits 1;
                        }
                        units "degrees celsius";
                        description "Indicates the temperature of the SFF that triggers a hi-warning.";
                    }

                    leaf low-warning {
                        type decimal64 {
                            fraction-digits 1;
                        }
                        units "degrees celsius";
                        description "Indicates the temperature of the SFF that triggers a low-warning.";
                    }

                    leaf low-alarm {
                        type decimal64 {
                            fraction-digits 1;
                        }
                        units "degrees celsius";
                        description "Tndicates the temperature of the SFF that triggers a low-alarm.";
                    }

                } // container ddm-temperature

                container ddm-supply-voltage {
                    description "Enter the ddm-supply-voltage context";

                    leaf current {
                        type decimal64 {
                            fraction-digits 2;
                        }
                        units "volts";
                        description
                            "Indicates the current supply-voltage of the SFF. For 100G MSA
                             Transponder, the supply voltage is in millivolts (mV). For all
                             other types the voltage is in deci-millivolts (1/10th of a millivolt
                             or 100 microvolt units).";
                    }

                    leaf high-alarm {
                        type decimal64 {
                            fraction-digits 2;
                        }
                        units "volts";
                        description "Indicates the supply voltage of the SFF that triggers a hi-alarm.";
                    }

                    leaf high-warning {
                        type decimal64 {
                            fraction-digits 2;
                        }
                        units "volts";
                        description "Indicates the supply voltage of the SFF that triggers a hi-warning.";
                    }

                    leaf low-warning {
                        type decimal64 {
                            fraction-digits 2;
                        }
                        units "volts";
                        description "Indicates the supply voltage of the SFF that trigger a low-warning.";
                    }

                    leaf low-alarm {
                        type decimal64 {
                            fraction-digits 2;
                        }
                        units "volts";
                        description "Indicates the supply voltage of the SFF that triggers a low-alarm.";
                    }

                } // container ddm-supply-voltage

                container ddm-tx-bias-current {
                    description "Enter the ddm-tx-bias-current context";

                    leaf high-alarm {
                        type decimal64 {
                            fraction-digits 1;
                        }
                        units "microamperes";
                        description "Indicates the Transmit Bias Current of the SFF that triggers a hi-alarm.";
                    }

                    leaf high-warning {
                        type decimal64 {
                            fraction-digits 1;
                        }
                        units "microamperes";
                        description "Indicates the Transmit Bias Current of the SFF that triggers a hi-warning.";
                    }

                    leaf low-warning {
                        type decimal64 {
                            fraction-digits 1;
                        }
                        units "microamperes";
                        description "Indicates the Transmit Bias Current of the SFF that triggers a low-warning.";
                    }

                    leaf low-alarm {
                        type decimal64 {
                            fraction-digits 1;
                        }
                        units "microamperes";
                        description "Indicates the Transmit Bias Current of the SFF that triggers a low-alarm.";
                    }

                } // container ddm-tx-bias-current

                container ddm-tx-output-power {
                    description "Enter the ddm-tx-output-power context";

                    leaf high-alarm {
                        type decimal64 {
                            fraction-digits 2;
                        }
                        units "decibel-milliwatts";
                        description
                            "Indicates the Output Power of the SFF in one tenths of a microwatt (uW) that triggers a
                             hi-alarm.";
                    }

                    leaf high-warning {
                        type decimal64 {
                            fraction-digits 2;
                        }
                        units "decibel-milliwatts";
                        description
                            "Indicates the Output Power of the SFF in one tenths of a microwatt (uW) that triggers a
                             hi-warning.";
                    }

                    leaf low-warning {
                        type decimal64 {
                            fraction-digits 2;
                        }
                        units "decibel-milliwatts";
                        description
                            "Indicates the Output Power of the SFF in one tenths of a microwatt (uW) that triggers a
                             low-warning.";
                    }

                    leaf low-alarm {
                        type decimal64 {
                            fraction-digits 2;
                        }
                        units "decibel-milliwatts";
                        description
                            "Indicates the Output Power of the SFF in one tenths of a microwatt (uW) that triggers a
                             low-alarm.";
                    }

                } // container ddm-tx-output-power

                container ddm-tx-optical-power {
                    description "Enter the ddm-tx-optical-power context";

                    leaf high-alarm {
                        type decimal64 {
                            fraction-digits 2;
                        }
                        units "decibel-milliwatts";
                        description
                            "Indicates the Received Optical Power of the SFF in one tenths of a microwatt (uW) that
                             triggers a hi-alarm.";
                    }

                    leaf high-warning {
                        type decimal64 {
                            fraction-digits 2;
                        }
                        units "decibel-milliwatts";
                        description
                            "Indicates the Received Optical Power of the SFF in one tenths of a microwatt (uW) that
                             triggers a hi-warning.";
                    }

                    leaf low-warning {
                        type decimal64 {
                            fraction-digits 2;
                        }
                        units "decibel-milliwatts";
                        description
                            "Indicates the Received Optical Power of the SFF in one tenths of a microwatt (uW) that
                             triggers a low-warning.";
                    }

                    leaf low-alarm {
                        type decimal64 {
                            fraction-digits 2;
                        }
                        units "decibel-milliwatts";
                        description
                            "Indicates the Received Optical Power of the SFF in one tenths of a microwatt (uW) that
                             triggers a low-alarm.";
                    }

                } // container ddm-tx-optical-power

                list nic-ddm-lane {
                    key "ddm-lane-id";
                    description "Enter the nic-ddm-lane list instance";

                    leaf ddm-lane-id {
                        type uint32 {
                            range "1..16";
                        }
                        description "The ID of the DDM lane";
                    }

                    leaf ddm-lane-tx-bias-current {
                        type decimal64 {
                            fraction-digits 1;
                        }
                        units "microamperes";
                        description "Indicates the current Transmit Bias Current of the SFF in 1/500 milliamperes (mA).";
                    }

                    leaf ddm-lane-rx-output-power {
                        type decimal64 {
                            fraction-digits 2;
                        }
                        units "decibel-milliwatts";
                        description "Indicates the current Output Power of the SFF in one tenths of a microwatt (uW).";
                    }

                    leaf ddm-lane-rx-optical-power {
                        type decimal64 {
                            fraction-digits 2;
                        }
                        units "decibel-milliwatts";
                        description "Indicates the current Received Optical Power of the SFF in one tenths of a microwatt (uW).";
                    }

                } // list nic-ddm-lane

                container port-monitoring {
                    description "Enter the port-monitoring context";

                    leaf oper-state {
                        type enumeration {
                            enum unknown                        { value 1; }
                            enum in-service                     { value 2; }
                            enum out-of-service                 { value 3; }
                        }
                        description "Indicates the operational status of the ESA interface connected to this port.";
                    }

                    leaf fwd-status {
                        type boolean;
                        description "Indicates the control traffic forwarding status of the ESA interface connected to this port.";
                    }

                    leaf rx-total-pkts {
                        type yang:counter64;
                        description "Indicates the total packets received on the ESA interface connected to this port.";
                    }

                    leaf tx-total-pkts {
                        type yang:counter64;
                        description "Indicates the total packets transmitted on the ESA interface connected to this port.";
                    }

                    leaf rx-discards {
                        type yang:counter64;
                        description "Indicates the total received packets discarded on the ESA interface connected to this port.";
                    }

                    leaf rx-crc-errors {
                        type yang:counter64;
                        description "Indicates the number of crc errors on packets received on the ESA interface connected to this port.";
                    }

                    leaf rx-symbol-errors {
                        type yang:counter64;
                        description "Indicates the number of symbol errors on packets received on the ESA interface connected to this port.";
                    }

                } // container port-monitoring

            } // list host-port

            list vm {
                key "vm-id";
                description "Enter the vm list instance";

                leaf vm-id {
                    type types-esa:vm-id;
                    description "The ID of the VM.";
                }

                leaf oper-state {
                    type enumeration {
                        enum unknown                        { value 1; }
                        enum in-service                     { value 2; }
                        enum out-of-service                 { value 3; }
                        enum booting                        { value 4; }
                        enum failed                         { value 5; }
                        enum provisioned                    { value 6; }
                        enum unprovisioned                  { value 7; }
                        enum upgrade                        { value 8; }
                    }
                    description "Indicates the operational state of the ESA VM.";
                }

                leaf oper-flags {
                    type bits {
                        bit admin-down                     { position 0; }
                        bit boot-failure                   { position 1; }
                        bit out-of-esa-rsrcs               { position 2; }
                        bit connect-failed                 { position 3; }
                        bit provision-fail                 { position 4; }
                        bit core-failure                   { position 5; }
                        bit forced-failure                 { position 6; }
                        bit icc-failure                    { position 7; }
                        bit export-restricted              { position 8; }
                        bit sw-ver-mismatch                { position 9; }
                        bit insufficient-core-allocation   { position 10; }
                        bit insufficient-memory-allocation { position 11; }
                        bit host-port-conn-fail            { position 12; }
                        bit vm-cores-exceed-os-limit       { position 13; }
                    }
                    description
                        "Indicates the operational flags that determine the status of
                         the ESA VM.";
                }

                leaf time-of-boot {
                    type yang:date-and-time;
                    description
                        "Indicates date and time the software running on this ESA VM was
                         last rebooted.";
                }

                leaf software-version {
                    type string {
                        length "0..255";
                    }
                    description "Indicates the software version currently running on the ESA VM.";
                }

                leaf core-util-last-coll {
                    type yang:date-and-time;
                    description
                        "Indicates the time since system startup, when the core utilization
                         statistics were last collected.";
                }

                container tunnel {
                    description "Enter the tunnel context";

                    container ipsec {
                        description "Enter the ipsec context";

                        list lockout-client {
                            key "public-service local-gateway-address address port";
                            description "Enter the lockout-client list instance";

                            leaf public-service {
                                type types-services:service-name;
                                description
                                    "The value of router-service-name is 'Base' for IES services.
                                     The value of router-service-name is the name of the service for VPRN services.";
                            }

                            leaf local-gateway-address {
                                type types-sros:ip-address;
                                description "The IP address of the local SAP IPsec gateway.";
                            }

                            leaf address {
                                type types-sros:ip-address;
                                description "The IP address of the lockout client.";
                            }

                            leaf port {
                                type union {
                                    type enumeration {
                                        enum all {
                                            value 0;
                                            description "all ports under the lockout client address are locked out";
                                        }
                                    }
                                    type types-sros:tcp-udp-port-non-zero;
                                }
                                description
                                    "The port number of the lockout client.
                                     The value 'all' means that all ports under
                                     the lockout client address are locked out.";
                            }

                            leaf lockout {
                                type boolean;
                                description
                                    "Indicates whether a client is locked out by the system.

                                     The value of 'true' indicates that the client is locked out and
                                     all IKE traffics from this client are rejected by the system.
                                     The value of 'false' indicates that the system still accepts IKE
                                     traffic from this client but the client has failed on certain
                                     IKE authentications.";
                            }

                            leaf remaining-block-time {
                                type union {
                                    type enumeration {
                                        enum infinite {
                                            value 0;
                                            description "the client will never be unblocked";
                                        }
                                    }
                                    type types-sros:time-duration {
                                        range "1..max";
                                    }
                                }
                                description
                                    "The time remaining until this client is unblocked.

                                     A value of 'infinite' indicates that this client will never be unblocked.";
                            }

                            container statistics {
                                description "Enter the statistics context";

                                leaf failed-attempts {
                                    type yang:counter32;
                                    description
                                        "The number of failed authentication attempts from the lockout client
                                         within the lockout duration.";
                                }

                                leaf dropped-packets {
                                    type yang:counter32;
                                    description "The number of dropped packets for the lockout client.";
                                }

                            } // container statistics

                        } // list lockout-client

                    } // container ipsec

                    container statistics {
                        description "Enter the statistics context";

                        container datapath {
                            description "Enter the datapath context";

                            leaf encrypted-packets {
                                type yang:counter64;
                                description "The number of packets encrypted by the IPsec data path";
                            }

                            leaf encrypted-bytes {
                                type yang:counter64;
                                description "The number of bytes encrypted by the IPsec data path";
                            }

                            leaf decrypted-packets {
                                type yang:counter64;
                                description "The number of packets decrypted by the IPsec data path";
                            }

                            leaf decrypted-bytes {
                                type yang:counter64;
                                description "The number of bytes decrypted by the IPsec data path";
                            }

                            leaf outbound-dropped-packets {
                                type yang:counter64;
                                description
                                    "The number of packets dropped before and during outbound (encryption)
                                     processing by the IPsec data path.";
                            }

                            leaf outbound-sa-misses {
                                type yang:counter64;
                                description
                                    "The number of packets dropped before outbound (encryption) processing by
                                     the IPsec data path due to no SA (security association) present.";
                            }

                            leaf outbound-policy-entry-misses {
                                type yang:counter32;
                                description
                                    "The number of packets dropped before outbound (encryption) processing
                                     by the IPsec data path due to no matching Policy Entry.";
                            }

                            leaf inbound-dropped-packets {
                                type yang:counter64;
                                description
                                    "The number of packets dropped before and during inbound (decryption)
                                     processing by the IPsec data path.";
                            }

                            leaf inbound-sa-misses {
                                type yang:counter64;
                                description
                                    "The number of packets dropped before inbound (decryption) processing by
                                     the IPsec data path due to no SA (security association) present.";
                            }

                            leaf inbound-ip-dst-src-mismatches {
                                type yang:counter32;
                                description
                                    "The the number of packets dropped before inbound (decryption) processing
                                     by the IPsec data path due to the received packet's outer IP
                                     destination or source address does not match the Tunnel's local or
                                     peer gateway address.";
                            }

                            leaf transmit-packet-errors {
                                type yang:counter32;
                                description "The number of packets transmit failures by the IPsec data path.";
                            }

                            leaf fragments-received {
                                type yang:counter64;
                                description "The number of fragments received by the IPsec data path.";
                            }

                            leaf reassembled-packets {
                                type yang:counter64;
                                description "The number of packets reassembled by the IPsec data path.";
                            }

                            leaf fragment-timeout-drops {
                                type yang:counter64;
                                description "The number of fragments dropped due to timeout by the IPsec data path.";
                            }

                            leaf fragments-total-drops {
                                type yang:counter64;
                                description "The number of total fragments dropped by the IPsec data path.";
                            }

                            leaf drop-too-big-df-set-packets {
                                type yang:counter64;
                                description
                                    "The number of packets with DF bit set dropped in this Tunnel exceeding MTU size
                                     and with clear tunnel DF bit not set.";
                            }

                            container gre-ip-tnl {
                                description "Enter the gre-ip-tnl context";

                                leaf received-packets {
                                    type yang:counter64;
                                    description "The number of packets received by the GRE tunnel data path.";
                                }

                                leaf received-bytes {
                                    type yang:counter64;
                                    description "The number of bytes received by the GRE tunnel data path.";
                                }

                                leaf received-errors {
                                    type yang:counter64;
                                    description "The number of packets dropped while receiving by the GRE tunnel data path";
                                }

                                leaf sent-packets {
                                    type yang:counter64;
                                    description "The number of packets transmitted by the GRE tunnel data path.";
                                }

                                leaf sent-bytes {
                                    type yang:counter64;
                                    description "The number of bytes transmitted by the GRE tunnel data path.";
                                }

                                leaf sent-errors {
                                    type yang:counter64;
                                    description "The number of packets dropped while transmitting by the GRE tunnel data path";
                                }

                            } // container gre-ip-tnl

                            container l2tpv3-tnl {
                                description "Enter the l2tpv3-tnl context";

                                leaf received-packets {
                                    type yang:counter64;
                                    description "The number of packets received by the L2TPv3 tunnel data path.";
                                }

                                leaf received-bytes {
                                    type yang:counter64;
                                    description "The number of bytes received by the L2TPv3 tunnel data path.";
                                }

                                leaf received-errors {
                                    type yang:counter64;
                                    description "The number of packets dropped while receiving by the L2TPv3 tunnel data path";
                                }

                                leaf sent-packets {
                                    type yang:counter64;
                                    description "The number of packets transmitted by the L2TPv3 tunnel data path.";
                                }

                                leaf sent-bytes {
                                    type yang:counter64;
                                    description "The number of bytes transmitted by the L2TPv3 tunnel data path.";
                                }

                                leaf sent-errors {
                                    type yang:counter64;
                                    description "The number of packets dropped while transmitting by the L2TPv3 tunnel data path.";
                                }

                            } // container l2tpv3-tnl

                        } // container datapath

                        container control {
                            description "Enter the control context";

                            leaf static-ipsec-tunnels {
                                type yang:counter32;
                                description "The number of configured static IPsec tunnels on the MDA.";
                            }

                            leaf dynamic-ipsec-tunnels {
                                type yang:counter32;
                                description "The number of dynamic IPsec tunnels in use on the MDA.";
                            }

                            leaf ip-gre-tunnels {
                                type yang:counter32;
                                description "The number of configured IP tunnels (with GRE headers) on the MDA.";
                            }

                            leaf ip-tunnels {
                                type yang:counter32;
                                description "The number of configured IPv4 tunnels on the MDA.";
                            }

                            leaf l2tpv3-tunnels {
                                type yang:counter32;
                                description "The number of configured L2TPv3 tunnels on the MDA.";
                            }

                        } // container control

                        container cpu-usage {
                            description "Enter the cpu-usage context";

                            container control-plane {
                                description "Enter the control-plane context";

                                container current {
                                    description "Enter the current context";

                                    leaf count {
                                        type decimal64 {
                                            range "0..100";
                                            fraction-digits 2;
                                        }
                                        units "percent";
                                        description "ISA Control Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf count {
                                        type decimal64 {
                                            range "0..100";
                                            fraction-digits 2;
                                        }
                                        units "percent";
                                        description "ISA Control Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container control-plane

                            container data-plane {
                                description "Enter the data-plane context";

                                container current {
                                    description "Enter the current context";

                                    leaf cpu-usage {
                                        type decimal64 {
                                            range "0..100";
                                            fraction-digits 2;
                                        }
                                        units "percent";
                                        description "ISA Data Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf cpu-usage {
                                        type decimal64 {
                                            range "0..100";
                                            fraction-digits 2;
                                        }
                                        units "percent";
                                        description "ISA Data Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container data-plane

                        } // container cpu-usage

                        container memory-allocation-failure-rate {
                            description "Enter the memory-allocation-failure-rate context";

                            container current {
                                description "Enter the current context";

                                leaf count {
                                    type yang:counter64;
                                    units "failures per hour";
                                    description "ISA Memory Allocation Failure Rate.";
                                }

                                leaf start-time {
                                    type yang:date-and-time;
                                    description "The time when the sampling interval started.";
                                }

                                leaf sampling-duration {
                                    type types-sros:time-duration;
                                    description "The duration of the corresponding sampling interval.";
                                }

                            } // container current

                            list historical {
                                key "index";
                                description "Enter the historical list instance";

                                leaf index {
                                    type uint32 {
                                        range "2..max";
                                    }
                                    description
                                        "The index of the finished sampling interval period for this statistic.
                                         It starts with '2' and is ordered by start time of intervals so that
                                         smaller index indicate more recent intervals.";
                                }

                                leaf count {
                                    type yang:counter64;
                                    units "failures per hour";
                                    description "ISA Memory Allocation Failure Rate.";
                                }

                                leaf start-time {
                                    type yang:date-and-time;
                                    description "The time when the sampling interval started.";
                                }

                                leaf sampling-duration {
                                    type types-sros:time-duration;
                                    description "The duration of the corresponding sampling interval.";
                                }

                            } // list historical

                        } // container memory-allocation-failure-rate

                        container ip-tunnel {
                            description "Enter the ip-tunnel context";

                            container number-of-tunnels {
                                description "Enter the number-of-tunnels context";

                                container current {
                                    description "Enter the current context";

                                    leaf gre {
                                        type yang:counter64;
                                        description "Number of GRE tunnels.";
                                    }

                                    leaf ip {
                                        type yang:counter64;
                                        description "Number of IP tunnels.";
                                    }

                                    leaf start-time {
                                        type yang:date-and-time;
                                        description "The time when the sampling interval started.";
                                    }

                                } // container current

                            } // container number-of-tunnels

                            container throughput {
                                description "Enter the throughput context";

                                container gre {
                                    description "Enter the gre context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated GRE tunnel throughput.";
                                            }

                                            leaf decapsulated {
                                                type yang:counter64;
                                                units "packets per second";
                                                description "Decapsulated GRE tunnel throughput.";
                                            }

                                            leaf total {
                                                type yang:counter64;
                                                units "packets per second";
                                                description "Encapsulated and decapsulated GRE tunnel throughput.";
                                            }

                                        } // container packets

                                        container bytes {
                                            description "Enter the bytes context";

                                            leaf encapsulated {
                                                type yang:counter64;
                                                units "megabps";
                                                description "Encapsulated GRE tunnel throughput.";
                                            }

                                            leaf decapsulated {
                                                type yang:counter64;
                                                units "megabps";
                                                description "Decapsulated GRE tunnel throughput.";
                                            }

                                            leaf total {
                                                type yang:counter64;
                                                units "megabps";
                                                description "Encapsulated and decapsulated GRE tunnel throughput.";
                                            }

                                        } // container bytes

                                    } // container current

                                    list historical {
                                        key "index";
                                        description "Enter the historical list instance";

                                        leaf index {
                                            type uint32 {
                                                range "2..max";
                                            }
                                            description
                                                "The index of the finished sampling interval period for this statistic.
                                                 It starts with '2' and is ordered by start time of intervals so that
                                                 smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated GRE tunnel throughput.";
                                            }

                                            leaf decapsulated {
                                                type yang:counter64;
                                                units "packets per second";
                                                description "Decapsulated GRE tunnel throughput.";
                                            }

                                            leaf total {
                                                type yang:counter64;
                                                units "packets per second";
                                                description "Encapsulated and decapsulated GRE tunnel throughput.";
                                            }

                                        } // container packets

                                        container bytes {
                                            description "Enter the bytes context";

                                            leaf encapsulated {
                                                type yang:counter64;
                                                units "megabps";
                                                description "Encapsulated GRE tunnel throughput.";
                                            }

                                            leaf decapsulated {
                                                type yang:counter64;
                                                units "megabps";
                                                description "Decapsulated GRE tunnel throughput.";
                                            }

                                            leaf total {
                                                type yang:counter64;
                                                units "megabps";
                                                description "Encapsulated and decapsulated GRE tunnel throughput.";
                                            }

                                        } // container bytes

                                    } // list historical

                                } // container gre

                                container ip {
                                    description "Enter the ip context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated IP tunnel throughput.";
                                            }

                                            leaf decapsulated {
                                                type yang:counter64;
                                                units "packets per second";
                                                description "Decapsulated IP tunnel throughput.";
                                            }

                                            leaf total {
                                                type yang:counter64;
                                                units "packets per second";
                                                description "Encapsulated and decapsulated IP tunnel throughput.";
                                            }

                                        } // container packets

                                        container bytes {
                                            description "Enter the bytes context";

                                            leaf encapsulated {
                                                type yang:counter64;
                                                units "megabps";
                                                description "Encapsulated IP tunnel throughput.";
                                            }

                                            leaf decapsulated {
                                                type yang:counter64;
                                                units "megabps";
                                                description "Decapsulated IP tunnel throughput.";
                                            }

                                            leaf total {
                                                type yang:counter64;
                                                units "megabps";
                                                description "Encapsulated and decapsulated IP tunnel throughput.";
                                            }

                                        } // container bytes

                                    } // container current

                                    list historical {
                                        key "index";
                                        description "Enter the historical list instance";

                                        leaf index {
                                            type uint32 {
                                                range "2..max";
                                            }
                                            description
                                                "The index of the finished sampling interval period for this statistic.
                                                 It starts with '2' and is ordered by start time of intervals so that
                                                 smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated IP tunnel throughput.";
                                            }

                                            leaf decapsulated {
                                                type yang:counter64;
                                                units "packets per second";
                                                description "Decapsulated IP tunnel throughput.";
                                            }

                                            leaf total {
                                                type yang:counter64;
                                                units "packets per second";
                                                description "Encapsulated and decapsulated IP tunnel throughput.";
                                            }

                                        } // container packets

                                        container bytes {
                                            description "Enter the bytes context";

                                            leaf encapsulated {
                                                type yang:counter64;
                                                units "megabps";
                                                description "Encapsulated IP tunnel throughput.";
                                            }

                                            leaf decapsulated {
                                                type yang:counter64;
                                                units "megabps";
                                                description "Decapsulated IP tunnel throughput.";
                                            }

                                            leaf total {
                                                type yang:counter64;
                                                units "megabps";
                                                description "Encapsulated and decapsulated IP tunnel throughput.";
                                            }

                                        } // container bytes

                                    } // list historical

                                } // container ip

                                container l2tpv3 {
                                    description "Enter the l2tpv3 context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated L2TPv3 tunnel throughput.";
                                            }

                                            leaf decapsulated {
                                                type yang:counter64;
                                                units "packets per second";
                                                description "Decapsulated L2TPv3 tunnel throughput.";
                                            }

                                            leaf total {
                                                type yang:counter64;
                                                units "packets per second";
                                                description "Encapsulated and decapsulated L2TPv3 tunnel throughput.";
                                            }

                                        } // container packets

                                        container bytes {
                                            description "Enter the bytes context";

                                            leaf encapsulated {
                                                type yang:counter64;
                                                units "megabps";
                                                description "Encapsulated L2TPv3 tunnel throughput.";
                                            }

                                            leaf decapsulated {
                                                type yang:counter64;
                                                units "megabps";
                                                description "Decapsulated L2TPv3 tunnel throughput.";
                                            }

                                            leaf total {
                                                type yang:counter64;
                                                units "megabps";
                                                description "Encapsulated and decapsulated L2TPv3 tunnel throughput.";
                                            }

                                        } // container bytes

                                    } // container current

                                    list historical {
                                        key "index";
                                        description "Enter the historical list instance";

                                        leaf index {
                                            type uint32 {
                                                range "2..max";
                                            }
                                            description
                                                "The index of the finished sampling interval period for this statistic.
                                                 It starts with '2' and is ordered by start time of intervals so that
                                                 smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated L2TPv3 tunnel throughput.";
                                            }

                                            leaf decapsulated {
                                                type yang:counter64;
                                                units "packets per second";
                                                description "Decapsulated L2TPv3 tunnel throughput.";
                                            }

                                            leaf total {
                                                type yang:counter64;
                                                units "packets per second";
                                                description "Encapsulated and decapsulated L2TPv3 tunnel throughput.";
                                            }

                                        } // container packets

                                        container bytes {
                                            description "Enter the bytes context";

                                            leaf encapsulated {
                                                type yang:counter64;
                                                units "megabps";
                                                description "Encapsulated L2TPv3 tunnel throughput.";
                                            }

                                            leaf decapsulated {
                                                type yang:counter64;
                                                units "megabps";
                                                description "Decapsulated L2TPv3 tunnel throughput.";
                                            }

                                            leaf total {
                                                type yang:counter64;
                                                units "megabps";
                                                description "Encapsulated and decapsulated L2TPv3 tunnel throughput.";
                                            }

                                        } // container bytes

                                    } // list historical

                                } // container l2tpv3

                            } // container throughput

                            container traffic-forward {
                                description "Enter the traffic-forward context";

                                container gre {
                                    description "Enter the gre context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped GRE tunnel packets.";
                                            }

                                            leaf decapsulated {
                                                type yang:counter64;
                                                units "packets";
                                                description "Number of decaped GRE tunnel packets.";
                                            }

                                            leaf total {
                                                type yang:counter64;
                                                units "packets";
                                                description "Number of encaped and decaped GRE tunnel packets.";
                                            }

                                        } // container packets

                                        container bytes {
                                            description "Enter the bytes context";

                                            leaf encapsulated {
                                                type yang:counter64;
                                                units "kilobytes";
                                                description "Number of kilobytes in the encaped GRE tunnel packets.";
                                            }

                                            leaf decapsulated {
                                                type yang:counter64;
                                                units "kilobytes";
                                                description "Number of kilobytes in the decaped GRE tunnel packets.";
                                            }

                                            leaf total {
                                                type yang:counter64;
                                                units "kilobytes";
                                                description "Number of kilobytes in the encaped and decaped GRE tunnel packets.";
                                            }

                                        } // container bytes

                                    } // container current

                                } // container gre

                                container ip {
                                    description "Enter the ip context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped IP tunnel packets.";
                                            }

                                            leaf decapsulated {
                                                type yang:counter64;
                                                units "packets";
                                                description "Number of decaped IP tunnel packets.";
                                            }

                                            leaf total {
                                                type yang:counter64;
                                                units "packets";
                                                description "Number of encaped and decaped IP tunnel packets.";
                                            }

                                        } // container packets

                                        container bytes {
                                            description "Enter the bytes context";

                                            leaf encapsulated {
                                                type yang:counter64;
                                                units "kilobytes";
                                                description "Number of kilobytes in the encaped IP tunnel packets.";
                                            }

                                            leaf decapsulated {
                                                type yang:counter64;
                                                units "kilobytes";
                                                description "Number of kilobytes in the decaped IP tunnel packets.";
                                            }

                                            leaf total {
                                                type yang:counter64;
                                                units "kilobytes";
                                                description "Number of kilobytes in the encaped and decaped IP tunnel packets.";
                                            }

                                        } // container bytes

                                    } // container current

                                } // container ip

                                container l2tpv3 {
                                    description "Enter the l2tpv3 context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped L2TPv3 tunnel packets.";
                                            }

                                            leaf decapsulated {
                                                type yang:counter64;
                                                units "packets";
                                                description "Number of decaped L2TPv3 tunnel packets.";
                                            }

                                            leaf total {
                                                type yang:counter64;
                                                units "packets";
                                                description "Number of encaped and decaped L2TPv3 tunnel packets.";
                                            }

                                        } // container packets

                                        container bytes {
                                            description "Enter the bytes context";

                                            leaf encapsulated {
                                                type yang:counter64;
                                                units "kilobytes";
                                                description "Number of kilobytes in the encaped L2TPv3 tunnel packets.";
                                            }

                                            leaf decapsulated {
                                                type yang:counter64;
                                                units "kilobytes";
                                                description "Number of kilobytes in the decaped L2TPv3 tunnel packets.";
                                            }

                                            leaf total {
                                                type yang:counter64;
                                                units "kilobytes";
                                                description "Number of kilobytes in the encaped and decaped L2TPv3 tunnel packets.";
                                            }

                                        } // container bytes

                                    } // container current

                                } // container l2tpv3

                            } // container traffic-forward

                        } // container ip-tunnel

                        container ipsec {
                            description "Enter the ipsec context";

                            container number-of-tunnels {
                                description "Enter the number-of-tunnels context";

                                container current {
                                    description "Enter the current context";

                                    leaf static-lan-to-lan {
                                        type yang:counter64;
                                        description "Number of IPsec static LAN-to-LAN (SL2L) tunnels.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf static-lan-to-lan {
                                        type yang:counter64;
                                        description "Number of IPsec static LAN-to-LAN (SL2L) tunnels.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // list historical

                            } // container number-of-tunnels

                            container throughput {
                                description "Enter the throughput context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // list historical

                            } // container throughput

                            container tunnel-setup-rate {
                                description "Enter the tunnel-setup-rate context";

                                container current {
                                    description "Enter the current context";

                                    leaf static-lan-to-lan {
                                        type decimal64 {
                                            fraction-digits 2;
                                        }
                                        units "tunnels per second";
                                        description "Static LAN-to-LAN (SL2L) tunnel setup rate.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf static-lan-to-lan {
                                        type decimal64 {
                                            fraction-digits 2;
                                        }
                                        units "tunnels per second";
                                        description "Static LAN-to-LAN (SL2L) tunnel setup rate.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container tunnel-setup-rate

                            container traffic-forward {
                                description "Enter the traffic-forward context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets";
                                            description "Number of encrypted IPsec packets.";
                                        }

                                        leaf decrypted {
                                            type yang:counter64;
                                            units "packets";
                                            description "Number of decrypted IPsec packets.";
                                        }

                                        leaf total {
                                            type yang:counter64;
                                            units "packets";
                                            description "Number of encrypted and decrypted IPsec packets.";
                                        }

                                    } // container packets

                                    container bytes {
                                        description "Enter the bytes context";

                                        leaf encrypted {
                                            type yang:counter64;
                                            units "kilobytes";
                                            description "Number of kilobytes in the encrypted IPsec packets.";
                                        }

                                        leaf decrypted {
                                            type yang:counter64;
                                            units "kilobytes";
                                            description "Number of kilobytes in the decrypted IPsec packets.";
                                        }

                                        leaf total {
                                            type yang:counter64;
                                            units "kilobytes";
                                            description "Number of kilobytes in the encrypted and decrypted IPsec packets.";
                                        }

                                    } // container bytes

                                } // container current

                            } // container traffic-forward

                            container ike-exchange-failure-rate {
                                description "Enter the ike-exchange-failure-rate context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // container current

                                list historical {
                                    key "index";
                                    description "Enter the historical list instance";

                                    leaf index {
                                        type uint32 {
                                            range "2..max";
                                        }
                                        description
                                            "The index of the finished sampling interval period for this statistic.
                                             It starts with '2' and is ordered by start time of intervals so that
                                             smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description
                                                "The time when the first IKE exchange failure happened
                                                 in the corresponding sampling interval.";
                                        }

                                        leaf first-failure-description {
                                            type types-sros:long-description;
                                            description "The description of the place where the first IKE exchange failure happened.";
                                        }

                                        leaf last-failure {
                                            type yang:date-and-time;
                                            description
                                                "The time when the last IKE exchange failure happened
                                                 in the corresponding sampling interval.";
                                        }

                                        leaf last-failure-description {
                                            type types-sros:long-description;
                                            description "The description of the place where the last IKE exchange failure happened.";
                                        }

                                    } // container other

                                } // list historical

                            } // container ike-exchange-failure-rate

                            container ikev2-msg-drop {
                                description "Enter the ikev2-msg-drop context";

                                container current {
                                    description "Enter the current context";

                                    leaf ike-sa-init {
                                        type yang:counter64;
                                        description "Number of IKE-SA-INIT exchange packet drops.";
                                    }

                                    leaf ike-auth {
                                        type yang:counter64;
                                        description "Number of IKE-AUTH exchange packet drops.";
                                    }

                                    leaf create-child-and-info {
                                        type yang:counter64;
                                        description "Number of Create-CHILD and informational exchange packet drops.";
                                    }

                                    leaf start-time {
                                        type yang:date-and-time;
                                        description "The time when the sampling interval started.";
                                    }

                                    leaf sampling-duration {
                                        type types-sros:time-duration;
                                        description "The duration of the corresponding sampling interval.";
                                    }

                                } // container current

                            } // container ikev2-msg-drop

                        } // container ipsec

                    } // container statistics

                } // container tunnel

                list core-utilization {
                    key "vm-core-id";
                    description "Enter the core-utilization list instance";

                    leaf vm-core-id {
                        type uint32 {
                            range "1..62";
                        }
                        description "The ID of the VM Core.";
                    }

                    leaf virt-core-role-name {
                        type types-sros:named-item;
                        description "Indicates the esa-vm virtual core role.";
                    }

                    leaf virt-core-curr-util {
                        type uint32;
                        units "centipercent";
                        description
                            "Indicates the current 10-second utilization of this virtual
                             core on the esa-vm.";
                    }

                    leaf virt-core-avg-util {
                        type uint32;
                        units "centipercent";
                        description
                            "Indicates the average 15-minute utilization of this virtual
                             core on the esa-vm.";
                    }

                    leaf virt-core-peak-util {
                        type uint32;
                        units "centipercent";
                        description
                            "Indicates the all-time peak 10-second utilization of
                             this virtual core on the esa-vm.";
                    }

                } // list core-utilization

            } // list vm

            list cell-topology {
                key "cell-id";
                description "Enter the cell-topology list instance";

                leaf cell-id {
                    type uint32 {
                        range "0..7";
                    }
                    description "The ID of the cell.";
                }

                leaf socket {
                    type uint32;
                    description "Indicates the socket number that the ESA NUMA cell resides on.";
                }

                leaf cores-available {
                    type yang:gauge32;
                    description "Indicates the total number of cores on the ESA NUMA cell.";
                }

                leaf cores-allocated {
                    type yang:gauge32;
                    description "Indicates the total number of allocated cores on the ESA NUMA cell.";
                }

                leaf memory-available {
                    type yang:gauge32;
                    units "gigabytes";
                    description
                        "Indicates the total amount of available memory (in GigaBytes)
                         on the ESA NUMA cell.";
                }

                leaf memory-allocated {
                    type yang:gauge32;
                    units "gigabytes";
                    description
                        "Indicates the total amount of allocated memory (in GigaBytes)
                         on the ESA NUMA cell.";
                }

            } // list cell-topology

        } // list esa

    } // grouping state-esa

}
