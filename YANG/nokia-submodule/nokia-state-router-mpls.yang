submodule nokia-state-router-mpls {

    yang-version "1.1";

    belongs-to nokia-state { prefix "state"; }

    import ietf-yang-types                { prefix "yang"; }
    import nokia-sros-yang-extensions     { prefix "sros-ext"; }
    import nokia-types-mpls               { prefix "types-mpls"; }
    import nokia-types-sros               { prefix "types-sros"; }

    include nokia-state-router;

    sros-ext:sros-major-release "rel26";
    organization "Nokia";
    contact
        "Nokia SR OS Support
         Web: <http://www.nokia.com>";
    description
        "Nokia YANG Data model with operational state for mpls protocol on SR OS based routers.

         Copyright 2016 Nokia. All rights reserved. Reproduction of this document
         is authorized on the condition that the foregoing copyright notice is included.

         This nokia-state-router-mpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-05-27";

    grouping state-router-mpls {
        container mpls {
            description "Enter the mpls context";

            leaf bypass-next-resignal-timer {
                type uint32;
                units "minutes";
                description
                    "The value indicates the time remaining, in minutes,
                     for the bypass-resignal-timer to expire.";
            }

            leaf issu-mpls-lockdown {
                type boolean;
                description
                    "The value indicates if MPLS has entered the state of not
                     accepting new requests for creation of LSP's(local/transit)
                     during the minor ISSU operation.";
            }

            leaf next-resignal-timer {
                type uint32;
                units "minutes";
                description "The value indicates the time remaining, in minutes, for the resignal-timer to expire.";
            }

            leaf oper-down-reason {
                status deprecated;
                type types-mpls:oper-down-reason-type;
                description
                    "The value of oper-down-reason indicates the reason due to which
                     the MPLS instance is operationally down.";
            }

            leaf oper-state {
                status deprecated;
                type types-sros:oper-state;
                description
                    "The value indicates the current operational state of this
                     MPLS protocol instance on this router.

                     This leaf was deprecated in release 19.10 on Nokia SROS series
                     It has been replaced by router/mpls/ipv4/oper-state.";
            }

            leaf p2mp-next-resignal-timer {
                type uint32;
                units "minutes";
                description "The value indicates the time remaining, in minutes, for the p2mp-resignal-timer to expire.";
            }

            leaf lsp-self-ping-timeouts {
                type yang:counter32;
                description
                    "The value of lsp-self-ping-timeouts indicate the number
                     of lsps/lsp-paths which have experienced lsp self
                     ping timeouts.";
            }

            leaf sr-te-next-resignal-timer {
                type uint32;
                units "minutes";
                description "The value indicates the time remaining, in minutes, for the srte-resignal-timer to expire.";
            }

            leaf lsp-self-ping-oam-resource-failures {
                type yang:counter32;
                description
                    "The value indicates the number of failed lsp self pings
                     due to oam resource limitations.";
            }

            leaf rsvp-pcc-oper-state {
                type types-sros:oper-state;
                description "The value indicates operational state for PCC in relation to RSVP LSPs";
            }

            leaf rsvp-pce-oper-state {
                type types-sros:oper-state;
                description "The value indicates operational state for PCE in relation to RSVP LSPs";
            }

            leaf sr-te-pcc-oper-state {
                type types-sros:oper-state;
                description "The value indicates operational state for PCC in relation to SRTE LSPs";
            }

            leaf sr-te-pce-oper-state {
                type types-sros:oper-state;
                description "The value indicates operational state for PCE in relation to SRTE LSPs";
            }

            container ipv4 {
                description "Enter the ipv4 context";

                leaf oper-state {
                    type types-sros:oper-state;
                    description
                        "The value indicates the current operational state of this
                         MPLS IPv4 protocol instance on this router.";
                }

                leaf oper-down-reason {
                    type types-mpls:oper-down-reason-type;
                    description
                        "The value of oper-down-reason indicates the reason due to which
                         the MPLS Ipv4 protocol instance is operationally down.";
                }

            } // container ipv4

            container ipv6 {
                description "Enter the ipv6 context";

                leaf oper-state {
                    type types-sros:oper-state;
                    description
                        "The value indicates the current operational state of this
                         MPLS IPv6 protocol instance on this router.";
                }

                leaf oper-down-reason {
                    type types-mpls:oper-down-reason-type;
                    description
                        "The value of oper-down-reason indicates the reason due to which
                         the MPLS IPv6 protocol instance is operationally down.";
                }

            } // container ipv6

            list interface {
                key "interface-name";
                description "Enter the interface list instance";

                leaf interface-name {
                    type leafref {
                        path "../../../interface/interface-name";
                    }
                    description "Router interface name.";
                }

                leaf oper-state {
                    status deprecated;
                    type types-sros:oper-state;
                    description
                        "Indicates the current status of the MPLS protocol running on this MPLS interface.

                         This leaf was deprecated in release 19.10 on Nokia SROS series
                         It has been replaced by router/mpls/interface/ipv4/oper-state.";
                }

                container ipv4 {
                    description "Enter the ipv4 context";

                    leaf oper-state {
                        type types-sros:oper-state;
                        description "Indicates the current status of the MPLS IPv4 protocol running on this MPLS interface.";
                    }

                } // container ipv4

                container ipv6 {
                    description "Enter the ipv6 context";

                    leaf oper-state {
                        type types-sros:oper-state;
                        description "Indicates the current status of the MPLS IPv6 protocol running on this MPLS interface.";
                    }

                } // container ipv6

                list label-map {
                    key "in-label";
                    description "Enter the label-map list instance";

                    leaf in-label {
                        type types-sros:mpls-label;
                        description "The incoming label for the label-map.";
                    }

                    leaf oper-state {
                        type types-sros:oper-state;
                        description "The current operational state of this label-map.";
                    }

                    leaf out-if-index {
                        type uint32;
                        description "The outgoing interface index.";
                    }

                    leaf xc-index {
                        type uint32;
                        description "The index for the cross-connect.";
                    }

                    leaf out-segment-index {
                        type uint32;
                        description "The index for outgoing segment.";
                    }

                } // list label-map

                container statistics {
                    description "Enter the statistics context";

                    leaf out-packets {
                        type yang:counter64;
                        description "The number of MPLS labeled packets transmitted from this interface.";
                    }

                    leaf out-octets {
                        type yang:counter64;
                        description "The total number of bytes in MPLS labeled packets transmitted from this interface.";
                    }

                    leaf in-packets {
                        type yang:counter64;
                        description "The number of MPLS labeled packets received on this interface.";
                    }

                    leaf in-octets {
                        type yang:counter64;
                        description "The total number of bytes in MPLS labeled packets received on this interface.";
                    }

                    leaf alt-out-packets {
                        type yang:counter64;
                        description "The number of non-RSVP labeled packets transmitted from this interface.";
                    }

                    leaf alt-out-octets {
                        type yang:counter64;
                        description "The total number of bytes in non-RSVP labeled packets transmitted from this interface.";
                    }

                    leaf alt-in-packets {
                        type yang:counter64;
                        description "The number of non-RSVP labeled packets received on this interface.";
                    }

                    leaf alt-in-octets {
                        type yang:counter64;
                        description "The total number of bytes in non-RSVP labeled packets received on this interface.";
                    }

                } // container statistics

            } // list interface

            list class-forwarding-policy {
                key "policy-name";
                description "Enter the class-forwarding-policy list instance";

                leaf policy-name {
                    type types-sros:named-item;
                    description "Specifies the name for class forwarding policy.";
                }

                leaf ref-count {
                    type uint32;
                    description
                        "Indicates number of LSPs or LSP templates referencing this
                         class forwarding policy.";
                }

            } // list class-forwarding-policy

            list path {
                key "path-name";
                description "Enter the path list instance";

                leaf path-name {
                    type types-sros:named-item-64;
                    description "The canonical name assigned to this tunnel.";
                }

                leaf oper-state {
                    type types-sros:oper-state;
                    description "Indicates the operational state of the MPLS path.";
                }

                leaf path-index {
                    type int32;
                    description "Index for the MPLS path.";
                }

            } // list path

            list lsp-template {
                key "template-name";
                description "Enter the lsp-template list instance";

                leaf template-name {
                    type types-sros:named-item;
                    description
                        "Specifies the name of the LSP Template which is used to
                         automatically create and signal multiple LSP instances.";
                }

                leaf lsp-count {
                    type yang:counter32;
                    description "The value indicates the number of LSPs that are created using this template.";
                }

                leaf mvpn-ref-count {
                    type yang:counter32;
                    description
                        "The value indicates the number of MVPNs as well as number of P2MP LSP
                         users associated with this template.";
                }

                leaf lsp-container-ref-count {
                    type yang:counter32;
                    description "Indicates the number of LSP containers referencing this template.";
                }

                container auto-bandwidth {
                    description "Enter the auto-bandwidth context";

                    leaf sample-time {
                        type uint32;
                        units "minutes";
                        description "Indicates the sample multipler times the collection interval.";
                    }

                } // container auto-bandwidth

            } // list lsp-template

            list lsp {
                key "lsp-name";
                description "Enter the lsp list instance";

                leaf lsp-name {
                    type types-sros:named-item-64;
                    description "Administrative name for Labeled Switch Path.";
                }

                leaf oper-state {
                    type types-sros:oper-state;
                    description "The current operational state of this LSP.";
                }

                leaf negotiated-mtu {
                    type uint32;
                    description
                        "Specifies the size for the maximum transmission unit (MTU)
                         that is negotiated during LSP establishment.";
                }

                leaf oper-fast-reroute {
                    type boolean;
                    description "Indicates whether the operational LSP has fast reroute enabled or disabled.";
                }

                leaf hold-timer {
                    type uint32;
                    description
                        "Specifies the time, in seconds, for which the ingress node
                         holds a bit before programming its data plane and declaring
                         the lsp up to the service module.";
                }

                leaf oper-metric {
                    type uint32;
                    description "Indicates the operational metric for the LSP.";
                }

                leaf lsp-container {
                    type types-sros:named-item;
                    description "Indicates the LSP container that this LSP is a member of.";
                }

                leaf member-id {
                    type uint32 {
                        range "1..64";
                    }
                    description "Indicates the member ID of this LSP within the LSP container.";
                }

                leaf origin-template {
                    type types-sros:named-item-or-empty;
                    description
                        "For auto created LSPs the value indicates the LSP Template
                         which was used to create this LSP.
                         For all other types of LSPs the value is an empty string.";
                }

                leaf from-address {
                    type types-sros:ip-address;
                    description "Indicates the source address.";
                }

                leaf revert-time-remain {
                    type uint32;
                    units "minutes";
                    description
                        "Indicates the time remaining in minutes before the revert timer
                         would expire causing an lsp revert to primary path.";
                }

                leaf lsp-index {
                    type uint32 {
                        range "0..65535|65536..131070";
                    }
                    description "Labeled Switch Path (LSP) index.";
                }

                leaf ttm-tunnel-id {
                    type uint32;
                    description
                        "Indicates the tunnel id sent to TTM for Segment Routing Tunnels
                         on this SROS system.";
                }

                leaf tunnel-id {
                    type uint32;
                    description
                        "Indicates the tunnel used to uniquely identify tunnels
                         on this SROS system.";
                }

                leaf age {
                    type types-sros:time-duration;
                    units "milliseconds";
                    description
                        "The age (i.e., time from creation until now) of this LSP in
                         10-millisecond periods.";
                }

                leaf time-up {
                    type types-sros:time-duration;
                    units "milliseconds";
                    description
                        "The total time in 10-millisecond units that this LSP has been
                         been operational.  For example, the percentage up time can be
                         determined by computing (time-up/age * 100 %).";
                }

                leaf time-down {
                    type types-sros:time-duration;
                    units "milliseconds";
                    description
                        "The total time in 10-millisecond units that this LSP has not
                         been operational.";
                }

                leaf primary-time-up {
                    type types-sros:time-duration;
                    units "milliseconds";
                    description
                        "The total time in 10-millisecond units that this LSP's primary
                         path has been operational.  For example, the percentage
                         contribution of the primary path to the operational time is
                         given by (primary-time-up/time-up * 100) %.";
                }

                leaf transitions {
                    type yang:counter32;
                    description
                        "The number of state transitions (up -> down and down -> up)
                         this LSP has undergone.";
                }

                leaf last-transition {
                    type types-sros:time-duration;
                    units "milliseconds";
                    description
                        "The time in 10-millisecond units since the last transition
                         occurred on this LSP.";
                }

                leaf path-changes {
                    type yang:counter32;
                    description
                        "The number of path changes this LSP has had. For every path
                         change (path down, path up, path change), a corresponding
                         syslog/trap (if enabled) is generated for it.";
                }

                leaf last-path-change {
                    type types-sros:time-duration;
                    units "milliseconds";
                    description
                        "The time in 10-millisecond units since the last change
                         occurred on this LSP.";
                }

                leaf configured-paths {
                    type int32;
                    description "The number of paths configured for this LSP.";
                }

                leaf standby-paths {
                    type int32;
                    description "The number of standby paths configured for this LSP.";
                }

                leaf operational-paths {
                    type int32;
                    description
                        "The number of operational paths for this LSP. This includes
                         the path currently active, as well as operational standby
                         paths.";
                }

                leaf configured-p2mp-instances {
                    type yang:gauge32;
                    description "The value indicates the number of p2mp instances configured for this LSP.";
                }

                leaf statistics-egress-index-unavailable {
                    type boolean;
                    description
                        "The value indicates whether an MPLS LSP egress statistics index is
                         available for the egress statistics.";
                }

                leaf lsp-self-ping-timeouts {
                    type yang:counter32;
                    description
                        "The value indicates the number of paths/networks which have experienced
                         the lsp self ping timeouts for this LSP.";
                }

                leaf lsp-self-ping-oam-resource-failures {
                    type yang:counter32;
                    description
                        "The value indicates the number of times lsp self ping
                         failed due to oam resource limitations for this LSP.";
                }

                leaf active-path {
                    type types-sros:named-item-64;
                    description "Indicates the active path for this LSP.";
                }

                leaf lsp-binding-sid {
                    type uint32;
                    description "Indicates Binding-Sid for this LSP.";
                }

                container entropy-label-state {
                    description "Enter the entropy-label-state context";

                    leaf operational {
                        type boolean;
                        description "Indicates the operational value of entropy label for this LSP.";
                    }

                    leaf negotiated {
                        type boolean;
                        description "Indicates the negotiated value of entropy label for this LSP.";
                    }

                } // container entropy-label-state

                container auto-bandwidth {
                    description "Enter the auto-bandwidth context";

                    leaf sample-time {
                        type uint32;
                        units "minutes";
                        description "Indicates the sample multipler times the collection interval.";
                    }

                    leaf last-adjustment {
                        type yang:date-and-time;
                        description "Indicates the system time for the last auto-bandwidth adjustment.";
                    }

                    leaf last-adjustment-cause {
                        type types-mpls:last-adjustment-cause;
                        description "Indicates the cause for the last auto-bandwidth adjustment.";
                    }

                    leaf next-adjust-time {
                        type uint32;
                        units "minutes";
                        description "Indicates the system time when then adjust-timer will expire.";
                    }

                    leaf adjust-time {
                        type uint32;
                        units "minutes";
                        description "Indicates the adjust multipler times the collection interval.";
                    }

                    leaf max-average-rate {
                        type uint32;
                        units "megabps";
                        description "Indicates the maximum average data rate in any sample interval of the current adjust interval.";
                    }

                    leaf last-average-rate {
                        type uint32;
                        units "megabps";
                        description "Indicates the average data rate in the sample interval that ended most recently.";
                    }

                    leaf current-bandwidth {
                        type uint32;
                        units "megabps";
                        description "Indicates the current bandwidth reserved along the primary path.";
                    }

                    leaf overflow-count {
                        type uint32;
                        description "Indicates the number of overflow samples since the last reset.";
                    }

                    leaf sample-count {
                        type uint32;
                        description "Indicates the count in the sample interval.";
                    }

                    leaf adjust-count {
                        type uint32;
                        description "Indicates the count in the adjust interval.";
                    }

                    leaf oper-state {
                        type types-sros:oper-state;
                        description "Indicates the operational state for the LSP auto bandwidth.";
                    }

                    leaf sample-interval {
                        type uint32;
                        description "Indicates the number of sample intervals.";
                    }

                    leaf underflow-count {
                        type yang:counter32;
                        description "Indicates the number of underflow samples since the last reset.";
                    }

                    leaf max-underflow-bandwidth {
                        type uint32;
                        units "megabps";
                        description "Indicates the maximum sampled bandwidth in the most recent consecutive underflow samples.";
                    }

                    leaf last-adj-bw {
                        type uint32;
                        units "megabps";
                        description
                            "Indicates the last adjusted bandwidth, expressed as
                             an absolute bandwidth (Mbps), for the LSP.";
                    }

                } // container auto-bandwidth

                list primary {
                    key "path-name";
                    description "Enter the primary list instance";

                    leaf path-name {
                        type leafref {
                            path "../../../path/path-name";
                        }
                        description "The path name.";
                    }

                    leaf oper-state {
                        type types-sros:oper-state;
                        description "The current operational state of this LSP or S2L path.";
                    }

                    leaf lsp-id {
                        type string {
                            length "0..62";
                        }
                        description "Identifies the label switched path that is signaled for this entry.";
                    }

                    leaf path-index {
                        type int32;
                        description "Path Index for this LSP or S2L path.";
                    }

                    leaf path-state {
                        type enumeration {
                            enum unknown                        { value 1; }
                            enum active                         { value 2; }
                            enum inactive                       { value 3; }
                        }
                        description "The current working state of this LSP or S2L path.";
                    }

                    leaf initial-timeout {
                        type uint32;
                        units "seconds";
                        description
                            "Indicates the amount of time remaining, in seconds, for the path state
                             to time out after the initial path message has been sent.";
                    }

                    leaf retry-time-remaining {
                        type uint32;
                        units "seconds";
                        description "The time in seconds to signal this LSP or S2L path.";
                    }

                    leaf is-fast-retry {
                        type boolean;
                        description "Indicates which retry timer is being referred to by retry-time-remaining.";
                    }

                    leaf fail-code {
                        type types-mpls:lsp-fail-code;
                        description "Indicates the reason code for LSP or S2L path failure.";
                    }

                    leaf fail-node-address {
                        type types-sros:ip-address;
                        description "Indicates the IP address of the node at which the LSP or S2L path failed.";
                    }

                    leaf ar-hop-list-index {
                        type int32 {
                            range "0..max";
                        }
                        description "Primary index identifying the recorded hop list.";
                    }

                    leaf cspf-hop-list-index {
                        type int32 {
                            range "0..max";
                        }
                        description "Primary index identifying the CSPF hop list.";
                    }

                    leaf last-resignal-attempt {
                        type yang:date-and-time;
                        description "Indicates the system time when the last attempt to resignal this LSP or S2L path was made.";
                    }

                    leaf oper-up-time {
                        type types-sros:time-interval;
                        units "centiseconds";
                        description "Indicates the total time the LSP path has been operationally up.";
                    }

                    leaf oper-down-time {
                        type types-sros:time-interval;
                        units "centiseconds";
                        description "Indicates the total time the LSP path has been operationally down.";
                    }

                    leaf setup-priority {
                        type uint32 {
                            range "0..7";
                        }
                        description "Indicates the setup-priority used by the operational LSP path.";
                    }

                    leaf hold-priority {
                        type uint32 {
                            range "0..7";
                        }
                        description "Indicates the hold-priority used by the operational LSP path.";
                    }

                    leaf oper-record {
                        type enumeration {
                            enum record                         { value 1; }
                            enum no-record                      { value 2; }
                        }
                        description
                            "Indicates whether the operational LSP path is recording or not
                             recording all the traversed hops.";
                    }

                    leaf oper-record-label {
                        type enumeration {
                            enum record                         { value 1; }
                            enum no-record                      { value 2; }
                        }
                        description
                            "Indicates whether the operational LSP path is recording or not
                             recording the label allocated at each traversed node.";
                    }

                    leaf oper-hop-limit {
                        type uint32 {
                            range "0..255";
                        }
                        description "Indicates the maximum hop limit used by the operational LSP path.";
                    }

                    leaf oper-include-admin-group {
                        type uint32;
                        description "Indicates a bitmap which lists admin groups included in the operational LSP path.";
                    }

                    leaf oper-exclude-admin-group {
                        type uint32;
                        description "Indicates a bitmap which lists admin groups excluded in the operational LSP path.";
                    }

                    leaf least-fill-path-sel-method {
                        type boolean;
                        description
                            "Indicates whether the operational LSP path was computed using the least-fill
                             path selection method.";
                    }

                    leaf resignal-eligible {
                        type boolean;
                        description
                            "Indicates that the LSP path is eligible for re-signaling
                             on the basis of available bandwidth.";
                    }

                    leaf rsvp-adspec {
                        type boolean;
                        description
                            "Indicates whether the operational LSP path has ADSPEC object included in RSVP
                             messages or not.";
                    }

                    leaf prop-admin-group {
                        type boolean;
                        description
                            "Indicates whether the operational LSP path has propagation admin-groups
                             enabled or disabled.";
                    }

                    leaf inter-area {
                        type boolean;
                        description "Indicates whether the operational LSP path is inter-area or intra-area.";
                    }

                    leaf metric {
                        type uint32;
                        description "Specifies the cost of the traffic engineered path returned by the IGP.";
                    }

                    leaf properties {
                        type bits {
                            bit record-route                   { position 0; }
                            bit adaptive                       { position 1; }
                            bit cspf                           { position 2; }
                            bit mergeable                      { position 3; }
                            bit fast-reroute                   { position 4; }
                            bit pce-reported                   { position 5; }
                            bit pce-controlled                 { position 6; }
                            bit pce-computed                   { position 7; }
                        }
                        description "The set of configured properties for this path expressed as a bit map.";
                    }

                    leaf oper-metric {
                        type uint32;
                        description "Indicates the operational metric for the LSP path.";
                    }

                    leaf oper-mtu {
                        type uint32;
                        description
                            "Indicates the size for the maximum transmission unit (MTU)
                             that is currently operation for this LSP path.";
                    }

                    leaf negotiated-mtu {
                        type uint32;
                        description
                            "Specifies the size for the maximum transmission unit (MTU) that is negotiated
                             during establishment of this LSP path.";
                    }

                    leaf oper-bandwidth {
                        type int32;
                        units "megabps";
                        description
                            "Indicates the amount of bandwidth in mega-bits per seconds that has been reserved
                             for the operational LSP path.";
                    }

                    leaf oper-class-type {
                        type types-mpls:class-type;
                        description "Indicates operational class type associated with the LSP.";
                    }

                    leaf oper-path-computation-method {
                        type enumeration {
                            enum none                           { value 1; }
                            enum local-cspf                     { value 2; }
                            enum pce                            { value 3; }
                        }
                        description "Indicates the path-computation-method that was used to compute the current operational LSP path.";
                    }

                    leaf oper-metric-type {
                        type enumeration {
                            enum igp                            { value 1; }
                            enum te                             { value 2; }
                            enum delay                          { value 3; }
                        }
                        description "Indicates the metric-type that was used to compute the current operational LSP path.";
                    }

                    leaf oper-delay-metric-limit {
                        type union {
                            type enumeration {
                                enum no-limit                       { value 0; }
                            }
                            type uint32 {
                                range "1..16777215";
                            }
                        }
                        description "Indicates the delay-metric-limit that was used to compute the current operational LSP path.";
                    }

                    leaf oper-local-sr-protection {
                        type enumeration {
                            enum none                           { value 1; }
                            enum preferred                      { value 2; }
                            enum mandatory                      { value 3; }
                        }
                        description "Indicates the local-sr-protection option used to compute the current operational LSP path.";
                    }

                    leaf oper-label-stack-reduction {
                        type boolean;
                        description "Indicates whether or not label stack reduction was used to compute the current operational LSP path.";
                    }

                    leaf self-ping-oper-state {
                        type types-sros:oper-state;
                        description "The current lsp self ping operational state of this LSP path.";
                    }

                    leaf degraded {
                        type boolean;
                        description "Indicates the path is degraded or not.";
                    }

                    leaf degraded-reason {
                        type bits {
                            bit frr-in-use                     { position 0; }
                            bit soft-preempted                 { position 1; }
                            bit bfd-down                       { position 2; }
                            bit manual-switch                  { position 3; }
                        }
                        description "Indicates the reason if path is degraded.";
                    }

                    leaf path-lsp-id {
                        type uint32 {
                            range "1..65535";
                        }
                        description "LSP identifier for this LSP path.";
                    }

                    leaf main-ct-retry-remaining {
                        type uint32;
                        description
                            "Indicates the number of remaining attempts the software should make before
                             it can start using the backup class type for the LSP.";
                    }

                    container bfd {
                        description "Enter the bfd context";

                        leaf bfd-state {
                            type enumeration {
                                enum not-applicable                 { value 0; }
                                enum down                           { value 1; }
                                enum up                             { value 2; }
                                enum await-to-up                    { value 3; }
                                enum fail-to-start                  { value 4; }
                            }
                            description "The current state of the BFD session on the LSP path.";
                        }

                        leaf bfd-wait-for-up-time-left {
                            type uint32;
                            units "seconds";
                            description "The time in seconds left to wait for the bfd session to be up.";
                        }

                        leaf bfd-start-fail-reason {
                            type types-sros:description-or-empty;
                            description "Specifies the reason bfd failed to start the session.";
                        }

                    } // container bfd

                    container last-update {
                        description "Enter the last-update context";

                        leaf time {
                            type yang:date-and-time;
                            description "Indicates the system time when the last update occured.";
                        }

                        leaf id {
                            type uint32;
                            description "Indicates the last update ID which was processed.";
                        }

                        leaf state {
                            type types-mpls:success-fail;
                            description "Indicates whether the last update was successful or failed.";
                        }

                        leaf fail-code {
                            type types-mpls:lsp-fail-code;
                            description "Indicates the reason code for last update failure.";
                        }

                    } // container last-update

                    container mbb {
                        description "Enter the mbb context";

                        container last-mbb {
                            description "Enter the last-mbb context";

                            leaf type {
                                type types-mpls:mbb-type;
                                description "Specifies the type of last make-before-break (MBB).";
                            }

                            leaf end-time {
                                type yang:date-and-time;
                                description "Specifies the system time when the last MBB ended.";
                            }

                            leaf metric {
                                type uint32;
                                description "Indicates the cost of the traffic engineered path for the LSP path prior to MBB.";
                            }

                            leaf state {
                                type types-mpls:success-fail;
                                description "Indicates whether the last make-before-break was successful or failed.";
                            }

                            leaf fail-code {
                                type types-mpls:lsp-fail-code;
                                description "Indicates the reason code for last MBB failure.";
                            }

                            leaf signaled-bw {
                                type uint32;
                                description "Indicates the bandwidth used to signal the last MBB that occurred.";
                            }

                        } // container last-mbb

                        container in-progress-mbb {
                            description "Enter the in-progress-mbb context";

                            leaf type {
                                type types-mpls:mbb-type;
                                description "Indicates the type of the make-before-break (MBB) that is in progress.";
                            }

                            leaf start-time {
                                type yang:date-and-time;
                                description "Indicates the system time when the in-progress MBB started.";
                            }

                            leaf next-retry {
                                type uint32;
                                units "seconds";
                                description
                                    "Indicates the amount of time remaining in seconds before the next
                                     attempt is made to retry the in-progress MBB.";
                            }

                            leaf retry-attempt {
                                type uint32;
                                description "Indicates 'n' where nth attempt for the MBB is in progress.";
                            }

                            leaf fail-code {
                                type types-mpls:lsp-fail-code;
                                description "Indicates the reason code for in-progress MBB failure.";
                            }

                            leaf fail-node {
                                type types-sros:ip-address;
                                description
                                    "Indicates the IP address of the node in the LSP path
                                     at which the in-progress MBB failed.";
                            }

                            leaf initial-timeout {
                                type uint32;
                                units "seconds";
                                description
                                    "Indicates the amount of time remaining, in seconds, for the in-progress MBB
                                     path state to time out after the initial path message has been sent.";
                            }

                            leaf signaled-bw {
                                type uint32;
                                description "Indicates the bandwidth used to signal the MBB currently in progress.";
                            }

                            leaf main-ct-retry-remaining {
                                type uint32;
                                description
                                    "Indicates the number of remaining attempts the software should
                                     make before it can start using the backup class type for the LSP.";
                            }

                        } // container in-progress-mbb

                    } // container mbb

                    container statistics {
                        description "Enter the statistics context";

                        leaf retry-attempts {
                            type uint32;
                            description
                                "Indicates the number of unsuccessful attempts which have been made
                                 to signal this LSP path.";
                        }

                        leaf transition-count {
                            type yang:counter32;
                            description "Indicates the number of transitions that have occurred for this LSP path.";
                        }

                        leaf cspf-queries {
                            type yang:counter32;
                            description "Indicates the number of CSPF queries that have been made for this LSP path.";
                        }

                    } // container statistics

                    container fast-reroute {
                        description "Enter the fast-reroute context";

                        leaf node-protect {
                            type boolean;
                            description
                                "Indicates whether fast reroute node protection is enabled or disabled for the
                                 operational LSP path.";
                        }

                        leaf hop-limit {
                            type uint32 {
                                range "0..255";
                            }
                            description "Indicates the fast reroute hop limit used by the operational LSP path.";
                        }

                        leaf prop-admin-group {
                            type boolean;
                            description
                                "Indicates whether the propagation of admin groups in the fast reroute object
                                 is enabled or disabled for the operational LSP path.";
                        }

                    } // container fast-reroute

                } // list primary

                list secondary {
                    key "path-name";
                    description "Enter the secondary list instance";

                    leaf path-name {
                        type leafref {
                            path "../../../path/path-name";
                        }
                        description "The path name.";
                    }

                    leaf oper-state {
                        type types-sros:oper-state;
                        description "The current operational state of this LSP or S2L path.";
                    }

                    leaf lsp-id {
                        type string {
                            length "0..62";
                        }
                        description "Identifies the label switched path that is signaled for this entry.";
                    }

                    leaf path-index {
                        type int32;
                        description "Path Index for this LSP or S2L path.";
                    }

                    leaf path-state {
                        type enumeration {
                            enum unknown                        { value 1; }
                            enum active                         { value 2; }
                            enum inactive                       { value 3; }
                        }
                        description "The current working state of this LSP or S2L path.";
                    }

                    leaf initial-timeout {
                        type uint32;
                        units "seconds";
                        description
                            "Indicates the amount of time remaining, in seconds, for the path state
                             to time out after the initial path message has been sent.";
                    }

                    leaf retry-time-remaining {
                        type uint32;
                        units "seconds";
                        description "The time in seconds to signal this LSP or S2L path.";
                    }

                    leaf is-fast-retry {
                        type boolean;
                        description "Indicates which retry timer is being referred to by retry-time-remaining.";
                    }

                    leaf fail-code {
                        type types-mpls:lsp-fail-code;
                        description "Indicates the reason code for LSP or S2L path failure.";
                    }

                    leaf fail-node-address {
                        type types-sros:ip-address;
                        description "Indicates the IP address of the node at which the LSP or S2L path failed.";
                    }

                    leaf ar-hop-list-index {
                        type int32 {
                            range "0..max";
                        }
                        description "Primary index identifying the recorded hop list.";
                    }

                    leaf cspf-hop-list-index {
                        type int32 {
                            range "0..max";
                        }
                        description "Primary index identifying the CSPF hop list.";
                    }

                    leaf last-resignal-attempt {
                        type yang:date-and-time;
                        description "Indicates the system time when the last attempt to resignal this LSP or S2L path was made.";
                    }

                    leaf oper-up-time {
                        type types-sros:time-interval;
                        units "centiseconds";
                        description "Indicates the total time the LSP path has been operationally up.";
                    }

                    leaf oper-down-time {
                        type types-sros:time-interval;
                        units "centiseconds";
                        description "Indicates the total time the LSP path has been operationally down.";
                    }

                    leaf setup-priority {
                        type uint32 {
                            range "0..7";
                        }
                        description "Indicates the setup-priority used by the operational LSP path.";
                    }

                    leaf hold-priority {
                        type uint32 {
                            range "0..7";
                        }
                        description "Indicates the hold-priority used by the operational LSP path.";
                    }

                    leaf oper-record {
                        type enumeration {
                            enum record                         { value 1; }
                            enum no-record                      { value 2; }
                        }
                        description
                            "Indicates whether the operational LSP path is recording or not
                             recording all the traversed hops.";
                    }

                    leaf oper-record-label {
                        type enumeration {
                            enum record                         { value 1; }
                            enum no-record                      { value 2; }
                        }
                        description
                            "Indicates whether the operational LSP path is recording or not
                             recording the label allocated at each traversed node.";
                    }

                    leaf oper-hop-limit {
                        type uint32 {
                            range "0..255";
                        }
                        description "Indicates the maximum hop limit used by the operational LSP path.";
                    }

                    leaf oper-include-admin-group {
                        type uint32;
                        description "Indicates a bitmap which lists admin groups included in the operational LSP path.";
                    }

                    leaf oper-exclude-admin-group {
                        type uint32;
                        description "Indicates a bitmap which lists admin groups excluded in the operational LSP path.";
                    }

                    leaf least-fill-path-sel-method {
                        type boolean;
                        description
                            "Indicates whether the operational LSP path was computed using the least-fill
                             path selection method.";
                    }

                    leaf resignal-eligible {
                        type boolean;
                        description
                            "Indicates that the LSP path is eligible for re-signaling
                             on the basis of available bandwidth.";
                    }

                    leaf rsvp-adspec {
                        type boolean;
                        description
                            "Indicates whether the operational LSP path has ADSPEC object included in RSVP
                             messages or not.";
                    }

                    leaf prop-admin-group {
                        type boolean;
                        description
                            "Indicates whether the operational LSP path has propagation admin-groups
                             enabled or disabled.";
                    }

                    leaf inter-area {
                        type boolean;
                        description "Indicates whether the operational LSP path is inter-area or intra-area.";
                    }

                    leaf metric {
                        type uint32;
                        description "Specifies the cost of the traffic engineered path returned by the IGP.";
                    }

                    leaf properties {
                        type bits {
                            bit record-route                   { position 0; }
                            bit adaptive                       { position 1; }
                            bit cspf                           { position 2; }
                            bit mergeable                      { position 3; }
                            bit fast-reroute                   { position 4; }
                            bit pce-reported                   { position 5; }
                            bit pce-controlled                 { position 6; }
                            bit pce-computed                   { position 7; }
                        }
                        description "The set of configured properties for this path expressed as a bit map.";
                    }

                    leaf oper-metric {
                        type uint32;
                        description "Indicates the operational metric for the LSP path.";
                    }

                    leaf oper-mtu {
                        type uint32;
                        description
                            "Indicates the size for the maximum transmission unit (MTU)
                             that is currently operation for this LSP path.";
                    }

                    leaf negotiated-mtu {
                        type uint32;
                        description
                            "Specifies the size for the maximum transmission unit (MTU) that is negotiated
                             during establishment of this LSP path.";
                    }

                    leaf oper-bandwidth {
                        type int32;
                        units "megabps";
                        description
                            "Indicates the amount of bandwidth in mega-bits per seconds that has been reserved
                             for the operational LSP path.";
                    }

                    leaf oper-class-type {
                        type types-mpls:class-type;
                        description "Indicates operational class type associated with the LSP.";
                    }

                    leaf oper-path-computation-method {
                        type enumeration {
                            enum none                           { value 1; }
                            enum local-cspf                     { value 2; }
                            enum pce                            { value 3; }
                        }
                        description "Indicates the path-computation-method that was used to compute the current operational LSP path.";
                    }

                    leaf oper-metric-type {
                        type enumeration {
                            enum igp                            { value 1; }
                            enum te                             { value 2; }
                            enum delay                          { value 3; }
                        }
                        description "Indicates the metric-type that was used to compute the current operational LSP path.";
                    }

                    leaf oper-delay-metric-limit {
                        type union {
                            type enumeration {
                                enum no-limit                       { value 0; }
                            }
                            type uint32 {
                                range "1..16777215";
                            }
                        }
                        description "Indicates the delay-metric-limit that was used to compute the current operational LSP path.";
                    }

                    leaf oper-local-sr-protection {
                        type enumeration {
                            enum none                           { value 1; }
                            enum preferred                      { value 2; }
                            enum mandatory                      { value 3; }
                        }
                        description "Indicates the local-sr-protection option used to compute the current operational LSP path.";
                    }

                    leaf oper-label-stack-reduction {
                        type boolean;
                        description "Indicates whether or not label stack reduction was used to compute the current operational LSP path.";
                    }

                    leaf self-ping-oper-state {
                        type types-sros:oper-state;
                        description "The current lsp self ping operational state of this LSP path.";
                    }

                    leaf degraded {
                        type boolean;
                        description "Indicates the path is degraded or not.";
                    }

                    leaf degraded-reason {
                        type bits {
                            bit frr-in-use                     { position 0; }
                            bit soft-preempted                 { position 1; }
                            bit bfd-down                       { position 2; }
                            bit manual-switch                  { position 3; }
                        }
                        description "Indicates the reason if path is degraded.";
                    }

                    leaf path-lsp-id {
                        type uint32 {
                            range "1..65535";
                        }
                        description "LSP identifier for this LSP path.";
                    }

                    leaf active-by-manual {
                        type enumeration {
                            enum not-applicable                 { value 0; }
                            enum no-force                       { value 1; }
                            enum force                          { value 2; }
                        }
                        description
                            "Indicates whether a secondary standby path has become the active LSP path
                             due to manual intervention.";
                    }

                    leaf srlg-disjoint {
                        type boolean;
                        description
                            "Indicates whether the relevant standby lsp path is SRLG disjoint
                             from the associated primary LSP path for an LSP at the head-end
                             Label Edge Router (LER).";
                    }

                    container bfd {
                        description "Enter the bfd context";

                        leaf bfd-state {
                            type enumeration {
                                enum not-applicable                 { value 0; }
                                enum down                           { value 1; }
                                enum up                             { value 2; }
                                enum await-to-up                    { value 3; }
                                enum fail-to-start                  { value 4; }
                            }
                            description "The current state of the BFD session on the LSP path.";
                        }

                        leaf bfd-wait-for-up-time-left {
                            type uint32;
                            units "seconds";
                            description "The time in seconds left to wait for the bfd session to be up.";
                        }

                        leaf bfd-start-fail-reason {
                            type types-sros:description-or-empty;
                            description "Specifies the reason bfd failed to start the session.";
                        }

                    } // container bfd

                    container last-update {
                        description "Enter the last-update context";

                        leaf time {
                            type yang:date-and-time;
                            description "Indicates the system time when the last update occured.";
                        }

                        leaf id {
                            type uint32;
                            description "Indicates the last update ID which was processed.";
                        }

                        leaf state {
                            type types-mpls:success-fail;
                            description "Indicates whether the last update was successful or failed.";
                        }

                        leaf fail-code {
                            type types-mpls:lsp-fail-code;
                            description "Indicates the reason code for last update failure.";
                        }

                    } // container last-update

                    container mbb {
                        description "Enter the mbb context";

                        container last-mbb {
                            description "Enter the last-mbb context";

                            leaf type {
                                type types-mpls:mbb-type;
                                description "Specifies the type of last make-before-break (MBB).";
                            }

                            leaf end-time {
                                type yang:date-and-time;
                                description "Specifies the system time when the last MBB ended.";
                            }

                            leaf metric {
                                type uint32;
                                description "Indicates the cost of the traffic engineered path for the LSP path prior to MBB.";
                            }

                            leaf state {
                                type types-mpls:success-fail;
                                description "Indicates whether the last make-before-break was successful or failed.";
                            }

                            leaf fail-code {
                                type types-mpls:lsp-fail-code;
                                description "Indicates the reason code for last MBB failure.";
                            }

                            leaf signaled-bw {
                                type uint32;
                                description "Indicates the bandwidth used to signal the last MBB that occurred.";
                            }

                        } // container last-mbb

                        container in-progress-mbb {
                            description "Enter the in-progress-mbb context";

                            leaf type {
                                type types-mpls:mbb-type;
                                description "Indicates the type of the make-before-break (MBB) that is in progress.";
                            }

                            leaf start-time {
                                type yang:date-and-time;
                                description "Indicates the system time when the in-progress MBB started.";
                            }

                            leaf next-retry {
                                type uint32;
                                units "seconds";
                                description
                                    "Indicates the amount of time remaining in seconds before the next
                                     attempt is made to retry the in-progress MBB.";
                            }

                            leaf retry-attempt {
                                type uint32;
                                description "Indicates 'n' where nth attempt for the MBB is in progress.";
                            }

                            leaf fail-code {
                                type types-mpls:lsp-fail-code;
                                description "Indicates the reason code for in-progress MBB failure.";
                            }

                            leaf fail-node {
                                type types-sros:ip-address;
                                description
                                    "Indicates the IP address of the node in the LSP path
                                     at which the in-progress MBB failed.";
                            }

                            leaf initial-timeout {
                                type uint32;
                                units "seconds";
                                description
                                    "Indicates the amount of time remaining, in seconds, for the in-progress MBB
                                     path state to time out after the initial path message has been sent.";
                            }

                            leaf signaled-bw {
                                type uint32;
                                description "Indicates the bandwidth used to signal the MBB currently in progress.";
                            }

                        } // container in-progress-mbb

                    } // container mbb

                    container statistics {
                        description "Enter the statistics context";

                        leaf retry-attempts {
                            type uint32;
                            description
                                "Indicates the number of unsuccessful attempts which have been made
                                 to signal this LSP path.";
                        }

                        leaf transition-count {
                            type yang:counter32;
                            description "Indicates the number of transitions that have occurred for this LSP path.";
                        }

                        leaf cspf-queries {
                            type yang:counter32;
                            description "Indicates the number of CSPF queries that have been made for this LSP path.";
                        }

                    } // container statistics

                } // list secondary

                list primary-p2mp-instance {
                    key "instance-name";
                    description "Enter the primary-p2mp-instance list instance";

                    leaf instance-name {
                        type types-sros:named-item;
                        description "The unique name which identifies this P2MP LSP for this virtual router. ";
                    }

                    leaf oper-state {
                        type types-sros:oper-state;
                        description "The current operational state of this P2MP instance.";
                    }

                    leaf p2mp-instance-state {
                        type enumeration {
                            enum unknown                        { value 1; }
                            enum active                         { value 2; }
                            enum inactive                       { value 3; }
                        }
                        description
                            "Indicates the current working state of this P2MP instance
                             within this LSP.";
                    }

                    leaf p2mp-instance-index {
                        type uint32 {
                            range "0..65535|65536..131070";
                        }
                        description "P2MP Instance index.";
                    }

                    leaf lsp-id {
                        type string {
                            length "0..62";
                        }
                        description "LSP ID for the P2MP instance.";
                    }

                    leaf properties {
                        type bits {
                            bit record-route                   { position 0; }
                            bit adaptive                       { position 1; }
                            bit cspf                           { position 2; }
                            bit mergeable                      { position 3; }
                            bit fast-reroute                   { position 4; }
                        }
                        description
                            "Indicates the set of configured properties for this P2MP instance
                             expressed as a bit map.";
                    }

                    leaf oper-bandwidth {
                        type int32;
                        units "megabps";
                        description
                            "Indicates the amount of bandwidth in mega-bits per seconds that has been reserved
                             for the P2MP instance.";
                    }

                    leaf last-resignal-attempt {
                        type yang:date-and-time;
                        description "Indicates the system time when the last attempt to resignal this LSP was made.";
                    }

                    leaf time-up {
                        type types-sros:time-interval;
                        units "centiseconds";
                        description "Indicates the total time that this P2MP instance has been operationally up.";
                    }

                    leaf time-down {
                        type types-sros:time-interval;
                        units "centiseconds";
                        description "Indicates the total time that this P2MP instance has been operationally down.";
                    }

                    leaf configured-s2ls {
                        type yang:gauge32;
                        description "Indicates the number of S2ls configured for this P2MP LSP.";
                    }

                    leaf operational-s2ls {
                        type yang:gauge32;
                        description
                            "Indicates the number of operational S2ls for this P2MP LSP.

                             This includes the S2ls currently active";
                    }

                    list s2l-path {
                        key "path-name to";
                        description "Enter the s2l-path list instance";

                        leaf path-name {
                            type leafref {
                                path "../../../../path/path-name";
                            }
                            description "A label switch path (P2MP LSP) name.";
                        }

                        leaf to {
                            type types-sros:ip-address;
                            description "The IP address of the destination address of the S2L sub LSP.";
                        }

                        leaf oper-state {
                            type types-sros:oper-state;
                            description "The current operational state of this LSP or S2L path.";
                        }

                        leaf lsp-id {
                            type string {
                                length "0..62";
                            }
                            description "Identifies the label switched path that is signaled for this entry.";
                        }

                        leaf path-index {
                            type int32;
                            description "Path Index for this LSP or S2L path.";
                        }

                        leaf path-state {
                            type enumeration {
                                enum unknown                        { value 1; }
                                enum active                         { value 2; }
                                enum inactive                       { value 3; }
                            }
                            description "The current working state of this LSP or S2L path.";
                        }

                        leaf initial-timeout {
                            type uint32;
                            units "seconds";
                            description
                                "Indicates the amount of time remaining, in seconds, for the path state
                                 to time out after the initial path message has been sent.";
                        }

                        leaf retry-time-remaining {
                            type uint32;
                            units "seconds";
                            description "The time in seconds to signal this LSP or S2L path.";
                        }

                        leaf is-fast-retry {
                            type boolean;
                            description "Indicates which retry timer is being referred to by retry-time-remaining.";
                        }

                        leaf fail-code {
                            type types-mpls:lsp-fail-code;
                            description "Indicates the reason code for LSP or S2L path failure.";
                        }

                        leaf fail-node-address {
                            type types-sros:ip-address;
                            description "Indicates the IP address of the node at which the LSP or S2L path failed.";
                        }

                        leaf ar-hop-list-index {
                            type int32 {
                                range "0..max";
                            }
                            description "Primary index identifying the recorded hop list.";
                        }

                        leaf cspf-hop-list-index {
                            type int32 {
                                range "0..max";
                            }
                            description "Primary index identifying the CSPF hop list.";
                        }

                        leaf last-resignal-attempt {
                            type yang:date-and-time;
                            description "Indicates the system time when the last attempt to resignal this LSP or S2L path was made.";
                        }

                        leaf group-id {
                            type uint32;
                            description "Indicates the group for this entry.";
                        }

                        leaf oper-up-time {
                            type types-sros:time-interval;
                            units "centiseconds";
                            description "Indicates the total time the S2L path has been operationally up.";
                        }

                        leaf oper-down-time {
                            type types-sros:time-interval;
                            units "centiseconds";
                            description "Indicates the total time the S2L path has been operationally down.";
                        }

                        leaf properties {
                            type bits {
                                bit record-route                   { position 0; }
                                bit adaptive                       { position 1; }
                                bit cspf                           { position 2; }
                                bit mergeable                      { position 3; }
                                bit fast-reroute                   { position 4; }
                            }
                            description
                                "Indicates the set of configured properties for this path
                                 expressed as a bit map.";
                        }

                        leaf oper-bandwidth {
                            type int32;
                            units "megabps";
                            description
                                "Indicates the amount of bandwidth in mega-bits per seconds that has been reserved
                                 for the operational S2L path.";
                        }

                        container mbb {
                            description "Enter the mbb context";

                            container last-mbb {
                                description "Enter the last-mbb context";

                                leaf type {
                                    type types-mpls:mbb-type;
                                    description "Specifies the type of last make-before-break (MBB).";
                                }

                                leaf end-time {
                                    type yang:date-and-time;
                                    description "Specifies the system time when the last MBB ended.";
                                }

                                leaf state {
                                    type types-mpls:success-fail;
                                    description "Indicates whether the last MBB was successful or failed.";
                                }

                            } // container last-mbb

                            container in-progress-mbb {
                                description "Enter the in-progress-mbb context";

                                leaf type {
                                    type types-mpls:mbb-type;
                                    description "Indicates the type of the make-before-break (MBB) that is in progress.";
                                }

                                leaf start-time {
                                    type yang:date-and-time;
                                    description "Indicates the system time when the in-progress MBB started.";
                                }

                                leaf next-retry {
                                    type uint32;
                                    units "seconds";
                                    description
                                        "Indicates the amount of time remaining in seconds before the next
                                         attempt is made to retry the in-progress MBB.";
                                }

                                leaf retry-attempt {
                                    type uint32;
                                    description "Indicates 'n' where nth attempt for the MBB is in progress.";
                                }

                                leaf fail-code {
                                    type types-mpls:lsp-fail-code;
                                    description "Indicates the reason code for in-progress MBB failure.";
                                }

                                leaf fail-node {
                                    type types-sros:ip-address;
                                    description
                                        "Indicates the IP address of the node in the LSP path
                                         at which the in-progress MBB failed.";
                                }

                                leaf initial-timeout {
                                    type uint32;
                                    units "seconds";
                                    description
                                        "Indicates the amount of time remaining, in seconds, for the in-progress MBB
                                         path state to time out after the initial path message has been sent.";
                                }

                            } // container in-progress-mbb

                        } // container mbb

                        container statistics {
                            description "Enter the statistics context";

                            leaf retry-attempts {
                                type uint32;
                                description
                                    "Indicates the number of unsuccessful attempts which have been made
                                     to signal this LSP path.";
                            }

                            leaf transition-count {
                                type yang:counter32;
                                description "Indicates the number of transitions that have occurred for this LSP path.";
                            }

                            leaf cspf-queries {
                                type yang:counter32;
                                description "Indicates the number of CSPF queries that have been made for this LSP path.";
                            }

                        } // container statistics

                    } // list s2l-path

                    container mbb {
                        description "Enter the mbb context";

                        container last-mbb {
                            description "Enter the last-mbb context";

                            leaf type {
                                type types-mpls:mbb-type;
                                description "Specifies the type of last make-before-break (MBB).";
                            }

                            leaf end-time {
                                type yang:date-and-time;
                                description "Specifies the system time when the last MBB ended.";
                            }

                            leaf state {
                                type types-mpls:success-fail;
                                description "Indicates whether the last MBB was successful or failed.";
                            }

                        } // container last-mbb

                        container in-progress-mbb {
                            description "Enter the in-progress-mbb context";

                            leaf type {
                                type types-mpls:mbb-type;
                                description "Indicates the type of the make-before-break (MBB) that is in progress.";
                            }

                            leaf start-time {
                                type yang:date-and-time;
                                description "Indicates the system time when the in-progress MBB started.";
                            }

                        } // container in-progress-mbb

                    } // container mbb

                    container statistics {
                        description "Enter the statistics context";

                        leaf transition-count {
                            type yang:counter32;
                            description
                                "Indicates the number of state transitions (up -> down and down -> up) this
                                 P2MP instance has undergone.";
                        }

                    } // container statistics

                } // list primary-p2mp-instance

            } // list lsp

            list static-lsp {
                key "lsp-name";
                description "Enter the static-lsp list instance";

                leaf lsp-name {
                    type types-sros:named-item-64;
                    description "Administrative name for Labeled Switch Path.";
                }

                leaf oper-state {
                    type types-sros:oper-state;
                    description "The current operational state of this LSP.";
                }

                leaf lsp-index {
                    type uint32;
                    description "Labeled Switch Path (LSP) index.";
                }

                leaf oper-metric {
                    type uint32;
                    description "Indicates the operational metric for the LSP.";
                }

                leaf time-up {
                    type types-sros:time-duration;
                    units "milliseconds";
                    description
                        "The total time in 10-millisecond units that this LSP has been
                         been operational.  For example, the percentage up time can be
                         determined by computing (time-up/age * 100 %).";
                }

                leaf time-down {
                    type types-sros:time-duration;
                    units "milliseconds";
                    description
                        "The total time in 10-millisecond units that this LSP has not
                         been operational.";
                }

                container push {
                    description "Enter the push context";

                    leaf out-if-index {
                        type uint32;
                        description "The outgoing interface index.";
                    }

                    leaf xc-index {
                        type uint32;
                        description "The index for the cross-connect.";
                    }

                    leaf out-segment-index {
                        type uint32;
                        description "The index for outgoing segment.";
                    }

                } // container push

            } // list static-lsp

            list lsp-container {
                key "container-name";
                description "Enter the lsp-container list instance";

                leaf container-name {
                    type types-sros:named-item;
                    description "LSP container name.";
                }

                leaf oper-state {
                    type types-sros:oper-state;
                    description "The current operational state of the LSP Container.";
                }

                leaf oper-down-reason {
                    type enumeration {
                        enum admin-down                     { value 1; }
                        enum lsp-name-conflict              { value 2; }
                        enum no-resources-available         { value 3; }
                        enum no-lsp-operational             { value 4; }
                    }
                    description "The reason due to which the LSP container is operationally down.";
                }

                leaf member-lsp-count {
                    type yang:gauge32;
                    description "The number of member LSPs in the LSP container.";
                }

                leaf member-lsp-up-count {
                    type yang:gauge32;
                    description "The number of member LSPs in the LSP container that are operationally up.";
                }

                leaf nominal-lsp-count {
                    type yang:gauge32;
                    description "The nominal number of member LSPs in the LSP container.";
                }

                leaf nominal-bandwidth {
                    type uint32;
                    units "megabps";
                    description
                        "The nominal bandwidth, in mega-bits per second, computed for
                         each member LSP in the LSP container.";
                }

                leaf optimization-time-remaining {
                    type uint32;
                    units "seconds";
                    description
                        "The time remaining, in seconds, till the optimization timer
                         expires and optimization is started for the LSP container.";
                }

                leaf ad-hoc-optimization-pending {
                    type boolean;
                    description "Indicates whether ad-hoc optimization is pending for the LSP container.";
                }

                leaf ad-hoc-optimization-event {
                    type enumeration {
                        enum lsp-auto-bw-failed             { value 1; }
                        enum lsp-failed-to-establish        { value 2; }
                        enum lsp-auto-bw-skipped            { value 3; }
                    }
                    description "The ad-hoc optimization event for the LSP container.";
                }

                container last-optimization {
                    description "Enter the last-optimization context";

                    leaf start-time {
                        type yang:date-and-time;
                        description "The system time when the last optimization started for the LSP container.";
                    }

                    leaf status {
                        type enumeration {
                            enum completed                      { value 1; }
                            enum failed                         { value 2; }
                        }
                        description "The status of the last optimization.";
                    }

                    leaf reason {
                        type enumeration {
                            enum timer-based                    { value 1; }
                            enum ad-hoc                         { value 2; }
                            enum config-param-modified          { value 3; }
                        }
                        description "The reason for the last optimization.";
                    }

                } // container last-optimization

                list member-lsp {
                    key "member-id";
                    description "Enter the member-lsp list instance";

                    leaf member-id {
                        type uint32 {
                            range "1..64";
                        }
                        description "Unique ID for the member LSP within the LSP container.";
                    }

                    leaf lsp-name {
                        type types-sros:named-item-64;
                        description "The name of the member LSP.";
                    }

                    leaf oper-state {
                        type types-sros:oper-state;
                        description "The current operational state of the member LSP.";
                    }

                    leaf tunnel-id {
                        type uint32;
                        description "The tunnel ID for the member LSP.";
                    }

                    leaf oper-bandwidth {
                        type uint32;
                        units "megabps";
                        description
                            "The operational bandwidth, in mega-bits per second, for
                             the member LSP.";
                    }

                    leaf sampled-avg-rate {
                        type uint32;
                        units "megabps";
                        description
                            "The sampled average rate, in mega-bits per second, for
                             the member LSP.";
                    }

                } // list member-lsp

            } // list lsp-container

            container forwarding-policies {
                description "Enter the forwarding-policies context";

                leaf oper-state {
                    type types-sros:oper-state;
                    description "The current operational state of Forwarding Policies.";
                }

                leaf oper-down-reason {
                    type enumeration {
                        enum not-applicable                 { value 0; }
                        enum admin-down                     { value 1; }
                        enum mpls-oper-down                 { value 2; }
                    }
                    description "The reason due to which Forwarding Policies is operationally down.";
                }

                list forwarding-policy {
                    key "policy-name";
                    description "Enter the forwarding-policy list instance";

                    leaf policy-name {
                        type types-sros:named-item-64;
                        description "Administrative name for Forwarding Policy.";
                    }

                    leaf oper-state {
                        type types-sros:oper-state;
                        description "The current operational state of this Forwarding Policy.";
                    }

                    list next-hop-group {
                        key "index";
                        description "Enter the next-hop-group list instance";

                        leaf index {
                            type uint32 {
                                range "1..32";
                            }
                            description "Index for next-hop group.";
                        }

                        leaf oper-state {
                            type types-sros:oper-state;
                            description "The current operational state of this next-hop group.";
                        }

                        container primary-next-hop {
                            description "Enter the primary-next-hop context";

                            leaf oper-state {
                                type types-sros:oper-state;
                                description "The current operational state of this next-hop.";
                            }

                        } // container primary-next-hop

                        container backup-next-hop {
                            description "Enter the backup-next-hop context";

                            leaf oper-state {
                                type types-sros:oper-state;
                                description "The current operational state of this next-hop.";
                            }

                        } // container backup-next-hop

                    } // list next-hop-group

                } // list forwarding-policy

                list binding-label {
                    key "label";
                    description "Enter the binding-label list instance";

                    leaf label {
                        type types-sros:mpls-label;
                        description "Binding Label for forwarding path.";
                    }

                    container ingress-statistics {
                        description "Enter the ingress-statistics context";

                        leaf packets {
                            type yang:counter64;
                            description "Total number of ingress packets for a binding label instance.";
                        }

                        leaf octets {
                            type yang:counter64;
                            description "Total number of ingress octets for a binding label instance.";
                        }

                    } // container ingress-statistics

                    list path {
                        key "path-id";
                        description "Enter the path list instance";

                        leaf path-id {
                            type uint32 {
                                range "1..max";
                            }
                            description "Path-ID for forwarding path.";
                        }

                        leaf policy-name {
                            type types-sros:named-item;
                            description "Indicates the policy name of this path.";
                        }

                        leaf preference {
                            type uint8;
                            description "Indicates the preference number of this path.";
                        }

                        leaf oper-state {
                            type types-sros:oper-state;
                            description "The current operational state of this path.";
                        }

                        leaf oper-down-reason {
                            type enumeration {
                                enum not-applicable                 { value 0; }
                                enum memory-allocation-failed       { value 1; }
                                enum invalid-endpoint-address       { value 2; }
                                enum invalid-binding-label          { value 3; }
                                enum duplicate-policy               { value 4; }
                                enum invalid-next-hop               { value 5; }
                                enum iom-programming-failed         { value 6; }
                                enum back-pressured                 { value 7; }
                                enum higher-preference-policy-programmed { value 8; }
                                enum label-not-available            { value 9; }
                                enum stats-allocation-failed        { value 10; }
                                enum max-policy-exceeded            { value 11; }
                                enum no-next-hops                   { value 12; }
                            }
                            description "The reason for the path being operationally down.";
                        }

                        leaf num-next-hop-groups {
                            type uint32 {
                                range "0..32";
                            }
                            description "Indicates the number of next-hop groups for this path.";
                        }

                        leaf retry-count {
                            type yang:counter32;
                            description "Indicates the number of retry attempts to bring up this path.";
                        }

                        leaf next-retry-in {
                            type uint32;
                            units "seconds";
                            description "Indicates the time remaining till the next retry to bring up this path.";
                        }

                        leaf revert-timer {
                            type uint32 {
                                range "0..600";
                            }
                            units "seconds";
                            description "Indicates the revert timer for this path.";
                        }

                        leaf ingress-stats {
                            type boolean;
                            description "Indicates whether ingress statistics are enabled for this path.";
                        }

                        leaf ingress-stats-oper-state {
                            type types-sros:oper-state;
                            description "The current operational state of ingress-statistics for this path.";
                        }

                        container egress-statistics {
                            description "Enter the egress-statistics context";

                            leaf overall-oper-state {
                                type types-sros:oper-state;
                                description "The operational state of egress statistics across all next-hops.";
                            }

                            leaf total-packets {
                                type yang:counter64;
                                description "Total number of egress packets for all next-hops.";
                            }

                            leaf total-octets {
                                type yang:counter64;
                                description "Total number of egress octets for all next-hops.";
                            }

                        } // container egress-statistics

                        list next-hop-group {
                            key "index";
                            description "Enter the next-hop-group list instance";

                            leaf index {
                                type uint32 {
                                    range "1..32";
                                }
                                description "Index for next-hop group.";
                            }

                            leaf oper-state {
                                type types-sros:oper-state;
                                description "The current operational state of this next-hop group.";
                            }

                            leaf resolution-type {
                                type enumeration {
                                    enum direct                         { value 1; }
                                    enum indirect                       { value 2; }
                                }
                                description "Indicates the resolution type of this next-hop group.";
                            }

                            leaf load-balancing-weight {
                                type uint32 {
                                    range "1..max";
                                }
                                description "Indicates load balancing weight of this next-hop group.";
                            }

                            leaf num-failover {
                                type yang:counter32;
                                description
                                    "The number of failovers from primary to backup next-hop for this
                                     next-hop group.";
                            }

                            leaf num-revert {
                                type yang:counter32;
                                description
                                    "The number of reverts from backup to primary next-hop for this
                                     next-hop group.";
                            }

                            leaf next-revert-in {
                                type uint32;
                                units "seconds";
                                description
                                    "The time remaining to revert from backup to primary for this
                                     next-hop group.";
                            }

                            leaf oper-down-reason {
                                type enumeration {
                                    enum not-applicable                 { value 0; }
                                    enum next-hop-not-resolved          { value 1; }
                                    enum next-hop-is-local              { value 3; }
                                    enum next-hop-is-multicast          { value 4; }
                                    enum resolution-type-mismatch       { value 5; }
                                }
                                description "The reason for the path next-hop group being operationally down.";
                            }

                            container primary-next-hop {
                                description "Enter the primary-next-hop context";

                                leaf next-hop {
                                    type types-sros:ip-unicast-address;
                                    description "Indicates the address of the next-hop.";
                                }

                                leaf resolved {
                                    type boolean;
                                    description "Indicates if next-hop is resolved or not.";
                                }

                                leaf down-reason-code {
                                    type enumeration {
                                        enum not-applicable                 { value 0; }
                                        enum nexthop-not-resolved           { value 1; }
                                        enum nexthop-islocal                { value 3; }
                                        enum nexthop-ismcast                { value 4; }
                                        enum restype-mismatch               { value 5; }
                                    }
                                    description "The reason for the path next-hop being operationally down.";
                                }

                                leaf egress-statistics-oper-state {
                                    type types-sros:oper-state;
                                    description
                                        "The current operational state of egress statistics
                                         for a next-hop group next-hop.";
                                }

                                list pushed-labels {
                                    key "index";
                                    description "Enter the pushed-labels list instance";

                                    leaf index {
                                        type uint32 {
                                            range "1..10";
                                        }
                                        description "Index for push-label.";
                                    }

                                    leaf label {
                                        type uint32 {
                                            range "1..1048575";
                                        }
                                        mandatory true;
                                        description "Push label value.";
                                    }

                                } // list pushed-labels

                                container egress-statistics {
                                    description "Enter the egress-statistics context";

                                    leaf packets {
                                        type yang:counter64;
                                        description
                                            "The value of packets indicates the total number of egress packets
                                             for a next-hop group next-hop.";
                                    }

                                    leaf octets {
                                        type yang:counter64;
                                        description
                                            "The value of octets indicates the total number of egress octets
                                             for a next-hop group next-hop.";
                                    }

                                } // container egress-statistics

                            } // container primary-next-hop

                            container backup-next-hop {
                                description "Enter the backup-next-hop context";

                                leaf next-hop {
                                    type types-sros:ip-unicast-address;
                                    description "Indicates the address of the next-hop.";
                                }

                                leaf resolved {
                                    type boolean;
                                    description "Indicates if next-hop is resolved or not.";
                                }

                                leaf down-reason-code {
                                    type enumeration {
                                        enum not-applicable                 { value 0; }
                                        enum nexthop-not-resolved           { value 1; }
                                        enum nexthop-islocal                { value 3; }
                                        enum nexthop-ismcast                { value 4; }
                                        enum restype-mismatch               { value 5; }
                                    }
                                    description "The reason for the path next-hop being operationally down.";
                                }

                                leaf egress-statistics-oper-state {
                                    type types-sros:oper-state;
                                    description
                                        "The current operational state of egress statistics
                                         for a next-hop group next-hop.";
                                }

                                list pushed-labels {
                                    key "index";
                                    description "Enter the pushed-labels list instance";

                                    leaf index {
                                        type uint32 {
                                            range "1..10";
                                        }
                                        description "Index for push-label.";
                                    }

                                    leaf label {
                                        type uint32 {
                                            range "1..1048575";
                                        }
                                        mandatory true;
                                        description "Push label value.";
                                    }

                                } // list pushed-labels

                                container egress-statistics {
                                    description "Enter the egress-statistics context";

                                    leaf packets {
                                        type yang:counter64;
                                        description
                                            "The value of packets indicates the total number of egress packets
                                             for a next-hop group next-hop.";
                                    }

                                    leaf octets {
                                        type yang:counter64;
                                        description
                                            "The value of octets indicates the total number of egress octets
                                             for a next-hop group next-hop.";
                                    }

                                } // container egress-statistics

                            } // container backup-next-hop

                        } // list next-hop-group

                    } // list path

                } // list binding-label

                list endpoint {
                    key "ip-address";
                    description "Enter the endpoint list instance";

                    leaf ip-address {
                        type types-sros:ip-address;
                        description "Binding endpoint address for forwarding path.";
                    }

                    list path {
                        key "path-id";
                        description "Enter the path list instance";

                        leaf path-id {
                            type uint32 {
                                range "1..max";
                            }
                            description "Path-ID for forwarding path.";
                        }

                        leaf policy-name {
                            type types-sros:named-item;
                            description "Indicates the policy name of this path.";
                        }

                        leaf preference {
                            type uint8;
                            description "Indicates the preference number of this path.";
                        }

                        leaf oper-state {
                            type types-sros:oper-state;
                            description "The current operational state of this path.";
                        }

                        leaf oper-down-reason {
                            type enumeration {
                                enum not-applicable                 { value 0; }
                                enum memory-allocation-failed       { value 1; }
                                enum invalid-endpoint-address       { value 2; }
                                enum invalid-binding-label          { value 3; }
                                enum duplicate-policy               { value 4; }
                                enum invalid-next-hop               { value 5; }
                                enum iom-programming-failed         { value 6; }
                                enum back-pressured                 { value 7; }
                                enum higher-preference-policy-programmed { value 8; }
                                enum label-not-available            { value 9; }
                                enum stats-allocation-failed        { value 10; }
                                enum max-policy-exceeded            { value 11; }
                                enum no-next-hops                   { value 12; }
                            }
                            description "The reason for the path being operationally down.";
                        }

                        leaf num-next-hop-groups {
                            type uint32 {
                                range "0..32";
                            }
                            description "Indicates the number of next-hop groups for this path.";
                        }

                        leaf retry-count {
                            type yang:counter32;
                            description "Indicates the number of retry attempts to bring up this path.";
                        }

                        leaf next-retry-in {
                            type uint32;
                            units "seconds";
                            description "Indicates the time remaining till the next retry to bring up this path.";
                        }

                        leaf revert-timer {
                            type uint32 {
                                range "0..600";
                            }
                            units "seconds";
                            description "Indicates the revert timer for this path.";
                        }

                        leaf metric {
                            type uint32 {
                                range "0..16777215";
                            }
                            description "Metric of this forwarding policy path.";
                        }

                        leaf tunnel-table-preference {
                            type uint8;
                            description "Tunnel-table-preference of this forwarding policy path.";
                        }

                        container egress-statistics {
                            description "Enter the egress-statistics context";

                            leaf overall-oper-state {
                                type types-sros:oper-state;
                                description "The operational state of egress statistics across all next-hops.";
                            }

                            leaf total-packets {
                                type yang:counter64;
                                description "Total number of egress packets for all next-hops.";
                            }

                            leaf total-octets {
                                type yang:counter64;
                                description "Total number of egress octets for all next-hops.";
                            }

                        } // container egress-statistics

                        list next-hop-group {
                            key "index";
                            description "Enter the next-hop-group list instance";

                            leaf index {
                                type uint32 {
                                    range "1..32";
                                }
                                description "Index for next-hop group.";
                            }

                            leaf oper-state {
                                type types-sros:oper-state;
                                description "The current operational state of this next-hop group.";
                            }

                            leaf resolution-type {
                                type enumeration {
                                    enum direct                         { value 1; }
                                    enum indirect                       { value 2; }
                                }
                                description "Indicates the resolution type of this next-hop group.";
                            }

                            leaf load-balancing-weight {
                                type uint32 {
                                    range "1..max";
                                }
                                description "Indicates load balancing weight of this next-hop group.";
                            }

                            leaf num-failover {
                                type yang:counter32;
                                description
                                    "The number of failovers from primary to backup next-hop for this
                                     next-hop group.";
                            }

                            leaf num-revert {
                                type yang:counter32;
                                description
                                    "The number of reverts from backup to primary next-hop for this
                                     next-hop group.";
                            }

                            leaf next-revert-in {
                                type uint32;
                                units "seconds";
                                description
                                    "The time remaining to revert from backup to primary for this
                                     next-hop group.";
                            }

                            leaf oper-down-reason {
                                type enumeration {
                                    enum not-applicable                 { value 0; }
                                    enum next-hop-not-resolved          { value 1; }
                                    enum next-hop-is-local              { value 3; }
                                    enum next-hop-is-multicast          { value 4; }
                                    enum resolution-type-mismatch       { value 5; }
                                }
                                description "The reason for the path next-hop group being operationally down.";
                            }

                            container primary-next-hop {
                                description "Enter the primary-next-hop context";

                                leaf next-hop {
                                    type types-sros:ip-unicast-address;
                                    description "Indicates the address of the next-hop.";
                                }

                                leaf resolved {
                                    type boolean;
                                    description "Indicates if next-hop is resolved or not.";
                                }

                                leaf down-reason-code {
                                    type enumeration {
                                        enum not-applicable                 { value 0; }
                                        enum nexthop-not-resolved           { value 1; }
                                        enum nexthop-islocal                { value 3; }
                                        enum nexthop-ismcast                { value 4; }
                                        enum restype-mismatch               { value 5; }
                                    }
                                    description "The reason for the path next-hop being operationally down.";
                                }

                                leaf egress-statistics-oper-state {
                                    type types-sros:oper-state;
                                    description
                                        "The current operational state of egress statistics
                                         for a next-hop group next-hop.";
                                }

                                list pushed-labels {
                                    key "index";
                                    description "Enter the pushed-labels list instance";

                                    leaf index {
                                        type uint32 {
                                            range "1..10";
                                        }
                                        description "Index for push-label.";
                                    }

                                    leaf label {
                                        type uint32 {
                                            range "1..1048575";
                                        }
                                        mandatory true;
                                        description "Push label value.";
                                    }

                                } // list pushed-labels

                                container egress-statistics {
                                    description "Enter the egress-statistics context";

                                    leaf packets {
                                        type yang:counter64;
                                        description
                                            "The value of packets indicates the total number of egress packets
                                             for a next-hop group next-hop.";
                                    }

                                    leaf octets {
                                        type yang:counter64;
                                        description
                                            "The value of octets indicates the total number of egress octets
                                             for a next-hop group next-hop.";
                                    }

                                } // container egress-statistics

                            } // container primary-next-hop

                            container backup-next-hop {
                                description "Enter the backup-next-hop context";

                                leaf next-hop {
                                    type types-sros:ip-unicast-address;
                                    description "Indicates the address of the next-hop.";
                                }

                                leaf resolved {
                                    type boolean;
                                    description "Indicates if next-hop is resolved or not.";
                                }

                                leaf down-reason-code {
                                    type enumeration {
                                        enum not-applicable                 { value 0; }
                                        enum nexthop-not-resolved           { value 1; }
                                        enum nexthop-islocal                { value 3; }
                                        enum nexthop-ismcast                { value 4; }
                                        enum restype-mismatch               { value 5; }
                                    }
                                    description "The reason for the path next-hop being operationally down.";
                                }

                                leaf egress-statistics-oper-state {
                                    type types-sros:oper-state;
                                    description
                                        "The current operational state of egress statistics
                                         for a next-hop group next-hop.";
                                }

                                list pushed-labels {
                                    key "index";
                                    description "Enter the pushed-labels list instance";

                                    leaf index {
                                        type uint32 {
                                            range "1..10";
                                        }
                                        description "Index for push-label.";
                                    }

                                    leaf label {
                                        type uint32 {
                                            range "1..1048575";
                                        }
                                        mandatory true;
                                        description "Push label value.";
                                    }

                                } // list pushed-labels

                                container egress-statistics {
                                    description "Enter the egress-statistics context";

                                    leaf packets {
                                        type yang:counter64;
                                        description
                                            "The value of packets indicates the total number of egress packets
                                             for a next-hop group next-hop.";
                                    }

                                    leaf octets {
                                        type yang:counter64;
                                        description
                                            "The value of octets indicates the total number of egress octets
                                             for a next-hop group next-hop.";
                                    }

                                } // container egress-statistics

                            } // container backup-next-hop

                        } // list next-hop-group

                    } // list path

                } // list endpoint

            } // container forwarding-policies

            container pce-init-lsp {
                description "Enter the pce-init-lsp context";

                container sr-te {
                    description "Enter the sr-te context";

                    leaf oper-state {
                        type types-sros:oper-state;
                        description "The current operational state of PCE initiated SR-TE LSPs.";
                    }

                    leaf oper-down-reason {
                        type enumeration {
                            enum not-applicable                 { value 0; }
                            enum admin-down                     { value 1; }
                            enum mpls-oper-down                 { value 2; }
                        }
                        description "The reason due to which PCE initiated SR-TE LSPs is operationally down.";
                    }

                } // container sr-te

            } // container pce-init-lsp

            container ingress-statistics {
                description "Enter the ingress-statistics context";

                list p2mp-template-lsp {
                    key "sender rsvp-session-name";
                    description "Enter the p2mp-template-lsp list instance";

                    leaf sender {
                        type types-sros:ip-unicast-address;
                        description "Indicates the sender address.";
                    }

                    leaf rsvp-session-name {
                        type types-sros:named-item-64;
                        description "Administrative name for RSVP session.";
                    }

                    leaf total-session {
                        type uint32;
                        description "Indicates the total number of sessions.";
                    }

                } // list p2mp-template-lsp

                list p2p-template-lsp {
                    key "sender rsvp-session-name";
                    description "Enter the p2p-template-lsp list instance";

                    leaf sender {
                        type types-sros:ip-unicast-address;
                        description "Indicates the sender address.";
                    }

                    leaf rsvp-session-name {
                        type types-sros:named-item-64;
                        description "Administrative name for RSVP session.";
                    }

                    leaf total-session {
                        type uint32;
                        description "Indicates the total number of sessions.";
                    }

                } // list p2p-template-lsp

            } // container ingress-statistics

            container lsp-totals {
                description "Enter the lsp-totals context";

                container p2p-static-mpls {
                    description "Enter the p2p-static-mpls context";

                    leaf originate-lsp-count {
                        type yang:gauge32;
                        description "The number of static LSPs that originate at this virtual router.";
                    }

                    leaf transit-lsp-count {
                        type yang:gauge32;
                        description "The number of static LSPs that transit at this virtual router.";
                    }

                    leaf terminate-lsp-count {
                        type yang:gauge32;
                        description "The number of static LSPs that terminate at this virtual router.";
                    }

                } // container p2p-static-mpls

                container p2p-rsvp {
                    description "Enter the p2p-rsvp context";

                    leaf originate-lsp-count {
                        type yang:gauge32;
                        description
                            "The number of RSVP sessions originating on this virtual router.
                             This count includes sessions associated with LSPs of type p2p-rsvp and 
                             p2p-rsvp-bypass, and dynamic bypass LSPs but excludes sessions 
                             associated with LSPs of type p2p-rsvp-one-hop, p2p-rsvp-mesh and p2p-rsvp-member.";
                    }

                    leaf transit-lsp-count {
                        type yang:gauge32;
                        description "The number of RSVP sessions that transit at this virtual router.";
                    }

                    leaf terminate-lsp-count {
                        type yang:gauge32;
                        description "The number of RSVP sessions that terminate at this virtual router.";
                    }

                    leaf originate-detour-count {
                        type yang:gauge32;
                        description "The number of RSVP detours that originate at this virtual router.";
                    }

                    leaf transit-detour-count {
                        type yang:gauge32;
                        description "The number of RSVP detours that transit at this virtual router.";
                    }

                    leaf terminate-detour-count {
                        type yang:gauge32;
                        description "The number of RSVP detours that terminate at this virtual router.";
                    }

                    leaf originate-mesh-lsp-count {
                        type yang:gauge32;
                        description
                            "The number of LSPs of type p2p-rsvp-mesh that are originating on
                             this router and that are operationally up.";
                    }

                    leaf originate-one-hop-lsp-count {
                        type yang:gauge32;
                        description
                            "The number of LSPs of type p2p-rsvp-one-hop that are originating
                             on this router and that are operationally up.";
                    }

                    leaf originate-member-lsp-count {
                        type yang:gauge32;
                        description
                            "The number of LSPs of type p2p-rsvp-member that are originating
                             on this router and that are operationally up.";
                    }

                    leaf lsp-up-count {
                        type yang:gauge32;
                        description
                            "The number of LSPs of type p2p-rsvp that are originating on this
                             router and that are operationally up.";
                    }

                } // container p2p-rsvp

                container p2mp-rsvp {
                    description "Enter the p2mp-rsvp context";

                    leaf originate-s2l-count {
                        type yang:gauge32;
                        description "The number of RSVP P2MP S2L sessions that originate at this virtual router.";
                    }

                    leaf transit-s2l-count {
                        type yang:gauge32;
                        description "The number of RSVP P2MP S2L sessions that transit at this virtual router.";
                    }

                    leaf terminate-s2l-count {
                        type yang:gauge32;
                        description "The number of RSVP P2MP S2L sessions that terminate at this virtual router.";
                    }

                } // container p2mp-rsvp

                container p2p-mpls-tp {
                    description "Enter the p2p-mpls-tp context";

                    leaf originate-lsp-count {
                        type yang:gauge32;
                        description "The number of MPLS TP LSPs that originate at this virtual router.";
                    }

                    leaf transit-lsp-count {
                        type yang:gauge32;
                        description "The number of MPLS TP LSPs that transit at this virtual router.";
                    }

                    leaf terminate-lsp-count {
                        type yang:gauge32;
                        description "The number of MPLS TP LSPs that terminate at this virtual router.";
                    }

                    leaf originate-path-instance-count {
                        type yang:gauge32;
                        description "The number of MPLS TP LSPs originate path instances.";
                    }

                    leaf transit-path-instance-count {
                        type yang:gauge32;
                        description "The number of MPLS TP LSPs transit path instances.";
                    }

                    leaf terminate-path-instance-count {
                        type yang:gauge32;
                        description "The number of MPLS TP LSPs terminated path instances.";
                    }

                } // container p2p-mpls-tp

                container p2p-sr-te {
                    description "Enter the p2p-sr-te context";

                    leaf originate-lsp-count {
                        type yang:gauge32;
                        description
                            "The number of Segment Routing TE LSPs that are originating at
                             this virtual router and that are operationally up.";
                    }

                    leaf originate-mesh-lsp-count {
                        type yang:gauge32;
                        description
                            "The number of Mesh P2P Segment Routing TE LSPs that are originating
                             at this virtual router and that are operationally up.";
                    }

                    leaf originate-one-hop-lsp-count {
                        type yang:gauge32;
                        description
                            "The number of one-hop P2P Segment Routing TE LSPs that are
                             originating at this virtual router and that are operationally up.";
                    }

                    leaf originate-pce-init-lsp-count {
                        type yang:gauge32;
                        description
                            "The number of PCE initiated P2P Segment Routing TE LSPs that are
                             originating at this virtual router and that are operationally up.";
                    }

                    leaf originate-on-demand-lsp-count {
                        type yang:gauge32;
                        description
                            "The number of On Demand P2P Segment Routing TE LSPs that are
                             originating at this virtual router and that are operationally up.";
                    }

                    leaf ipv4-up-count {
                        type yang:gauge32;
                        description
                            "The number of Ipv4 SR-TE LSPs operationally up on this virtual router
                             and that are operationally up.";
                    }

                    leaf ipv6-up-count {
                        type yang:gauge32;
                        description
                            "The number of Ipv6 SR-TE LSPs operationally up on this virtual router
                             and that are operationally up.";
                    }

                    leaf mesh-ipv4-up-count {
                        type yang:gauge32;
                        description
                            "The number of Ipv4 Mesh P2P SR-TE LSPs operationally up on this virtual router
                             and that are operationally up.";
                    }

                    leaf mesh-ipv6-up-count {
                        type yang:gauge32;
                        description
                            "The number of Ipv6 Mesh P2P SR-TE LSPs operationally up on this virtual router
                             and that are operationally up.";
                    }

                    leaf one-hop-ipv4-up-count {
                        type yang:gauge32;
                        description
                            "The number of Ipv4 One hop P2P SR-TE LSPs operationally up on this virtual router
                             and that are operationally up.";
                    }

                    leaf one-hop-ipv6-up-count {
                        type yang:gauge32;
                        description
                            "The number of Ipv6 One hop P2P SR-TE LSPs operationally up on this virtual router
                             and that are operationally up.";
                    }

                    leaf pce-init-ipv4-up-count {
                        type yang:gauge32;
                        description
                            "The number of Ipv4 PCE INIT P2P SR-TE LSPs operationally up on this virtual router
                             and that are operationally up.";
                    }

                    leaf pce-init-ipv6-up-count {
                        type yang:gauge32;
                        description
                            "The number of Ipv6 PCE INIT P2P SR-TE LSPs operationally up on this virtual router
                             and that are operationally up.";
                    }

                    leaf on-demand-ipv4-up-count {
                        type yang:gauge32;
                        description
                            "The number of Ipv4 On Demand P2P SR-TE LSPs operationally up on this virtual router
                             and that are operationally up.";
                    }

                    leaf on-demand-ipv6-up-count {
                        type yang:gauge32;
                        description
                            "The number of Ipv6 On Demand P2P SR-TE LSPs operationally up on this virtual router
                             and that are operationally up.";
                    }

                } // container p2p-sr-te

                container ingress {
                    description "Enter the ingress context";

                    leaf lsp-stats-object-count {
                        type yang:counter32;
                        description "The number of LSP ingress statistics configured on this virtual router.";
                    }

                } // container ingress

                container egress {
                    description "Enter the egress context";

                    leaf lsp-stats-object-count {
                        type yang:counter32;
                        description "The number of LSP egress statistics configured on this virtual router.";
                    }

                } // container egress

            } // container lsp-totals

            container statistics {
                description "Enter the statistics context";

                list lsp-ingress {
                    key "sender lsp-name";
                    description "Enter the lsp-ingress list instance";

                    leaf sender {
                        type types-sros:ip-address;
                        description "Indicates the sender address.";
                    }

                    leaf lsp-name {
                        type types-sros:named-item-64;
                        description "Administrative name for Labeled Switch Path.";
                    }

                    container fc {
                        description "Enter the fc context";

                        container be {
                            description "Enter the be context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container be

                        container l2 {
                            description "Enter the l2 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container l2

                        container af {
                            description "Enter the af context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container af

                        container l1 {
                            description "Enter the l1 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container l1

                        container h2 {
                            description "Enter the h2 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container h2

                        container ef {
                            description "Enter the ef context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container ef

                        container h1 {
                            description "Enter the h1 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container h1

                        container nc {
                            description "Enter the nc context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container nc

                    } // container fc

                    container aggregate {
                        description "Enter the aggregate context";

                        leaf packets {
                            type yang:counter64;
                            description
                                "The value of packets indicates the aggregated value of all in profile
                                 and out profile packets received for all forwarding classes.";
                        }

                        leaf octets {
                            type yang:counter64;
                            description
                                "The value of octets indicates the aggregated value of all in profile
                                 and out profile octets received for all forwarding classes.";
                        }

                    } // container aggregate

                } // list lsp-ingress

                list lsp-egress {
                    key "lsp-name";
                    description "Enter the lsp-egress list instance";

                    leaf lsp-name {
                        type types-mpls:lsp-name;
                        description "Administrative name for Labeled Switch Path.";
                    }

                    container fc {
                        description "Enter the fc context";

                        container be {
                            description "Enter the be context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container be

                        container l2 {
                            description "Enter the l2 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container l2

                        container af {
                            description "Enter the af context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container af

                        container l1 {
                            description "Enter the l1 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container l1

                        container h2 {
                            description "Enter the h2 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container h2

                        container ef {
                            description "Enter the ef context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container ef

                        container h1 {
                            description "Enter the h1 context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container h1

                        container nc {
                            description "Enter the nc context";

                            leaf in-profile-packets {
                                type yang:counter64;
                                description
                                    "The value of in-profile-packets indicates the number of in profile packets
                                     received for a specific FC.";
                            }

                            leaf out-profile-packets {
                                type yang:counter64;
                                description
                                    "The value of out-profile-packets indicates the number of out of profile packets
                                     received for a specific FC.";
                            }

                            leaf in-profile-octets {
                                type yang:counter64;
                                description
                                    "The value of in-profile-octets indicates the number of in profile octets
                                     received for a specific FC.";
                            }

                            leaf out-profile-octets {
                                type yang:counter64;
                                description
                                    "The value of out-profile-octets indicates the number of out of profile octets
                                     received for a specific FC.";
                            }

                        } // container nc

                    } // container fc

                    container aggregate {
                        description "Enter the aggregate context";

                        leaf packets {
                            type yang:counter64;
                            description
                                "The value of packets indicates the aggregated value of all in profile
                                 and out profile packets received for all forwarding classes.";
                        }

                        leaf octets {
                            type yang:counter64;
                            description
                                "The value of octets indicates the aggregated value of all in profile
                                 and out profile octets received for all forwarding classes.";
                        }

                        leaf packet-rate {
                            type yang:counter32;
                            units "packets per second";
                            description "The value of packet-rate indicates the average rate in packets per second for the collection interval that ended most recently.";
                        }

                        leaf bits-rate {
                            type yang:counter32;
                            units "megabps";
                            description
                                "The value of bits-rate indicates the average rate in megabits per second (Mbps)
                                 for the collection interval that ended most recently.";
                        }

                    } // container aggregate

                    list lsp-path {
                        key "path-name";
                        description "Enter the lsp-path list instance";

                        leaf path-name {
                            type types-sros:named-item-64;
                            description "The path name.";
                        }

                        leaf packets {
                            type yang:counter64;
                            description "Total number of egress packets for a SR-TE LSP path.";
                        }

                        leaf octets {
                            type yang:counter64;
                            description "Total number of egress octets for a SR-TE LSP path.";
                        }

                        leaf oper-state {
                            type types-sros:oper-state;
                            description "The current egress statistics operational state of SR-TE LSPs.";
                        }

                    } // list lsp-path

                } // list lsp-egress

            } // container statistics

            list actual-route-hop-list {
                key "hop-list-index hop-index";
                description "Enter the actual-route-hop-list list instance";

                leaf hop-list-index {
                    type int32;
                    description "Primary index identifying a particular hop list.";
                }

                leaf hop-index {
                    type int32;
                    description "Secondary index identifying a particular hop.";
                }

                leaf ip-address {
                    type types-sros:ip-address;
                    description "IP Address for this hop.";
                }

                leaf is-loose {
                    type boolean;
                    description "Indicates if this tunnel hop is loose.";
                }

                leaf unnumbered-if-id {
                    type uint32;
                    description "The value of unnumbered interface identifier of this hop.";
                }

                leaf router-id {
                    type types-sros:ip-address;
                    description "The value of router ID.";
                }

                leaf hop-type {
                    type enumeration {
                        enum ipv4                           { value 1; }
                        enum ipv6                           { value 2; }
                        enum unnum                          { value 4; }
                    }
                    description "Hop type.";
                }

                leaf flags {
                    type bits {
                        bit local-protection-available     { position 0; }
                        bit local-protection-in-use        { position 1; }
                        bit bandwidth-protection           { position 2; }
                        bit node-protection                { position 3; }
                        bit preemption-pending             { position 4; }
                        bit node-id                        { position 5; }
                    }
                    description "Flags for this hop.";
                }

                leaf record-label {
                    type uint32;
                    description "Label recorded for this hop.";
                }

                leaf sid-type {
                    type enumeration {
                        enum not-applicable                 { value 1; }
                        enum node-sid                       { value 2; }
                        enum adjacency-sid                  { value 3; }
                    }
                    description "Type of Segment Identifier (SID).";
                }

            } // list actual-route-hop-list

            list computed-hop-list {
                key "hop-list-index hop-index";
                description "Enter the computed-hop-list list instance";

                leaf hop-list-index {
                    type int32;
                    description "Primary index identifying a particular hop list.";
                }

                leaf hop-index {
                    type int32;
                    description "Secondary index identifying a particular hop.";
                }

                leaf ip-address {
                    type types-sros:ip-address;
                    description "IP Address for this hop.";
                }

                leaf is-loose {
                    type boolean;
                    description "Indicates if this tunnel hop is loose.";
                }

                leaf unnumbered-if-id {
                    type uint32;
                    description "The value of unnumbered interface identifier of this hop.";
                }

                leaf router-id {
                    type types-sros:ip-address;
                    description "The value of router ID.";
                }

                leaf hop-type {
                    type enumeration {
                        enum ipv4                           { value 1; }
                        enum ipv6                           { value 2; }
                        enum unnum                          { value 5; }
                    }
                    description "Hop type.";
                }

                leaf egress-admin-group {
                    type uint32;
                    description "The value of administrative groups on the egressing interface for this hop.";
                }

                leaf is-abr {
                    type boolean;
                    description "Indicates whether this hop is an Area Border Router (ABR) or not.";
                }

            } // list computed-hop-list

        } // container mpls

    } // grouping state-router-mpls

}
