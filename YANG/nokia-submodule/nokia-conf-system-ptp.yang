submodule nokia-conf-system-ptp {

    yang-version "1.1";

    belongs-to nokia-conf { prefix "conf"; }

    import ietf-yang-types                { prefix "yang"; }
    import nokia-sros-yang-extensions     { prefix "sros-ext"; }
    import nokia-types-ptp                { prefix "types-ptp"; }
    import nokia-types-sros               { prefix "types-sros"; }

    include nokia-conf-groups;
    include nokia-conf-port;

    sros-ext:sros-major-release "rel26";
    organization "Nokia";
    contact
        "Nokia SR OS Support
         Web: <http://www.nokia.com>";
    description
        "Nokia YANG Data model to configure system ptp parameters on SR OS based routers.

         Copyright 2016 Nokia. All rights reserved. Reproduction of this document
         is authorized on the condition that the foregoing copyright notice is included.

         This nokia-conf-system-ptp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-system-ptp {
        container ptp {
            description "Enter the ptp context";

            leaf admin-state {
                type types-sros:admin-state;
                default "disable";
                description "Administrative state of PTP";
            }

            leaf announce-receipt-timeout {
                type uint32 {
                    range "2..10";
                }
                sros-ext:auto-restart-to-modify;
                default "3";
                description "Expired intervals count before timeout event declared";
            }

            leaf clock-type {
                type types-ptp:clock-type;
                sros-ext:immutable;
                sros-ext:auto-restart-to-modify;
                description "Clock type";
            }

            leaf domain {
                type types-ptp:domain;
                sros-ext:auto-restart-to-modify;
                description "PTP domain";
            }

            leaf profile {
                type types-ptp:profile;
                sros-ext:immutable;
                sros-ext:auto-restart-to-modify;
                description "PTP profile";
            }

            leaf local-priority {
                type types-ptp:priority {
                    range "1..255";
                }
                default "128";
                description "PTP clock local priority";
            }

            leaf log-announce-interval {
                type types-ptp:log-interval {
                    range "-3..4";
                }
                sros-ext:auto-restart-to-modify;
                description "Announce message interval in log form";
            }

            leaf network-type {
                type enumeration {
                    enum sonet                          { value 1; }
                    enum sdh                            { value 2; }
                }
                default "sdh";
                description "PTP network type";
            }

            leaf priority1 {
                type types-ptp:priority;
                default "128";
                description "Priority1 of the local clock";
            }

            leaf priority2 {
                type types-ptp:priority;
                default "128";
                description "Priority2 of the local clock";
            }

            leaf tx-while-sync-uncertain {
                type boolean;
                default "true";
                description "Send Announce messages while clock is unsynchronized";
            }

            leaf time-inaccuracy {
                type uint32 {
                    range "0..10000000";
                }
                units "nanoseconds";
                default "0";
                description "Time inaccuracy value override";
            }

            leaf initial-time-inaccuracy {
                type uint32 {
                    range "0..10000000";
                }
                units "nanoseconds";
                default "0";
                description "Total time inaccuracy from grandmaster to local clock";
            }

            leaf tx-path-trace {
                type boolean;
                default "false";
                description "Include PATH TRACE TLV in Announce messages";
            }

            leaf max-steps-removed {
                type uint32 {
                    range "1..255";
                }
                default "255";
                description "Threshold for steps removed in Announce messages";
            }

            leaf within-holdover-spec-timer {
                type uint32 {
                    range "0..3600";
                }
                units "seconds";
                default "600";
                description "Duration for local clock to specify the holdover state";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container ptsf {
                description "Enter the ptsf context";

                container monitor-ptsf-unusable {
                    description "Enter the monitor-ptsf-unusable context";

                    leaf admin-state {
                        type types-sros:admin-state;
                        default "disable";
                        description "Administrative state of PTSF unusable monitoring";
                    }

                } // container monitor-ptsf-unusable

            } // container ptsf

            list port {
                key "port-id";
                description "Enter the port list instance";

                leaf port-id {
                    type leafref {
                        path "../../../../port/port-id";
                    }
                    description "Ethernet PTP port ID";
                }

                leaf address {
                    type yang:mac-address;
                    default "01:1B:19:00:00:00";
                    description "Destination MAC address of the transmitted PTP messages";
                }

                leaf local-priority {
                    type types-ptp:priority {
                        range "1..255";
                    }
                    default "128";
                    description "PTP port local priority";
                }

                leaf log-delay-interval {
                    type types-ptp:log-interval {
                        range "-6..0";
                    }
                    description "Minimum interval for Delay_Req messages in log form";
                }

                leaf log-sync-interval {
                    type types-ptp:log-interval {
                        range "-6..0";
                    }
                    description "Interval for transmission of Sync messages in log form";
                }

                leaf master-only {
                    type boolean;
                    description "Restrict the local port to master state";
                }

                leaf alternate-profile {
                    type leafref {
                        path "../../alternate-profile/name";
                    }
                    description "Alternate profile for the PTP port";
                }

                leaf admin-state {
                    type types-sros:admin-state;
                    default "enable";
                    description "Administrative state of the PTP port";
                }

                leaf monitor-receiver {
                    type boolean;
                    description "Enable the PTP port as a monitor-receiver";
                }

                leaf monitor-sender {
                    type boolean;
                    description "Enable the PTP port as a monitor-sender";
                }

                leaf not-master {
                    type boolean;
                    default "false";
                    description "Block PTP port from entering the timeTransmitter state";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list port

            list router {
                key "router-instance";
                description "Enter the router list instance";

                leaf router-instance {
                    type string;
                    description "Router name or VPRN service name";
                }

                leaf peer-limit {
                    type int32 {
                        range "0..1600";
                    }
                    description "Number of discovered peers allowed for routing instance";
                }

                leaf admin-state {
                    when "not(../router-instance = 'Base')" {
                        description "router-instance must not be 'Base' to set the admin-state";
                    }
                    type types-sros:admin-state;
                    default "enable";
                    description "Administrative state of PTP on the router instance";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list peer {
                    key "ip-address";
                    description "Enter the peer list instance";

                    leaf ip-address {
                        type types-sros:ip-address;
                        description "IP address of the remote PTP peer";
                    }

                    leaf local-priority {
                        type types-ptp:priority {
                            range "1..255";
                        }
                        default "128";
                        description "PTP peer local priority";
                    }

                    leaf log-sync-interval {
                        type types-ptp:log-interval {
                            range "-6..0";
                        }
                        sros-ext:auto-restart-to-modify;
                        description "PTP peer interval for Sync messages in log form";
                    }

                    leaf admin-state {
                        type types-sros:admin-state;
                        default "enable";
                        description "Administrative state of the PTP peer";
                    }

                    leaf monitor-receiver {
                        type boolean;
                        description "Enable the PTP peer as a monitor-receiver";
                    }

                    leaf not-master {
                        type boolean;
                        default "false";
                        description "Block PTP port from entering the timeTransmitter state";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list peer

            } // list router

            list alternate-profile {
                key "name";
                max-elements 6;
                description "Enter the alternate-profile list instance";

                leaf name {
                    type types-sros:named-item-64;
                    description "Alternate profile name";
                }

                leaf admin-state {
                    type types-sros:admin-state;
                    default "disable";
                    description "Administrative state of the alternate PTP profile";
                }

                leaf profile {
                    type enumeration {
                        enum g8265dot1-2010 {
                            value 1;
                            description "ITU-T G.8265.1 specification";
                        }
                        enum ieee1588-2008 {
                            value 2;
                            description "2008 version of IEEE 1588 standard";
                        }
                        enum g8275dot1-2014 {
                            value 3;
                            description "2014 version of ITU-T G.8275.1 specification";
                        }
                        enum g8275dot2-2016 {
                            value 4;
                            description "2016 version of ITU-T G.8275.2 specification";
                        }
                        enum iec-61850-9-3-2016 {
                            value 5;
                            description "2016 version of IEC/IEEE 61850-9-3 standard";
                        }
                        enum c37dot238-2017 {
                            value 6;
                            description "2017 version of C37.238 specification";
                        }
                    }
                    sros-ext:auto-restart-to-modify;
                    default "g8275dot1-2014";
                    description "Standard based profile used within an alternate profile";
                }

                leaf domain {
                    type types-ptp:domain;
                    sros-ext:auto-restart-to-modify;
                    default "24";
                    description "Alternate profile PTP domain number";
                }

                leaf log-announce-interval {
                    type types-ptp:log-interval {
                        range "-3..4";
                    }
                    sros-ext:auto-restart-to-modify;
                    default "-3";
                    description "PTP announce message interval in log form";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list alternate-profile

        } // container ptp

    } // grouping conf-system-ptp

}
