submodule nokia-state-system-ptp {

    yang-version "1.1";

    belongs-to nokia-state { prefix "state"; }

    import ietf-yang-types                { prefix "yang"; }
    import nokia-sros-yang-extensions     { prefix "sros-ext"; }
    import nokia-types-card               { prefix "types-card"; }
    import nokia-types-port               { prefix "types-port"; }
    import nokia-types-ptp                { prefix "types-ptp"; }
    import nokia-types-services           { prefix "types-services"; }
    import nokia-types-sros               { prefix "types-sros"; }

    sros-ext:sros-major-release "rel26";
    organization "Nokia";
    contact
        "Nokia SR OS Support
         Web: <http://www.nokia.com>";
    description
        "Nokia YANG Data model with operational state for system ptp parameters on SR OS based routers.

         Copyright 2016 Nokia. All rights reserved. Reproduction of this document
         is authorized on the condition that the foregoing copyright notice is included.

         This nokia-state-system-ptp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-system-ptp {
        container ptp {
            description "Enter the ptp context";

            list instance {
                key "instance-id";
                description "Enter the instance list instance";

                leaf instance-id {
                    type types-card:cpm-card-slot;
                    description "The CPM card slot on which the current PTP instance resides.";
                }

                leaf oper-state {
                    type types-sros:oper-state;
                    description
                        "The operational state of PTP on the system.

                         On some SROS systems, PTP may remain operationally down even
                         when PTP is administratively enabled.  This occurs when the
                         PTP profile or clock-type has changed since system
                         initialization, and indicates that a system reset is required
                         to bring PTP operationally up.";
                }

                container default-ds {
                    description "Enter the default-ds context";

                    leaf two-step-flag {
                        type boolean;
                        description
                            "When set to true, the clock is a two-step clock;
                             otherwise,the clock is a one-step clock.

                             In SROS systems the clock is always one-step clock
                             and never transmits PTP 'follow up' packets.";
                    }

                    leaf clock-identity {
                        type types-ptp:clock-identity-type;
                        description "The clock identity of the local clock.";
                    }

                    container clock-quality {
                        description "Enter the clock-quality context";

                        leaf clock-class {
                            type uint8;
                            description
                                "The clock class denotes the traceability of the time
                                 or frequency distributed by the clock.";
                        }

                        leaf clock-accuracy {
                            type uint8;
                            description
                                "The clock accuracy indicates the expected accuracy
                                 of the clock.";
                        }

                        leaf offset-scaled-log-variance {
                            type uint16;
                            description
                                "The offset scaled log variance provides an estimate of
                                 the variations of the clock from a linear timescale
                                 when it is not synchronized to another clock
                                 using the protocol.";
                        }

                    } // container clock-quality

                } // container default-ds

                container current-ds {
                    description "Enter the current-ds context";

                    leaf steps-removed {
                        type uint16;
                        description
                            "The number of communication paths traversed
                             between the local clock and the grandmaster clock.";
                    }

                    leaf offset-from-master {
                        status obsolete;
                        type types-ptp:time-interval-type;
                        description
                            "The current value of the time difference between
                             a master and a slave clock as computed by the slave.

                             This leaf is obsolete as of Release 26.3 and replaced by offset-from-master-ns";
                    }

                    leaf offset-from-master-ns {
                        type int32;
                        units "nanoseconds";
                        description
                            "The current value of the time difference between
                             a master and a slave clock as computed by the slave.";
                    }

                    leaf mean-path-delay {
                        status obsolete;
                        type types-ptp:time-interval-type;
                        description
                            "The current value of the mean propagation time between
                             a master and a slave clock as computed by the slave.

                              This leaf is obsolete as of Release 26.3 and replaced by mean-delay-ns";
                    }

                    leaf mean-delay-ns {
                        type int32;
                        units "nanoseconds";
                        description
                            "The current value of the mean propagation time between
                             a master and a slave clock as computed by the slave.";
                    }

                    leaf last-calc-time {
                        type yang:date-and-time;
                        description "The time when offset-from-master-ns was last calculated.";
                    }

                    leaf mean-delay-last-calc-time {
                        type yang:date-and-time;
                        description "The time when mean-delay-ns was last calculated.";
                    }

                    leaf sync-uncertain {
                        type boolean;
                        description "Specifies the synchronization uncertain indication of the local PTP clock.";
                    }

                    leaf sync-uncertain-reason {
                        type enumeration {
                            enum not-applicable                 { value 0; }
                            enum clock-stabilization            { value 1; }
                            enum parent-uncertain               { value 2; }
                            enum parent-clock-class             { value 3; }
                            enum local-clock-class              { value 4; }
                            enum sets-not-locked                { value 5; }
                            enum sets-quality                   { value 6; }
                            enum time-not-locked                { value 7; }
                            enum freq-not-locked                { value 8; }
                        }
                        description "When sync-uncertain is true, the value indicates the reason why the value is true.";
                    }

                } // container current-ds

                container time-properties-ds {
                    description "Enter the time-properties-ds context";

                    leaf current-utc-offset-valid {
                        type boolean;
                        description "When set to true, the current UTC offset is valid.";
                    }

                    leaf current-utc-offset {
                        type int16;
                        units "seconds";
                        description
                            "The offset between International Atomic Time (TAI) and
                             Coordinated Universal Time (UTC), in seconds.";
                    }

                    leaf leap59 {
                        type boolean;
                        description
                            "When set to true, the last minute of the current UTC
                             day contains 59 seconds.";
                    }

                    leaf leap61 {
                        type boolean;
                        description
                            "When set to true, the last minute of the current UTC
                             day contains 61 seconds.";
                    }

                    leaf time-traceable {
                        type boolean;
                        description
                            "When set to true, the timescale and the
                             current-utc-offset are traceable to a primary
                             reference.";
                    }

                    leaf frequency-traceable {
                        type boolean;
                        description
                            "When set to true, the frequency determining the
                             timescale is traceable to a primary reference.";
                    }

                    leaf ptp-timescale {
                        type boolean;
                        description
                            "When set to true, the clock timescale of the
                             grandmaster clock is PTP; otherwise, the timescale is
                             ARB (arbitrary).";
                    }

                    leaf time-source {
                        type union {
                            type enumeration {
                                enum atomic-clock                   { value 16; }
                                enum gps                            { value 32; }
                                enum terrestrial-radio              { value 48; }
                                enum ptp                            { value 64; }
                                enum ntp                            { value 80; }
                                enum hand-set                       { value 96; }
                                enum other                          { value 144; }
                                enum internal-oscillator            { value 160; }
                                enum reserved                       { value 255; }
                            }
                            type types-sros:hex-string {
                                length "1";
                            }
                        }
                        description "The source of time used by the grandmaster clock.";
                    }

                    leaf time {
                        type yang:date-and-time;
                        description
                            "The current date and time.

                             If ptp-timescale, the time is converted to UTC time,
                             based on the current offset between UTC and PTP time.";
                    }

                } // container time-properties-ds

                container frequency-recovery-engine {
                    description "Enter the frequency-recovery-engine context";

                    leaf algorithm-state {
                        type enumeration {
                            enum not-applicable                 { value 0; }
                            enum initial                        { value 1; }
                            enum acquiring                      { value 2; }
                            enum phase-tracking                 { value 3; }
                            enum holdover                       { value 4; }
                            enum locked                         { value 5; }
                        }
                        description "The state of the frequency recovery process on a PTP system.";
                    }

                    leaf state-last-changed {
                        type yang:date-and-time;
                        description "Indicates the time when the frequency recovery process last changed state.";
                    }

                    leaf frequency-offset {
                        type int32;
                        description
                            "The frequency offset of the recovered clock,
                             from the nominal clock rate, in parts per trillion.

                             Positive values indicate that the recovered clock is faster
                             than nominal, negative values indicate that the recovered
                             clock is slower than nominal.";
                    }

                    container statistics {
                        description "Enter the statistics context";

                        leaf time-in-initial {
                            type uint32;
                            units "seconds";
                            description
                                "Indicates the number of seconds that the frequency recovery process
                                 has been in the initial state.";
                        }

                        leaf time-in-acquiring {
                            type uint32;
                            units "seconds";
                            description
                                "Indicates the number of seconds that the frequency recovery process
                                 has been in the acquiring state.";
                        }

                        leaf time-in-phase-tracking {
                            type uint32;
                            units "seconds";
                            description
                                "Indicates the number of seconds that the frequency recovery process
                                 has been in the phase-tracking state.";
                        }

                        leaf time-in-holdover {
                            type uint32;
                            units "seconds";
                            description
                                "Indicates the number of seconds that the frequency recovery process
                                 has been in the holdover state.";
                        }

                        leaf time-in-locked {
                            type uint32;
                            units "seconds";
                            description
                                "Indicates the number of seconds that the frequency recovery process
                                 has been in the locked state.";
                        }

                    } // container statistics

                } // container frequency-recovery-engine

                container time-recovery-engine {
                    description "Enter the time-recovery-engine context";

                    leaf algorithm-state {
                        type enumeration {
                            enum disabled                       { value 0; }
                            enum initial                        { value 1; }
                            enum acquiring                      { value 2; }
                            enum locked                         { value 3; }
                            enum holdover                       { value 4; }
                        }
                        description "The state of the time recovery process on a PTP system.";
                    }

                    leaf state-last-changed {
                        type yang:date-and-time;
                        description "Indicates the time when time recovery process last changed state.";
                    }

                    leaf last-adjustment {
                        type int64;
                        units "nanoseconds";
                        description "Specifies the last adjustment in nanoseconds to the local time of the PTP clock.";
                    }

                    leaf last-adjustment-timestamp {
                        type yang:date-and-time;
                        description "The time when last-adjustment was last calculated";
                    }

                    container statistics {
                        description "Enter the statistics context";

                        leaf time-in-initial {
                            type uint32;
                            units "seconds";
                            description
                                "Indicates the number of seconds that the time recovery process
                                 has been in the initial state.";
                        }

                        leaf time-in-acquiring {
                            type uint32;
                            units "seconds";
                            description
                                "Indicates the number of seconds that the time recovery process
                                 has been in the acquiring state.";
                        }

                        leaf time-in-locked {
                            type uint32;
                            units "seconds";
                            description
                                "Indicates the number of seconds that the time recovery process
                                 has been in the locked state.";
                        }

                        leaf time-in-holdover {
                            type uint32;
                            units "seconds";
                            description
                                "Indicates the number of seconds that the time recovery process
                                 has been in the hold-over state.";
                        }

                    } // container statistics

                } // container time-recovery-engine

                container parent-ds {
                    description "Enter the parent-ds context";

                    leaf grandmaster-identity {
                        type types-ptp:clock-identity-type;
                        description "The clock identity attribute of the grandmaster clock.";
                    }

                    leaf grandmaster-priority1 {
                        type uint8;
                        description "The priority1 attribute of the grandmaster clock.";
                    }

                    leaf grandmaster-priority2 {
                        type uint8;
                        description "The priority2 attribute of the grandmaster clock.";
                    }

                    leaf synchronization-uncertain {
                        type boolean;
                        description
                            "Indicates whether the master clock is reporting Sync Uncertain or not.

                             The value of this object corresponds to the parentDS.synchronizationUncertain
                             data set member defined in IEEE Std 1588-2019.";
                    }

                    container grandmaster-clock-quality {
                        description "Enter the grandmaster-clock-quality context";

                        leaf clock-class {
                            type uint8;
                            description
                                "The clock class denotes the traceability of the time
                                 or frequency distributed by the clock.";
                        }

                        leaf clock-accuracy {
                            type uint8;
                            description
                                "The clock accuracy indicates the expected accuracy
                                 of the clock.";
                        }

                        leaf offset-scaled-log-variance {
                            type uint16;
                            description
                                "The offset scaled log variance provides an estimate of
                                 the variations of the clock from a linear timescale
                                 when it is not synchronized to another clock
                                 using the protocol.";
                        }

                    } // container grandmaster-clock-quality

                    container parent-port-identity {
                        description "Enter the parent-port-identity context";

                        leaf clock-identity {
                            type types-ptp:clock-identity-type;
                            description "Identity of the clock.";
                        }

                        leaf port-number {
                            type uint16;
                            description "Port number.";
                        }

                    } // container parent-port-identity

                    container transport-address {
                        description "Enter the transport-address context";

                        leaf port-id {
                            type types-sros:port;
                            description
                                "The Ethernet port used to reach the parent clock, or the local GNSS port that
                                 the PTP clock is synchronizing from.";
                        }

                        leaf neighbor-mac-address {
                            type yang:mac-address;
                            description "The Ethernet MAC address of the parent clock.";
                        }

                        leaf local-clock-is-parent-clock {
                            type boolean;
                            description "Indicates local clock as parent clock.";
                        }

                        container peer {
                            description "Enter the peer context";

                            leaf router-name {
                                type types-sros:named-item-64-or-empty;
                                description "Administrative name of virtual router.";
                            }

                            leaf ip-address {
                                type types-sros:ip-address;
                                description "The IP address of the Parent Clock.";
                            }

                        } // container peer

                    } // container transport-address

                } // container parent-ds

                list statistics {
                    key "direction";
                    description "Enter the statistics list instance";

                    leaf direction {
                        type enumeration {
                            enum rx                             { value 1; }
                            enum tx                             { value 2; }
                        }
                        description
                            "Specifies the direction in which the packet
                             statistics are accumulated.";
                    }

                    leaf announce {
                        type yang:counter64;
                        description "The accumulated packet statistics for PTP announce messages.";
                    }

                    leaf sync {
                        type yang:counter64;
                        description "The accumulated packet statistics for PTP sync messages.";
                    }

                    leaf follow-up {
                        type yang:counter64;
                        description "The accumulated packet statistics for PTP follow up messages.";
                    }

                    leaf delay-request {
                        type yang:counter64;
                        description "The accumulated packet statistics for PTP delay request messages.";
                    }

                    leaf delay-response {
                        type yang:counter64;
                        description "The accumulated packet statistics for PTP delay response messages.";
                    }

                    leaf signalling {
                        type yang:counter64;
                        description "The accumulated packet statistics for PTP signalling messages.";
                    }

                    leaf other-message {
                        type yang:counter64;
                        description "The accumulated packet statistics for all other PTP messages.";
                    }

                    leaf event-timestamp-at-port {
                        type yang:counter64;
                        description
                            "The accumulated packet statistics for PTP event packets
                             where the timestamp point is at the physical layer.";
                    }

                    leaf event-timestamp-at-cpm {
                        type yang:counter64;
                        description
                            "The accumulated packet statistics for PTP event packets
                             where the timestamp point is at the operating system kernel.";
                    }

                    leaf peer-delay-request {
                        type yang:counter64;
                        description "The accumulated packet statistics for PTP Pdelay_Req messages.";
                    }

                    leaf peer-delay-response {
                        type yang:counter64;
                        description "The accumulated packet statistics for PTP Pdelay_Resp messages.";
                    }

                    leaf peer-delay-response-follow-up {
                        type yang:counter64;
                        description "The accumulated packet statistics for PTP Pdelay_Resp_Follow_Up messages.";
                    }

                    container discards {
                        description "Enter the discards context";

                        leaf bad-domain {
                            type yang:counter64;
                            description
                                "The accumulated packet statistics for PTP packets dropped because the PTP domain
                                 indicated in the packet does not match the configured PTP domain.";
                        }

                        leaf alternate-master {
                            type yang:counter64;
                            description
                                "The accumulated packet statistics for PTP packets dropped because the PTP header
                                 has the 'alternate master flag' set.";
                        }

                        leaf out-of-sequence {
                            type yang:counter64;
                            description
                                "The accumulated packet statistics for PTP packets dropped because the packets
                                 were received out of sequence.";
                        }

                        leaf other {
                            type yang:counter64;
                            description
                                "The accumulated packet statistics for PTP packets dropped and not counted
                                 in the other drop counters.";
                        }

                        leaf freerun {
                            status obsolete;
                            type yang:counter64;
                            description
                                "The accumulated packet statistics for PTP packets dropped because the central
                                 clock is running in freeerun.

                                 This object is obsolete as of Release 26.3.";
                        }

                        leaf id-in-path-trace-tlv {
                            type yang:counter64;
                            description
                                "The clockIdentiy for the local clock was found in a PATH_TRACE TLV in a received Announce message.
                                 This may indicate a network timing loop.";
                        }

                        leaf steps-removed-exceeded {
                            type yang:counter64;
                            description
                                "The number of times the local clock dropped a packet because the 'stepsRemoved' field in the
                                 ingress header exceeded the max steps removed configured.";
                        }

                        leaf peer-disabled {
                            type yang:counter64;
                            description
                                "The accumulated packet statistics for PTP packets dropped because the packets
                                 were received from a PTP peer that has been administratively disabled.";
                        }

                        leaf ptsf-unusable {
                            type yang:counter64;
                            description
                                "The accumulated packet statistics for PTP packets dropped because the packet
                                 timing signal from the neighboring clock is considered unusable.";
                        }

                    } // container discards

                    list announce-tlv {
                        key "tlv-type";
                        description "Enter the announce-tlv list instance";

                        leaf tlv-type {
                            type types-ptp:announce-packet-tlv-type;
                            description "Specifies the announce tlv type.";
                        }

                        leaf count {
                            type yang:counter64;
                            description "The count of the announce TLVs for the given tlv-type.";
                        }

                    } // list announce-tlv

                    list signalling-tlv {
                        key "tlv-type message-type";
                        description "Enter the signalling-tlv list instance";

                        leaf tlv-type {
                            type enumeration {
                                enum request                        { value 1; }
                                enum grant                          { value 2; }
                                enum reject                         { value 3; }
                                enum cancel                         { value 4; }
                                enum ack-cancel                     { value 5; }
                                enum other                          { value 6; }
                            }
                            description "Specifies the tlv type.";
                        }

                        leaf message-type {
                            type enumeration {
                                enum announce                       { value 1; }
                                enum sync                           { value 2; }
                                enum delay-response                 { value 3; }
                                enum other                          { value 4; }
                            }
                            description "Specifies the message type.";
                        }

                        leaf count {
                            type yang:counter64;
                            description "The count of the TLVs for the given tlv-type and message-type.";
                        }

                    } // list signalling-tlv

                    container unicast-message-rates {
                        description "Enter the unicast-message-rates context";

                        leaf announce {
                            type yang:counter64;
                            description "The rate of PTP announce packets transmitted or received by the local PTP clock.";
                        }

                        leaf sync {
                            type yang:counter64;
                            description "The rate of PTP sync packets transmitted or received by the local PTP clock.";
                        }

                        leaf follow-up {
                            type yang:counter64;
                            description "The rate of PTP follow up packets transmitted or received by the local PTP clock.";
                        }

                        leaf delay-request {
                            type yang:counter64;
                            description "The rate of PTP delay request packets transmitted or received by the local PTP clock.";
                        }

                        leaf delay-response {
                            type yang:counter64;
                            description "The rate of PTP delay response packets transmitted or received by the local PTP clock.";
                        }

                        leaf other {
                            type yang:counter64;
                            description
                                "The rate of PTP packets of all other types
                                 transmitted or received by the local PTP clock.";
                        }

                    } // container unicast-message-rates

                    container multicast-message-rates {
                        description "Enter the multicast-message-rates context";

                        leaf announce {
                            type yang:counter64;
                            description "The rate of PTP announce packets transmitted or received by the local PTP clock.";
                        }

                        leaf sync {
                            type yang:counter64;
                            description "The rate of PTP sync packets transmitted or received by the local PTP clock.";
                        }

                        leaf follow-up {
                            type yang:counter64;
                            description "The rate of PTP follow up packets transmitted or received by the local PTP clock.";
                        }

                        leaf delay-request {
                            type yang:counter64;
                            description "The rate of PTP delay request packets transmitted or received by the local PTP clock.";
                        }

                        leaf delay-response {
                            type yang:counter64;
                            description "The rate of PTP delay response packets transmitted or received by the local PTP clock.";
                        }

                        leaf other {
                            type yang:counter64;
                            description
                                "The rate of PTP packets of all other types
                                 transmitted or received by the local PTP clock.";
                        }

                        leaf peer-delay-request {
                            type yang:counter64;
                            description "The rate of PTP Pdelay_Req packets transmitted or received by the local PTP clock.";
                        }

                        leaf peer-delay-response {
                            type yang:counter64;
                            description "The rate of PTP Pdelay_Resp packets transmitted or received by the local PTP clock.";
                        }

                        leaf peer-delay-response-follow-up {
                            type yang:counter64;
                            description "The rate of PTP Pdelay_Resp_Follow_Up packets transmitted or received by the local PTP clock.";
                        }

                    } // container multicast-message-rates

                } // list statistics

                list port-ds {
                    key "port-number";
                    description "Enter the port-ds list instance";

                    leaf port-number {
                        type uint16;
                        description
                            "The PTP port number assigned by the local clock and
                             used when communicating with the remote clock.";
                    }

                    leaf port-state {
                        type enumeration {
                            enum not-applicable                 { value 0; }
                            enum initializing                   { value 1; }
                            enum faulty                         { value 2; }
                            enum disabled                       { value 3; }
                            enum listening                      { value 4; }
                            enum pre-master                     { value 5; }
                            enum master                         { value 6; }
                            enum passive                        { value 7; }
                            enum uncalibrated                   { value 8; }
                            enum slave                          { value 9; }
                        }
                        description "Operational state of the PTP port.";
                    }

                    leaf log-min-delay-req-interval {
                        type types-ptp:log-interval {
                            range "-6..0";
                        }
                        description
                            "The minimum permitted mean time interval between
                             successive delay req messages.";
                    }

                    leaf log-announce-interval {
                        type types-ptp:log-interval {
                            range "-3..4";
                        }
                        description
                            "The mean time interval between
                             successive announce messages.";
                    }

                    leaf announce-receipt-timeout {
                        type uint8;
                        description
                            "The number of announce intervals that have to pass
                             without receipt of an announce message before the
                             occurrence of the event ANNOUNCE_RECEIPT_TIMEOUT_
                             EXPIRES.";
                    }

                    leaf log-sync-interval {
                        type types-ptp:log-interval {
                            range "-6..0";
                        }
                        description
                            "The mean sync interval for multicast messages.
                             The rates for unicast transmissions are negotiated
                             separately on a per-port basis and are not constrained
                             by this attribute.";
                    }

                    container statistics {
                        description "Enter the statistics context";

                        leaf tx-messages {
                            type uint64;
                            units "packets per second";
                            description
                                "The current rate of PTP packets that the local PTP clock
                                 is transmitting on the Ethernet port.";
                        }

                        leaf rx-messages {
                            type uint64;
                            units "packets per second";
                            description
                                "The current rate of PTP packets received
                                 by the local PTP clock on the Ethernet port.";
                        }

                    } // container statistics

                } // list port-ds

                list router {
                    key "router-name";
                    description "Enter the router list instance";

                    leaf router-name {
                        type types-sros:named-item-64;
                        description "The administrative name of a virtual router.";
                    }

                    leaf oper-state {
                        type types-sros:oper-state;
                        description "The operational state of PTP on the virtual router instance.";
                    }

                    list peer {
                        key "ip-address";
                        description "Enter the peer list instance";

                        leaf ip-address {
                            type types-sros:ip-address;
                            description "The address of the PTP peer.";
                        }

                        leaf grandmaster-identity {
                            type types-ptp:clock-identity-type;
                            description "The clock identity attribute of the grandmaster clock.";
                        }

                        leaf grandmaster-priority1 {
                            type uint8;
                            description "The priority1 attribute of the grandmaster clock.";
                        }

                        leaf grandmaster-priority2 {
                            type uint8;
                            description "The priority2 attribute of the grandmaster clock.";
                        }

                        leaf best-master {
                            type boolean;
                            description "Indicates if this peer was selected by the BMCA to be the best master.";
                        }

                        leaf parent-clock {
                            type boolean;
                            description
                                "Indicates if this peer is the current parent clock of this PTP clock.
                                 May differ from best-master due to use of local GNSS as time source.";
                        }

                        leaf apts-asymmetry {
                            status obsolete;
                            type int64;
                            units "nanoseconds";
                            description
                                "Indicates the computed asymmetry between the local clock and the peer.

                                 This is updated while the local clock has GNSS lock and the local clock is
                                 exchanging PTP event messages with the peer.

                                 This leaf was obsoleted in Release 24.3 and was replaced by offset-from-local-clock";
                        }

                        leaf apts-asymmetry-last-update {
                            status obsolete;
                            type yang:date-and-time;
                            description
                                "The date and time the apts-asymmetry was last computed.

                                 This leaf was obsoleted in Release 24.3 and was replaced by offset-last-update";
                        }

                        leaf offset-from-local-clock {
                            status obsolete;
                            type int64;
                            units "nanoseconds";
                            description
                                "Indicates the time offset between the clock recovered from the peer and
                                 the local clock's time. This time offset may be caused by delay
                                 asymmetry in the path between the peer clock and the local clock.

                                 This leaf is obsolete as of Release 26.3 and replaced by offset-from-local-clock-ns";
                        }

                        leaf offset-from-local-clock-ns {
                            type int32;
                            units "nanoseconds";
                            description
                                "Indicates the time offset between the clock recovered from the peer and
                                 the local clock's time. This time offset may be caused by delay
                                 asymmetry in the path between the peer clock and the local clock.";
                        }

                        leaf offset-last-update {
                            type yang:date-and-time;
                            description "The date and time the offset-from-local-clock-ns was last computed.";
                        }

                        leaf backup-source {
                            type boolean;
                            description "When true indicates this peer is the backup when the clock is using GNSS.";
                        }

                        leaf alternate-profile {
                            type types-sros:named-item-64;
                            description "Name of the alternate-profile applied to this peer.";
                        }

                        leaf local-ptp-port {
                            type leafref {
                                path "../../../port-ds/port-number";
                            }
                            description
                                "The PTP port number assigned by the local clock
                                 and used when communicating with the remote clock.";
                        }

                        leaf remote-clock-identity {
                            type types-ptp:clock-identity-type;
                            description "The clock identity of the peer.";
                        }

                        leaf remote-port-number {
                            type uint16;
                            description
                                "The PTP port number used by the remote peer
                                 when communicating with the local clock.";
                        }

                        leaf steps-removed {
                            type uint16;
                            description
                                "The number of communication paths traversed
                                 between the local clock and the grandmaster clock.";
                        }

                        leaf tx-timestamp-point {
                            type types-ptp:timestamp-reference-point;
                            description
                                "The reference point used to generate the PTP timestamp
                                 for the last transmitted PTP event packet.";
                        }

                        leaf rx-timestamp-point {
                            type types-ptp:timestamp-reference-point;
                            description
                                "The reference point used to generate the PTP timestamp
                                 for the last received PTP event packet.";
                        }

                        leaf monitor-time-state {
                            type enumeration {
                                enum disabled                       { value 0; }
                                enum initial                        { value 1; }
                                enum acquiring                      { value 2; }
                                enum locked                         { value 3; }
                                enum holdover                       { value 4; }
                            }
                            description
                                "The state of the time recovery process on a port or peer
                                 where monitor-receiver has been enabled.";
                        }

                        leaf state-last-changed {
                            type yang:date-and-time;
                            description "Indicates the time when the time recovery process last changed state.";
                        }

                        leaf offset-from-master {
                            status obsolete;
                            type types-ptp:time-interval-type;
                            description
                                "The current value of the time difference between
                                 a master clock and a slave clock as computed by the slave.

                                 This leaf is obsolete as of Release 26.3 and replaced by offset-from-master-ns";
                        }

                        leaf offset-from-master-ns {
                            type int32;
                            units "nanoseconds";
                            description
                                "The current value of the time difference between
                                 a master clock and a slave clock as computed by the slave.";
                        }

                        leaf mean-path-delay {
                            status obsolete;
                            type types-ptp:time-interval-type;
                            description
                                "The current value of the mean propagation time between
                                 a master clock and a slave clock as computed by the slave.

                                 This leaf is obsolete as of Release 26.3 and replaced by mean-path-delay-ns";
                        }

                        leaf mean-path-delay-ns {
                            type int32;
                            units "nanoseconds";
                            description
                                "The current value of the mean propagation time between
                                 a master clock and a slave clock as computed by the slave.";
                        }

                        leaf last-calc-time {
                            type yang:date-and-time;
                            description
                                "The time when offset-from-master-ns and mean-path-delay-ns
                                 were last calculated.";
                        }

                        container grandmaster-clock-quality {
                            description "Enter the grandmaster-clock-quality context";

                            leaf clock-class {
                                type uint8;
                                description
                                    "The clock class denotes the traceability of the time
                                     or frequency distributed by the clock.";
                            }

                            leaf clock-accuracy {
                                type uint8;
                                description
                                    "The clock accuracy indicates the expected accuracy
                                     of the clock.";
                            }

                            leaf offset-scaled-log-variance {
                                type uint16;
                                description
                                    "The offset scaled log variance provides an estimate of
                                     the variations of the clock from a linear timescale
                                     when it is not synchronized to another clock
                                     using the protocol.";
                            }

                        } // container grandmaster-clock-quality

                        container last-tx-port {
                            description "Enter the last-tx-port context";

                            leaf port-id {
                                type types-sros:port;
                                description "The last port used to transmit PTP packets to the PTP peer.";
                            }

                            leaf encapsulation-type {
                                type types-port:network-interface-encap-type;
                                description "The encapsulation type for the last port used to transmit PTP packets to the PTP peer.";
                            }

                            leaf encapsulation-value {
                                type types-services:encap-value;
                                description "The encapsulation value for the last port used to transmit PTP packets to the PTP peer.";
                            }

                        } // container last-tx-port

                        container last-rx-port {
                            description "Enter the last-rx-port context";

                            leaf port-id {
                                type types-sros:port;
                                description "The last port used to receive PTP packets from the PTP peer.";
                            }

                            leaf encapsulation-type {
                                type types-port:network-interface-encap-type;
                                description "The encapsulation type for the last port used to receive PTP packets from the PTP peer.";
                            }

                            leaf encapsulation-value {
                                type types-services:encap-value;
                                description "The encapsulation value for the last port used to receive PTP packets from the PTP peer.";
                            }

                        } // container last-rx-port

                        container performance-monitoring {
                            description "Enter the performance-monitoring context";

                            list record {
                                key "index";
                                description "Enter the record list instance";

                                leaf index {
                                    type uint32 {
                                        range "0..98 | 501..516";
                                    }
                                    description
                                        "Index to specific record in the list. Values supported are:
                                         0 : current 15 minute interval,
                                         1..96 : completed 15 minute interval in last 24 hours,
                                         97 : current 24 hour interval,
                                         98 : previous 24 hour interval,
                                         501 : current 1 minute interval,
                                         502..516 : completed 1 minute interval in last 15 minutes";
                                }

                                leaf measurement-valid {
                                    type boolean;
                                    description
                                        "This flag indicates the data can be correctly interpreted. Validity is
                                         implementation specific and may be defined in a PTP Profile.
                                         For SROS, as long as the clock received packets and did computations
                                         during the period for the record, the measurement-valid flag shall
                                         be true.  If no packets were received, the measurement-valid
                                         flag shall be false.";
                                }

                                leaf period-complete {
                                    type boolean;
                                    description
                                        "This flag is set to true when the recording period closes and measurements
                                         were performed during the entire period (1 minute, 15 minute, or 24 hour).

                                         For example, if the PTP instance is disabled for 5 minutes of
                                         a 15 minute period, period-complete is false.

                                         The period-complete flag is not related to the
                                         validity of measurements that were performed.

                                         The period-complete flag applies to all parameters for a
                                         given measurement period.

                                         A recording period closes at the next boundary for the record type
                                         15 minute: 0, 15, 30, 45 minutes after the hour. UTC.
                                         24 hour: 00:00. UTC.
                                         1 minute: integral minute. UTC.";
                                }

                                leaf start-time {
                                    type yang:date-and-time;
                                    description "Time at which the recording started. UTC.";
                                }

                                leaf duration {
                                    type uint32;
                                    units "seconds";
                                    description "The amount of time, in seconds, for which the data for this record was collected";
                                }

                                leaf average-master-slave-delay {
                                    status obsolete;
                                    type types-ptp:time-interval-type;
                                    description
                                        "Average of the MasterSlaveDelay for this interval.

                                         This leaf is obsolete as of Release 26.3 and replaced by average-master-slave-delay-ns";
                                }

                                leaf minimum-master-slave-delay {
                                    status obsolete;
                                    type types-ptp:time-interval-type;
                                    description
                                        "Minimum of the MasterSlaveDelay for this interval.

                                         This leaf is obsolete as of Release 26.3 and replaced by minimum-master-slave-delay-ns";
                                }

                                leaf maximum-master-slave-delay {
                                    status obsolete;
                                    type types-ptp:time-interval-type;
                                    description
                                        "Maximum of the MasterSlaveDelay for this interval.

                                         This leaf is obsolete as of Release 26.3 and replaced by maximum-master-slave-delay-ns";
                                }

                                leaf stddev-master-slave-delay {
                                    status obsolete;
                                    type types-ptp:time-interval-type;
                                    description
                                        "Standard Deviation of the MasterSlaveDelay for this interval.

                                         This leaf is obsolete as of Release 26.3 and replaced by stddev-master-slave-delay-ns";
                                }

                                leaf average-slave-master-delay {
                                    status obsolete;
                                    type types-ptp:time-interval-type;
                                    description
                                        "Average of the Slave Master Delay for this interval.

                                         This leaf is obsolete as of Release 26.3 and replaced by average-slave-master-delay-ns";
                                }

                                leaf minimum-slave-master-delay {
                                    status obsolete;
                                    type types-ptp:time-interval-type;
                                    description
                                        "Minimum of the Slave Master Delay for this interval.

                                         This leaf is obsolete as of Release 26.3 and replaced by minimum-slave-master-delay-ns";
                                }

                                leaf maximum-slave-master-delay {
                                    status obsolete;
                                    type types-ptp:time-interval-type;
                                    description
                                        "Maximum of the Slave Master Delay for this interval.

                                         This leaf is obsolete as of Release 26.3 and replaced by maximum-slave-master-delay-ns";
                                }

                                leaf stddev-slave-master-delay {
                                    status obsolete;
                                    type types-ptp:time-interval-type;
                                    description
                                        "Standard Deviation of the Slave Master Delay for this interval.

                                         This leaf is obsolete as of Release 26.3 and replaced by stddev-slave-master-delay-ns";
                                }

                                leaf average-mean-path-delay {
                                    status obsolete;
                                    type types-ptp:time-interval-type;
                                    description
                                        "Average of the Mean Path Delay for this interval.

                                         This leaf is obsolete as of Release 26.3 and replaced by average-mean-path-delay-ns";
                                }

                                leaf minimum-mean-path-delay {
                                    status obsolete;
                                    type types-ptp:time-interval-type;
                                    description
                                        "Minimum of the Mean Path Delay for this interval.

                                         This leaf is obsolete as of Release 26.3 and replaced by minimum-mean-path-delay-ns";
                                }

                                leaf maximum-mean-path-delay {
                                    status obsolete;
                                    type types-ptp:time-interval-type;
                                    description
                                        "Maximum of the Mean Path Delay for this interval.

                                         This leaf is obsolete as of Release 26.3 and replaced by maximum-mean-path-delay-ns";
                                }

                                leaf stddev-mean-path-delay {
                                    status obsolete;
                                    type types-ptp:time-interval-type;
                                    description
                                        "Standard Deviation of the Mean Path Delay for this interval.

                                         This leaf is obsolete as of Release 26.3 and replaced by stddev-mean-path-delay-ns";
                                }

                                leaf average-offset-from-master {
                                    status obsolete;
                                    type types-ptp:time-interval-type;
                                    description
                                        "Average of the Offset From Master for this interval.

                                         This leaf is obsolete as of Release 26.3 and replaced by average-offset-from-master-ns";
                                }

                                leaf minimum-offset-from-master {
                                    status obsolete;
                                    type types-ptp:time-interval-type;
                                    description
                                        "Minimum of the Offset From Master for this interval.

                                         This leaf is obsolete as of Release 26.3 and replaced by minimum-offset-from-master-ns";
                                }

                                leaf maximum-offset-from-master {
                                    status obsolete;
                                    type types-ptp:time-interval-type;
                                    description
                                        "Maximum of the Offset From Master for this interval.

                                         This leaf is obsolete as of Release 26.3 and replaced by maximum-offset-from-master-ns";
                                }

                                leaf stddev-offset-from-master {
                                    status obsolete;
                                    type types-ptp:time-interval-type;
                                    description
                                        "Standard Deviation of the Offset From Master for this interval.

                                         This leaf is obsolete as of Release 26.3 and replaced by stddev-offset-from-master-ns";
                                }

                                leaf average-master-slave-delay-ns {
                                    type int32;
                                    units "nanoseconds";
                                    description "Average of the MasterSlaveDelay for this interval.";
                                }

                                leaf minimum-master-slave-delay-ns {
                                    type int32;
                                    units "nanoseconds";
                                    description "Minimum of the MasterSlaveDelay for this interval.";
                                }

                                leaf maximum-master-slave-delay-ns {
                                    type int32;
                                    units "nanoseconds";
                                    description "Maximum of the MasterSlaveDelay for this interval.";
                                }

                                leaf stddev-master-slave-delay-ns {
                                    type int32;
                                    units "nanoseconds";
                                    description "Standard Deviation of the MasterSlaveDelay for this interval.";
                                }

                                leaf average-slave-master-delay-ns {
                                    type int32;
                                    units "nanoseconds";
                                    description "Average of the Slave Master Delay for this interval.";
                                }

                                leaf minimum-slave-master-delay-ns {
                                    type int32;
                                    units "nanoseconds";
                                    description "Minimum of the Slave Master Delay for this interval.";
                                }

                                leaf maximum-slave-master-delay-ns {
                                    type int32;
                                    units "nanoseconds";
                                    description "Maximum of the Slave Master Delay for this interval.";
                                }

                                leaf stddev-slave-master-delay-ns {
                                    type int32;
                                    units "nanoseconds";
                                    description "Standard Deviation of the Slave Master Delay for this interval.";
                                }

                                leaf average-mean-path-delay-ns {
                                    type int32;
                                    units "nanoseconds";
                                    description "Average of the Mean Path Delay for this interval.";
                                }

                                leaf minimum-mean-path-delay-ns {
                                    type int32;
                                    units "nanoseconds";
                                    description "Minimum of the Mean Path Delay for this interval.";
                                }

                                leaf maximum-mean-path-delay-ns {
                                    type int32;
                                    units "nanoseconds";
                                    description "Maximum of the Mean Path Delay for this interval.";
                                }

                                leaf stddev-mean-path-delay-ns {
                                    type int32;
                                    units "nanoseconds";
                                    description "Standard Deviation of the Mean Path Delay for this interval.";
                                }

                                leaf average-offset-from-master-ns {
                                    type int32;
                                    units "nanoseconds";
                                    description "Average of the Offset From Master for this interval.";
                                }

                                leaf minimum-offset-from-master-ns {
                                    type int32;
                                    units "nanoseconds";
                                    description "Minimum of the Offset From Master for this interval.";
                                }

                                leaf maximum-offset-from-master-ns {
                                    type int32;
                                    units "nanoseconds";
                                    description "Maximum of the Offset From Master for this interval.";
                                }

                                leaf stddev-offset-from-master-ns {
                                    type int32;
                                    units "nanoseconds";
                                    description "Standard Deviation of the Offset From Master for this interval.";
                                }

                            } // list record

                        } // container performance-monitoring

                        list unicast-negotiation {
                            key "direction message-type";
                            description "Enter the unicast-negotiation list instance";

                            leaf direction {
                                type enumeration {
                                    enum rx                             { value 1; }
                                    enum tx                             { value 2; }
                                }
                                description
                                    "Specifies the direction in which the packet
                                     statistics are accumulated.";
                            }

                            leaf message-type {
                                type enumeration {
                                    enum announce                       { value 1; }
                                    enum sync                           { value 2; }
                                    enum delay-response                 { value 3; }
                                }
                                description "Specifies the message type.";
                            }

                            leaf state {
                                type enumeration {
                                    enum pending                        { value 1; }
                                    enum granted                        { value 2; }
                                    enum denied                         { value 3; }
                                    enum expired                        { value 4; }
                                    enum canceled                       { value 5; }
                                }
                                description "Indicates the state of the unicast transmission.";
                            }

                            leaf log-interval {
                                type types-ptp:log-interval;
                                description
                                    "The packet rate requested or granted for unicast
                                     transmission between the PTP peers.";
                            }

                            leaf duration {
                                type uint32;
                                units "seconds";
                                description
                                    "The duration, in seconds, requested or granted
                                     for unicast transmission between the PTP peers.";
                            }

                            leaf time-of-last-grant {
                                type yang:date-and-time;
                                description
                                    "The time when status last changed or the
                                     unicast session between the PTP clocks was renewed.";
                            }

                        } // list unicast-negotiation

                        list statistics {
                            key "direction";
                            description "Enter the statistics list instance";

                            leaf direction {
                                type enumeration {
                                    enum rx                             { value 1; }
                                    enum tx                             { value 2; }
                                }
                                description
                                    "Specifies the direction in which the packet
                                     statistics are accumulated.";
                            }

                            leaf announce {
                                type yang:counter64;
                                description "The accumulated packet statistics for PTP announce messages.";
                            }

                            leaf sync {
                                type yang:counter64;
                                description "The accumulated packet statistics for PTP sync messages.";
                            }

                            leaf follow-up {
                                type yang:counter64;
                                description "The accumulated packet statistics for PTP follow up messages.";
                            }

                            leaf delay-request {
                                type yang:counter64;
                                description "The accumulated packet statistics for PTP delay request messages.";
                            }

                            leaf delay-response {
                                type yang:counter64;
                                description "The accumulated packet statistics for PTP delay response messages.";
                            }

                            leaf signalling {
                                type yang:counter64;
                                description "The accumulated packet statistics for PTP signalling messages.";
                            }

                            leaf other-message {
                                type yang:counter64;
                                description "The accumulated packet statistics for all other PTP messages.";
                            }

                            leaf event-timestamp-at-port {
                                type yang:counter64;
                                description
                                    "The accumulated packet statistics for PTP event packets
                                     where the timestamp point is at the physical layer.";
                            }

                            leaf event-timestamp-at-cpm {
                                type yang:counter64;
                                description
                                    "The accumulated packet statistics for PTP event packets
                                     where the timestamp point is at the operating system kernel.";
                            }

                            container discards {
                                description "Enter the discards context";

                                leaf bad-domain {
                                    type yang:counter64;
                                    description
                                        "The accumulated packet statistics for PTP packets dropped because the PTP domain
                                         indicated in the packet does not match the configured PTP domain.";
                                }

                                leaf alternate-master {
                                    type yang:counter64;
                                    description
                                        "The accumulated packet statistics for PTP packets dropped because the PTP header
                                         has the 'alternate master flag' set.";
                                }

                                leaf out-of-sequence {
                                    type yang:counter64;
                                    description
                                        "The accumulated packet statistics for PTP packets dropped because the packets
                                         were received out of sequence.";
                                }

                                leaf other {
                                    type yang:counter64;
                                    description
                                        "The accumulated packet statistics for PTP packets dropped and not counted
                                         in the other drop counters.";
                                }

                                leaf freerun {
                                    status obsolete;
                                    type yang:counter64;
                                    description
                                        "The accumulated packet statistics for PTP packets dropped because the central
                                         clock is running in freeerun.

                                         This object is obsolete as of Release 26.3.";
                                }

                                leaf id-in-path-trace-tlv {
                                    type yang:counter64;
                                    description
                                        "The clockIdentiy for the local clock was found in a PATH_TRACE TLV in a received Announce message.
                                         This may indicate a network timing loop.";
                                }

                                leaf steps-removed-exceeded {
                                    type yang:counter64;
                                    description
                                        "The number of times the local clock dropped a packet because the 'stepsRemoved' field in the
                                         ingress header exceeded the max steps removed configured.";
                                }

                                leaf peer-disabled {
                                    type yang:counter64;
                                    description
                                        "The accumulated packet statistics for PTP packets dropped because the packets
                                         were received from a PTP peer that has been administratively disabled.";
                                }

                            } // container discards

                            list signalling-tlv {
                                key "tlv-type message-type";
                                description "Enter the signalling-tlv list instance";

                                leaf tlv-type {
                                    type enumeration {
                                        enum request                        { value 1; }
                                        enum grant                          { value 2; }
                                        enum reject                         { value 3; }
                                        enum cancel                         { value 4; }
                                        enum ack-cancel                     { value 5; }
                                        enum other                          { value 6; }
                                    }
                                    description "Specifies the tlv type.";
                                }

                                leaf message-type {
                                    type enumeration {
                                        enum announce                       { value 1; }
                                        enum sync                           { value 2; }
                                        enum delay-response                 { value 3; }
                                        enum other                          { value 4; }
                                    }
                                    description "Specifies the message type.";
                                }

                                leaf count {
                                    type yang:counter64;
                                    description "The count of the TLVs for the given tlv-type and message-type.";
                                }

                            } // list signalling-tlv

                        } // list statistics

                    } // list peer

                } // list router

                list port {
                    key "port-id";
                    description "Enter the port list instance";

                    leaf port-id {
                        type types-sros:port;
                        description "The ethernet PTP port.";
                    }

                    leaf local-mac-address {
                        type yang:mac-address;
                        description
                            "The MAC address of the physical port
                             associated with the PTP port.";
                    }

                    leaf local-ptp-port {
                        type leafref {
                            path "../../port-ds/port-number";
                        }
                        description
                            "The PTP port number assigned by the local clock
                             and used when communicating directly over the Ethernet physical port.";
                    }

                    leaf oper-state {
                        type types-sros:oper-state;
                        description "The operational state of PTP on the Ethernet port.";
                    }

                    leaf timestamp-point {
                        type types-ptp:timestamp-reference-point;
                        description
                            "The reference point used to generate PTP timestamps
                             for transmitted and received PTP event packets on the port.";
                    }

                    leaf neighbor-count {
                        type uint16;
                        description
                            "The numbers of neighboring PTP clocks visible
                             to the local clock on the Ethernet port.";
                    }

                    leaf mean-link-delay-ns {
                        type int32;
                        units "nanoseconds";
                        description
                            "The estimated one-way propagation delay on the PTP link, computed using the
                             peer-to-peer delay mechanism.

                             It represents the 'instantaneous' value of the calculated mean link
                             delay, using timestamp information from the most recent exchange of
                             Pdelay_Req, Pdelay_Resp, and possibly Pdelay_Resp_Follow_Up messages.

                             There is no filtering applied to the received messages, and there is
                             no averaging of this calculation over multiple exchanges of peer delay
                             messages.

                             The active CPM calculates the mean link delay each time it exchanges
                             Pdelay_Req, Pdelay_Resp, and possibly Pdelay_Resp_Follow_Up messages
                             over the link.  The standby CPM does not calculate the mean link
                             delay, returning a value of 0 for mean-link-delay-ns.

                             The time that this mean link delay was last calculated is provided in
                             mean-link-delay-last-calc-time.

                             This corresponds to the 'portDS.meanLinkDelay' data set member
                             defined in IEEE Std 1588-2019.";
                    }

                    leaf mean-link-delay-last-calc-time {
                        type yang:date-and-time;
                        description "The date and time the mean-link-delay-ns was last computed.";
                    }

                    list neighbor {
                        key "mac-address";
                        description "Enter the neighbor list instance";

                        leaf mac-address {
                            type yang:mac-address;
                            description "Mac address of the neighboring PTP clock.";
                        }

                        leaf best-master {
                            type boolean;
                            description "Indicates if this neighbor was selected by the BMCA to be the best master.";
                        }

                        leaf parent-clock {
                            type boolean;
                            description
                                "Indicates if this neighbor is the current parent clock of this PTP clock.
                                 May differ from best-master due to use of local GNSS as time source.";
                        }

                        leaf apts-asymmetry {
                            status obsolete;
                            type int32;
                            units "nanoseconds";
                            description
                                "Indicates the computed asymmetry between the local clock and the neighbor.

                                 This is updated while the local clock has GNSS lock and the local clock is
                                 exchanging PTP event messages with the neighbor.

                                 This leaf was obsoleted in Release 24.3 and was replaced by offset-from-local-clock";
                        }

                        leaf apts-asymmetry-last-update {
                            status obsolete;
                            type yang:date-and-time;
                            description
                                "The date and time the apts-asymmetry was last computed.

                                 This leaf was obsoleted in Release 24.3 and was replaced by offset-last-update";
                        }

                        leaf offset-from-local-clock {
                            status obsolete;
                            type int64;
                            units "nanoseconds";
                            description
                                "Indicates the time offset between the clock recovered from the neighboring
                                 clock and the local clock's time. This time offset may be caused by delay
                                 asymmetry in the path between the neighboring clock and the local clock.

                                 This leaf is obsolete as of Release 26.3 and replaced by offset-from-local-clock-ns";
                        }

                        leaf offset-from-local-clock-ns {
                            type int32;
                            units "nanoseconds";
                            description
                                "Indicates the time offset between the clock recovered from the neighboring
                                 clock and the local clock's time. This time offset may be caused by delay
                                 asymmetry in the path between the neighboring clock and the local clock.";
                        }

                        leaf offset-last-update {
                            type yang:date-and-time;
                            description "The date and time the offset-from-local-clock-ns was last computed.";
                        }

                        leaf backup-source {
                            type boolean;
                            description "When true indicates this port is the backup when the clock is using GNSS.";
                        }

                        leaf clock-identity {
                            type types-ptp:clock-identity-type;
                            description "The clock identity of the neighboring PTP clock.";
                        }

                        leaf port-number {
                            type uint16;
                            description
                                "The PTP port number of the PTP port on the neighbor clock
                                 that is connected to the local clock on this Ethernet port.";
                        }

                        leaf rx-message-rate {
                            type uint16;
                            description
                                "The current rate of PTP packets received by the local clock
                                 from the neighboring PTP clock.";
                        }

                        leaf ptsf-unusable {
                            type boolean;
                            description
                                "Indicates whether or not the neighboring PTP clock
                                 has Packet Timing Signal Fail (PTSF) unusable set.";
                        }

                        leaf monitor-time-state {
                            type enumeration {
                                enum disabled                       { value 0; }
                                enum initial                        { value 1; }
                                enum acquiring                      { value 2; }
                                enum locked                         { value 3; }
                                enum holdover                       { value 4; }
                            }
                            description
                                "The state of the time recovery process on a port or peer
                                 where monitor-receiver has been enabled.";
                        }

                        leaf state-last-changed {
                            type yang:date-and-time;
                            description "Indicates the time when the time recovery process last changed state.";
                        }

                        leaf offset-from-master {
                            status obsolete;
                            type types-ptp:time-interval-type;
                            description
                                "The current value of the time difference between
                                 a master clock and a slave clock as computed by the slave.

                                 This leaf is obsolete as of Release 26.3 and replaced by offset-from-master-ns";
                        }

                        leaf offset-from-master-ns {
                            type int32;
                            units "nanoseconds";
                            description
                                "The current value of the time difference between
                                 a master clock and a slave clock as computed by the slave.";
                        }

                        leaf mean-path-delay {
                            status obsolete;
                            type types-ptp:time-interval-type;
                            description
                                "The current value of the mean propagation time between
                                 a master clock and a slave clock as computed by the slave.

                                 This leaf is obsolete as of Release 26.3 and replaced by mean-path-delay-ns";
                        }

                        leaf mean-path-delay-ns {
                            type int32;
                            units "nanoseconds";
                            description
                                "The current value of the mean propagation time between
                                 a master clock and a slave clock as computed by the slave.";
                        }

                        leaf last-calc-time {
                            type yang:date-and-time;
                            description
                                "The time when offset-from-master-ns and mean-path-delay-ns
                                 were last calculated.";
                        }


                        container performance-monitoring {
                            description "Enter the performance-monitoring context";

                            list record {
                                key "index";
                                description "Enter the record list instance";

                                leaf index {
                                    type uint32 {
                                        range "0..98 | 501..516";
                                    }
                                    description
                                        "Index to specific record in the list. Values supported are:
                                         0 : current 15 minute interval,
                                         1..96 : completed 15 minute interval in last 24 hours,
                                         97 : current 24 hour interval,
                                         98 : previous 24 hour interval,
                                         501 : current 1 minute interval,
                                         502..516 : completed 1 minute interval in last 15 minutes";
                                }

                                leaf measurement-valid {
                                    type boolean;
                                    description
                                        "This flag indicates the data can be correctly interpreted. Validity is
                                         implementation specific and may be defined in a PTP Profile.
                                         For SROS, as long as the clock received packets and did computations
                                         during the period for the record, the measurement-valid flag shall
                                         be true.  If no packets were received, the measurement-valid
                                         flag shall be false.";
                                }

                                leaf period-complete {
                                    type boolean;
                                    description
                                        "This flag is set to true when the recording period closes and measurements
                                         were performed during the entire period (1 minute, 15 minute, or 24 hour).

                                         For example, if the PTP instance is disabled for 5 minutes of
                                         a 15 minute period, period-complete is false.

                                         The period-complete flag is not related to the
                                         validity of measurements that were performed.

                                         The period-complete flag applies to all parameters for a
                                         given measurement period.

                                         A recording period closes at the next boundary for the record type
                                         15 minute: 0, 15, 30, 45 minutes after the hour. UTC.
                                         24 hour: 00:00. UTC.
                                         1 minute: integral minute. UTC.";
                                }

                                leaf start-time {
                                    type yang:date-and-time;
                                    description "Time at which the recording started. UTC.";
                                }

                                leaf duration {
                                    type uint32;
                                    units "seconds";
                                    description "The amount of time, in seconds, for which the data for this record was collected";
                                }

                                leaf average-master-slave-delay {
                                    status obsolete;
                                    type types-ptp:time-interval-type;
                                    description
                                        "Average of the MasterSlaveDelay for this interval.

                                         This leaf is obsolete as of Release 26.3 and replaced by average-master-slave-delay-ns";
                                }

                                leaf minimum-master-slave-delay {
                                    status obsolete;
                                    type types-ptp:time-interval-type;
                                    description
                                        "Minimum of the MasterSlaveDelay for this interval.

                                         This leaf is obsolete as of Release 26.3 and replaced by minimum-master-slave-delay-ns";
                                }

                                leaf maximum-master-slave-delay {
                                    status obsolete;
                                    type types-ptp:time-interval-type;
                                    description
                                        "Maximum of the MasterSlaveDelay for this interval.

                                         This leaf is obsolete as of Release 26.3 and replaced by maximum-master-slave-delay-ns";
                                }

                                leaf stddev-master-slave-delay {
                                    status obsolete;
                                    type types-ptp:time-interval-type;
                                    description
                                        "Standard Deviation of the MasterSlaveDelay for this interval.

                                         This leaf is obsolete as of Release 26.3 and replaced by stddev-master-slave-delay-ns";
                                }

                                leaf average-slave-master-delay {
                                    status obsolete;
                                    type types-ptp:time-interval-type;
                                    description
                                        "Average of the Slave Master Delay for this interval.

                                         This leaf is obsolete as of Release 26.3 and replaced by average-slave-master-delay-ns";
                                }

                                leaf minimum-slave-master-delay {
                                    status obsolete;
                                    type types-ptp:time-interval-type;
                                    description
                                        "Minimum of the Slave Master Delay for this interval.

                                         This leaf is obsolete as of Release 26.3 and replaced by minimum-slave-master-delay-ns";
                                }

                                leaf maximum-slave-master-delay {
                                    status obsolete;
                                    type types-ptp:time-interval-type;
                                    description
                                        "Maximum of the Slave Master Delay for this interval.

                                         This leaf is obsolete as of Release 26.3 and replaced by maximum-slave-master-delay-ns";
                                }

                                leaf stddev-slave-master-delay {
                                    status obsolete;
                                    type types-ptp:time-interval-type;
                                    description
                                        "Standard Deviation of the Slave Master Delay for this interval.

                                         This leaf is obsolete as of Release 26.3 and replaced by stddev-slave-master-delay-ns";
                                }

                                leaf average-mean-path-delay {
                                    status obsolete;
                                    type types-ptp:time-interval-type;
                                    description
                                        "Average of the Mean Path Delay for this interval.

                                         This leaf is obsolete as of Release 26.3 and replaced by average-mean-path-delay-ns";
                                }

                                leaf minimum-mean-path-delay {
                                    status obsolete;
                                    type types-ptp:time-interval-type;
                                    description
                                        "Minimum of the Mean Path Delay for this interval.

                                         This leaf is obsolete as of Release 26.3 and replaced by minimum-mean-path-delay-ns";
                                }

                                leaf maximum-mean-path-delay {
                                    status obsolete;
                                    type types-ptp:time-interval-type;
                                    description
                                        "Maximum of the Mean Path Delay for this interval.

                                         This leaf is obsolete as of Release 26.3 and replaced by maximum-mean-path-delay-ns";
                                }

                                leaf stddev-mean-path-delay {
                                    status obsolete;
                                    type types-ptp:time-interval-type;
                                    description
                                        "Standard Deviation of the Mean Path Delay for this interval.

                                         This leaf is obsolete as of Release 26.3 and replaced by stddev-mean-path-delay-ns";
                                }

                                leaf average-offset-from-master {
                                    status obsolete;
                                    type types-ptp:time-interval-type;
                                    description
                                        "Average of the Offset From Master for this interval.

                                         This leaf is obsolete as of Release 26.3 and replaced by average-offset-from-master-ns";
                                }

                                leaf minimum-offset-from-master {
                                    status obsolete;
                                    type types-ptp:time-interval-type;
                                    description
                                        "Minimum of the Offset From Master for this interval.

                                         This leaf is obsolete as of Release 26.3 and replaced by minimum-offset-from-master-ns";
                                }

                                leaf maximum-offset-from-master {
                                    status obsolete;
                                    type types-ptp:time-interval-type;
                                    description
                                        "Maximum of the Offset From Master for this interval.

                                         This leaf is obsolete as of Release 26.3 and replaced by maximum-offset-from-master-ns";
                                }

                                leaf stddev-offset-from-master {
                                    status obsolete;
                                    type types-ptp:time-interval-type;
                                    description
                                        "Standard Deviation of the Offset From Master for this interval.

                                         This leaf is obsolete as of Release 26.3 and replaced by stddev-offset-from-master-ns";
                                }

                                leaf average-master-slave-delay-ns {
                                    type int32;
                                    units "nanoseconds";
                                    description "Average of the MasterSlaveDelay for this interval.";
                                }

                                leaf minimum-master-slave-delay-ns {
                                    type int32;
                                    units "nanoseconds";
                                    description "Minimum of the MasterSlaveDelay for this interval.";
                                }

                                leaf maximum-master-slave-delay-ns {
                                    type int32;
                                    units "nanoseconds";
                                    description "Maximum of the MasterSlaveDelay for this interval.";
                                }

                                leaf stddev-master-slave-delay-ns {
                                    type int32;
                                    units "nanoseconds";
                                    description "Standard Deviation of the MasterSlaveDelay for this interval.";
                                }

                                leaf average-slave-master-delay-ns {
                                    type int32;
                                    units "nanoseconds";
                                    description "Average of the Slave Master Delay for this interval.";
                                }

                                leaf minimum-slave-master-delay-ns {
                                    type int32;
                                    units "nanoseconds";
                                    description "Minimum of the Slave Master Delay for this interval.";
                                }

                                leaf maximum-slave-master-delay-ns {
                                    type int32;
                                    units "nanoseconds";
                                    description "Maximum of the Slave Master Delay for this interval.";
                                }

                                leaf stddev-slave-master-delay-ns {
                                    type int32;
                                    units "nanoseconds";
                                    description "Standard Deviation of the Slave Master Delay for this interval.";
                                }

                                leaf average-mean-path-delay-ns {
                                    type int32;
                                    units "nanoseconds";
                                    description "Average of the Mean Path Delay for this interval.";
                                }

                                leaf minimum-mean-path-delay-ns {
                                    type int32;
                                    units "nanoseconds";
                                    description "Minimum of the Mean Path Delay for this interval.";
                                }

                                leaf maximum-mean-path-delay-ns {
                                    type int32;
                                    units "nanoseconds";
                                    description "Maximum of the Mean Path Delay for this interval.";
                                }

                                leaf stddev-mean-path-delay-ns {
                                    type int32;
                                    units "nanoseconds";
                                    description "Standard Deviation of the Mean Path Delay for this interval.";
                                }

                                leaf average-offset-from-master-ns {
                                    type int32;
                                    units "nanoseconds";
                                    description "Average of the Offset From Master for this interval.";
                                }

                                leaf minimum-offset-from-master-ns {
                                    type int32;
                                    units "nanoseconds";
                                    description "Minimum of the Offset From Master for this interval.";
                                }

                                leaf maximum-offset-from-master-ns {
                                    type int32;
                                    units "nanoseconds";
                                    description "Maximum of the Offset From Master for this interval.";
                                }

                                leaf stddev-offset-from-master-ns {
                                    type int32;
                                    units "nanoseconds";
                                    description "Standard Deviation of the Offset From Master for this interval.";
                                }

                            } // list record

                        } // container performance-monitoring

                    } // list neighbor

                    list statistics {
                        key "direction";
                        description "Enter the statistics list instance";

                        leaf direction {
                            type enumeration {
                                enum rx                             { value 1; }
                                enum tx                             { value 2; }
                            }
                            description
                                "Specifies the direction in which the packet
                                 statistics are accumulated.";
                        }

                        leaf announce {
                            type yang:counter64;
                            description "The accumulated packet statistics for PTP announce messages.";
                        }

                        leaf sync {
                            type yang:counter64;
                            description "The accumulated packet statistics for PTP sync messages.";
                        }

                        leaf follow-up {
                            type yang:counter64;
                            description "The accumulated packet statistics for PTP follow up messages.";
                        }

                        leaf delay-request {
                            type yang:counter64;
                            description "The accumulated packet statistics for PTP delay request messages.";
                        }

                        leaf delay-response {
                            type yang:counter64;
                            description "The accumulated packet statistics for PTP delay response messages.";
                        }

                        leaf signalling {
                            type yang:counter64;
                            description "The accumulated packet statistics for PTP signalling messages.";
                        }

                        leaf other-message {
                            type yang:counter64;
                            description "The accumulated packet statistics for all other PTP messages.";
                        }

                        leaf event-timestamp-at-port {
                            type yang:counter64;
                            description
                                "The accumulated packet statistics for PTP event packets
                                 where the timestamp point is at the physical layer.";
                        }

                        leaf event-timestamp-at-cpm {
                            type yang:counter64;
                            description
                                "The accumulated packet statistics for PTP event packets
                                 where the timestamp point is at the operating system kernel.";
                        }

                        leaf peer-delay-request {
                            type yang:counter64;
                            description "The accumulated packet statistics for PTP Pdelay_Req messages.";
                        }

                        leaf peer-delay-response {
                            type yang:counter64;
                            description "The accumulated packet statistics for PTP Pdelay_Resp messages.";
                        }

                        leaf peer-delay-response-follow-up {
                            type yang:counter64;
                            description "The accumulated packet statistics for PTP Pdelay_Resp_Follow_Up messages.";
                        }

                        list announce-tlv {
                            key "tlv-type";
                            description "Enter the announce-tlv list instance";

                            leaf tlv-type {
                                type types-ptp:announce-packet-tlv-type;
                                description "Specifies the announce tlv type.";
                            }

                            leaf count {
                                type yang:counter64;
                                description "The count of the announce TLVs for the given tlv-type.";
                            }

                        } // list announce-tlv

                        container discards {
                            description "Enter the discards context";

                            leaf bad-domain {
                                type yang:counter64;
                                description
                                    "The accumulated packet statistics for PTP packets dropped because the PTP domain
                                     indicated in the packet does not match the configured PTP domain.";
                            }

                            leaf alternate-master {
                                type yang:counter64;
                                description
                                    "The accumulated packet statistics for PTP packets dropped because the PTP header
                                     has the 'alternate master flag' set.";
                            }

                            leaf out-of-sequence {
                                type yang:counter64;
                                description
                                    "The accumulated packet statistics for PTP packets dropped because the packets
                                     were received out of sequence.";
                            }

                            leaf other {
                                type yang:counter64;
                                description
                                    "The accumulated packet statistics for PTP packets dropped and not counted
                                     in the other drop counters.";
                            }

                            leaf freerun {
                                status obsolete;
                                type yang:counter64;
                                description
                                    "The accumulated packet statistics for PTP packets dropped because the central
                                     clock is running in freeerun.

                                     This object is obsolete as of Release 26.3.";
                            }

                            leaf id-in-path-trace-tlv {
                                type yang:counter64;
                                description
                                    "The clockIdentiy for the local clock was found in a PATH_TRACE TLV in a received Announce message.
                                     This may indicate a network timing loop.";
                            }

                            leaf steps-removed-exceeded {
                                type yang:counter64;
                                description
                                    "The number of times the local clock dropped a packet because the 'stepsRemoved' field in the
                                     ingress header exceeded the max steps removed configured.";
                            }

                            leaf ptsf-unusable {
                                type yang:counter64;
                                description
                                    "The accumulated packet statistics for PTP packets dropped because the packet
                                     timing signal from the neighboring clock is considered unusable.";
                            }

                        } // container discards

                    } // list statistics

                } // list port

                container events {
                    description "Enter the events context";

                    leaf sync-packet-loss {
                        type yang:counter32;
                        description
                            "The number of times that the clock recovery process
                             detected packet loss in the sync packet flow from the best master clock.";
                    }

                    leaf sync-excessive-packet-loss-freq {
                        type yang:counter32;
                        description
                            "The number of times that the clock recovery process
                             detected a large amount of packet loss in the sync
                             flow from the remote master clock.";
                    }

                    leaf sync-excessive-phase-shift-freq {
                        type yang:counter32;
                        description
                            "The number of times that the clock recovery process
                             detected a large change in the amount of time taken
                             for sync packets to be sent from the best master clock.";
                    }

                    leaf sync-too-much-packet-delay-variation-freq {
                        type yang:counter32;
                        description
                            "The number of times that the clock recovery process
                             has determined that a sample of sync packets from the best master clock
                             had too much packet delay variation to be useful in recovering the clock
                             from the best master.";
                    }

                    leaf sync-excessive-freq-adjustment {
                        type yang:counter32;
                        description
                            "The number of times that the clock recovery process has
                             determined that a sample of sync packets from the best master clock
                             resulted in an unexpected, excessive frequency adjustment.
                             On detection, the algorithm is reset.";
                    }

                    leaf delay-packet-loss {
                        type yang:counter32;
                        description
                            "The number of times that the clock recovery process
                             detected packet loss in the delay request/response packet flow";
                    }

                    leaf delay-excessive-packet-loss-freq {
                        type yang:counter32;
                        description
                            "The number of times that the clock recovery process
                             detected a large amount of packet loss in the delay
                             request/response flow from the remote master clock.";
                    }

                    leaf delay-excessive-phase-shift-freq {
                        type yang:counter32;
                        description
                            "The number of times that the clock recovery process
                             detected a large change in the amount of time taken
                             for delay request packets to be sent to the best
                             master clock.";
                    }

                    leaf delay-too-much-packet-delay-variation-freq {
                        type yang:counter32;
                        description
                            "The number of times that the clock recovery process
                             has determined that a sample of delay request packets
                             to the best master clock had too much packet delay variation
                             to be useful in recovering the clock from the best master.";
                    }

                    leaf sync-too-much-packet-delay-variation-time {
                        type yang:counter32;
                        description
                            "The number of times that the time recovery process
                             has determined that a sample of delay request packets
                             to the best master clock had too much packet delay variation
                             to be useful in recovering the time from the best master.";
                    }

                    leaf delay-too-much-packet-delay-variation-time {
                        type yang:counter32;
                        description
                            "The number of times that the time recovery process
                             has determined that a sample of sync packets from the best master clock
                             had too much packet delay variation to be useful in recovering the time
                             from the best master.";
                    }

                    leaf delay-excessive-freq-adjustment {
                        type yang:counter32;
                        description
                            "The number of times that the clock recovery process
                             has determined that a sample of delay request packets
                             to the best master clock had computed an unexpected,
                             excessive frequency adjustment.
                             On detection, the algorithm is reset.";
                    }

                } // container events

                container performance-monitoring {
                    description "Enter the performance-monitoring context";

                    list record {
                        key "index";
                        description "Enter the record list instance";

                        leaf index {
                            type uint32 {
                                range "0..98 | 501..516";
                            }
                            description
                                "Index to specific record in the list. Values supported are:
                                 0 : current 15 minute interval,
                                 1..96 : completed 15 minute interval in last 24 hours,
                                 97 : current 24 hour interval,
                                 98 : previous 24 hour interval,
                                 501 : current 1 minute interval,
                                 502..516 : completed 1 minute interval in last 15 minutes";
                        }

                        leaf measurement-valid {
                            type boolean;
                            description
                                "This flag indicates the data can be correctly interpreted. Validity is
                                 implementation specific and may be defined in a PTP Profile.
                                 For SROS, as long as the clock received packets and did computations
                                 during the period for the record, the measurement-valid flag shall
                                 be true.  If no packets were received, the measurement-valid
                                 flag shall be false.";
                        }

                        leaf period-complete {
                            type boolean;
                            description
                                "This flag is set to true when the recording period closes and measurements
                                 were performed during the entire period (1 minute, 15 minute, or 24 hour).

                                 For example, if the PTP instance is disabled for 5 minutes of
                                 a 15 minute period, period-complete is false.

                                 The period-complete flag is not related to the
                                 validity of measurements that were performed.

                                 The period-complete flag applies to all parameters for a
                                 given measurement period.

                                 A recording period closes at the next boundary for the record type
                                 15 minute: 0, 15, 30, 45 minutes after the hour. UTC.
                                 24 hour: 00:00. UTC.
                                 1 minute: integral minute. UTC.";
                        }

                        leaf start-time {
                            type yang:date-and-time;
                            description "Time at which the recording started. UTC.";
                        }

                        leaf duration {
                            type uint32;
                            units "seconds";
                            description "The amount of time, in seconds, for which the data for this record was collected";
                        }

                        leaf average-master-slave-delay {
                            status obsolete;
                            type types-ptp:time-interval-type;
                            description
                                "Average of the MasterSlaveDelay for this interval.

                                 This leaf is obsolete as of Release 26.3 and replaced by average-master-slave-delay-ns";
                        }

                        leaf minimum-master-slave-delay {
                            status obsolete;
                            type types-ptp:time-interval-type;
                            description
                                "Minimum of the MasterSlaveDelay for this interval.

                                 This leaf is obsolete as of Release 26.3 and replaced by minimum-master-slave-delay-ns";
                        }

                        leaf maximum-master-slave-delay {
                            status obsolete;
                            type types-ptp:time-interval-type;
                            description
                                "Maximum of the MasterSlaveDelay for this interval.

                                 This leaf is obsolete as of Release 26.3 and replaced by maximum-master-slave-delay-ns";
                        }

                        leaf stddev-master-slave-delay {
                            status obsolete;
                            type types-ptp:time-interval-type;
                            description
                                "Standard Deviation of the MasterSlaveDelay for this interval.

                                 This leaf is obsolete as of Release 26.3 and replaced by stddev-master-slave-delay-ns";
                        }

                        leaf average-slave-master-delay {
                            status obsolete;
                            type types-ptp:time-interval-type;
                            description
                                "Average of the Slave Master Delay for this interval.

                                 This leaf is obsolete as of Release 26.3 and replaced by average-slave-master-delay-ns";
                        }

                        leaf minimum-slave-master-delay {
                            status obsolete;
                            type types-ptp:time-interval-type;
                            description
                                "Minimum of the Slave Master Delay for this interval.

                                 This leaf is obsolete as of Release 26.3 and replaced by minimum-slave-master-delay-ns";
                        }

                        leaf maximum-slave-master-delay {
                            status obsolete;
                            type types-ptp:time-interval-type;
                            description
                                "Maximum of the Slave Master Delay for this interval.

                                 This leaf is obsolete as of Release 26.3 and replaced by maximum-slave-master-delay-ns";
                        }

                        leaf stddev-slave-master-delay {
                            status obsolete;
                            type types-ptp:time-interval-type;
                            description
                                "Standard Deviation of the Slave Master Delay for this interval.

                                 This leaf is obsolete as of Release 26.3 and replaced by stddev-slave-master-delay-ns";
                        }

                        leaf average-mean-path-delay {
                            status obsolete;
                            type types-ptp:time-interval-type;
                            description
                                "Average of the Mean Path Delay for this interval.

                                 This leaf is obsolete as of Release 26.3 and replaced by average-mean-path-delay-ns";
                        }

                        leaf minimum-mean-path-delay {
                            status obsolete;
                            type types-ptp:time-interval-type;
                            description
                                "Minimum of the Mean Path Delay for this interval.

                                 This leaf is obsolete as of Release 26.3 and replaced by minimum-mean-path-delay-ns";
                        }

                        leaf maximum-mean-path-delay {
                            status obsolete;
                            type types-ptp:time-interval-type;
                            description
                                "Maximum of the Mean Path Delay for this interval.

                                 This leaf is obsolete as of Release 26.3 and replaced by maximum-mean-path-delay-ns";
                        }

                        leaf stddev-mean-path-delay {
                            status obsolete;
                            type types-ptp:time-interval-type;
                            description
                                "Standard Deviation of the Mean Path Delay for this interval.

                                 This leaf is obsolete as of Release 26.3 and replaced by stddev-mean-path-delay-ns";
                        }

                        leaf average-offset-from-master {
                            status obsolete;
                            type types-ptp:time-interval-type;
                            description
                                "Average of the Offset From Master for this interval.

                                 This leaf is obsolete as of Release 26.3 and replaced by average-offset-from-master-ns";
                        }

                        leaf minimum-offset-from-master {
                            status obsolete;
                            type types-ptp:time-interval-type;
                            description
                                "Minimum of the Offset From Master for this interval.

                                 This leaf is obsolete as of Release 26.3 and replaced by minimum-offset-from-master-ns";
                        }

                        leaf maximum-offset-from-master {
                            status obsolete;
                            type types-ptp:time-interval-type;
                            description
                                "Maximum of the Offset From Master for this interval.

                                 This leaf is obsolete as of Release 26.3 and replaced by maximum-offset-from-master-ns";
                        }

                        leaf stddev-offset-from-master {
                            status obsolete;
                            type types-ptp:time-interval-type;
                            description
                                "Standard Deviation of the Offset From Master for this interval.

                                 This leaf is obsolete as of Release 26.3 and replaced by stddev-offset-from-master-ns";
                        }

                        leaf average-master-slave-delay-ns {
                            type int32;
                            units "nanoseconds";
                            description "Average of the MasterSlaveDelay for this interval.";
                        }

                        leaf minimum-master-slave-delay-ns {
                            type int32;
                            units "nanoseconds";
                            description "Minimum of the MasterSlaveDelay for this interval.";
                        }

                        leaf maximum-master-slave-delay-ns {
                            type int32;
                            units "nanoseconds";
                            description "Maximum of the MasterSlaveDelay for this interval.";
                        }

                        leaf stddev-master-slave-delay-ns {
                            type int32;
                            units "nanoseconds";
                            description "Standard Deviation of the MasterSlaveDelay for this interval.";
                        }

                        leaf average-slave-master-delay-ns {
                            type int32;
                            units "nanoseconds";
                            description "Average of the Slave Master Delay for this interval.";
                        }

                        leaf minimum-slave-master-delay-ns {
                            type int32;
                            units "nanoseconds";
                            description "Minimum of the Slave Master Delay for this interval.";
                        }

                        leaf maximum-slave-master-delay-ns {
                            type int32;
                            units "nanoseconds";
                            description "Maximum of the Slave Master Delay for this interval.";
                        }

                        leaf stddev-slave-master-delay-ns {
                            type int32;
                            units "nanoseconds";
                            description "Standard Deviation of the Slave Master Delay for this interval.";
                        }

                        leaf average-mean-path-delay-ns {
                            type int32;
                            units "nanoseconds";
                            description "Average of the Mean Path Delay for this interval.";
                        }

                        leaf minimum-mean-path-delay-ns {
                            type int32;
                            units "nanoseconds";
                            description "Minimum of the Mean Path Delay for this interval.";
                        }

                        leaf maximum-mean-path-delay-ns {
                            type int32;
                            units "nanoseconds";
                            description "Maximum of the Mean Path Delay for this interval.";
                        }

                        leaf stddev-mean-path-delay-ns {
                            type int32;
                            units "nanoseconds";
                            description "Standard Deviation of the Mean Path Delay for this interval.";
                        }

                        leaf average-offset-from-master-ns {
                            type int32;
                            units "nanoseconds";
                            description "Average of the Offset From Master for this interval.";
                        }

                        leaf minimum-offset-from-master-ns {
                            type int32;
                            units "nanoseconds";
                            description "Minimum of the Offset From Master for this interval.";
                        }

                        leaf maximum-offset-from-master-ns {
                            type int32;
                            units "nanoseconds";
                            description "Maximum of the Offset From Master for this interval.";
                        }

                        leaf stddev-offset-from-master-ns {
                            type int32;
                            units "nanoseconds";
                            description "Standard Deviation of the Offset From Master for this interval.";
                        }

                    } // list record

                } // container performance-monitoring

                container path-trace-ds {
                    description "Enter the path-trace-ds context";

                    leaf-list sequence {
                        type types-ptp:clock-identity-type;
                        description "List of clockIds from the received PATH_TRACE TLV.";
                    }

                } // container path-trace-ds

            } // list instance

        } // container ptp

    } // grouping state-system-ptp

}
