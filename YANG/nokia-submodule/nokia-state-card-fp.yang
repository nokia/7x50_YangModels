submodule nokia-state-card-fp {

    yang-version "1.1";

    belongs-to nokia-state { prefix "state"; }

    import ietf-yang-types                { prefix "yang"; }
    import nokia-sros-yang-extensions     { prefix "sros-ext"; }
    import nokia-types-card               { prefix "types-card"; }
    import nokia-types-qos                { prefix "types-qos"; }
    import nokia-types-sros               { prefix "types-sros"; }

    include nokia-state-qos;

    sros-ext:sros-major-release "rel26";
    organization "Nokia";
    contact
        "Nokia SR OS Support
         Web: <http://www.nokia.com>";
    description
        "Nokia YANG Data model with operational state for card forwarding plane on SR OS based routers.

         Copyright 2016 Nokia. All rights reserved. Reproduction of this document
         is authorized on the condition that the foregoing copyright notice is included.

         This nokia-state-card-fp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping state-card-fp {
        list fp {
            key "fp-number";
            description "Enter the fp list instance";

            leaf fp-number {
                type types-card:fp-id;
                description
                    "The unique value which uniquely identifies the forwarding plane within
                     a specific IOM card in the system.";
            }

            leaf total-policy-accounting-in-use {
                type uint32;
                description "Indicates the total number of statistics resources currently in use.";
            }

            leaf generation {
                type types-card:fp-generation;
                description "Indicates the generation of the FP network processor.";
            }

            list core {
                key "core-number";
                description "Enter the core list instance";

                leaf core-number {
                    type uint32 {
                        range "0..1";
                    }
                    description
                        "The value which uniquely identifies the core within a
                         specific IOM card forwarding plane in the system.";
                }

                container resource-usage {
                    description "Enter the resource-usage context";

                    list direct-mapped-policers {
                        key "partition";
                        description "Enter the direct-mapped-policers list instance";

                        leaf partition {
                            type enumeration {
                                enum per-fc                         { value 1; }
                                enum per-fc-unicast-multicast-or-multipoint { value 2; }
                                enum per-fc-unicast-broadcast-unknown-multicast { value 3; }
                                enum per-2-fc-unicast-multicast-or-multipoint { value 4; }
                                enum per-4-fc-unicast-multicast-or-multipoint { value 5; }
                                enum per-2-fc                       { value 6; }
                                enum per-4-fc                       { value 7; }
                            }
                            description "Indicates the policer pool.";
                        }

                        leaf total {
                            type yang:counter32;
                            description
                                "Indicates the number of total number of policers in the partition.
                                 When the value is zero, it indicates that this  resource type is
                                 not supported on this core.";
                        }

                        leaf stats-total {
                            type yang:counter32;
                            description
                                "Indicates the number of total number of policers stats in the partition.
                                 When the value is zero, it indicates that this  resource type is not
                                 supported on this core.";
                        }

                        leaf allocated {
                            type yang:counter32;
                            description
                                "Indicates the number of total number of policers allocated
                                 from the partition.";
                        }

                        leaf stats-allocated {
                            type yang:counter32;
                            description
                                "Indicates the number of total number of policers stats
                                  allocated from the partition.";
                        }

                    } // list direct-mapped-policers

                    container ingress-egress {
                        description "Enter the ingress-egress context";

                        container floating-policers-entries {
                            description "Enter the floating-policers-entries context";

                            leaf total {
                                type yang:counter32;
                                description
                                    "Indicates the number of total number of ingress floating
                                     policers supported on the core.";
                            }

                            leaf stats-total {
                                type yang:counter32;
                                description
                                    "Indicates the number of total number of ingress floating
                                     policers stats supported on the core.";
                            }

                            leaf allocated {
                                type yang:counter32;
                                description
                                    "Indicates the number of total number of  ingress floating
                                     policers currently allocated on the core.";
                            }

                            leaf stats-allocated {
                                type yang:counter32;
                                description
                                    "Indicates the number of total number of  ingress floating
                                     policers stats currently allocated on the core.";
                            }

                            leaf ingress-stats-acl {
                                type yang:counter32;
                                description
                                    "Indicates the the subset of floating policer stats which are
                                     currently in use by ingress ACLs for stats collection.";
                            }

                            leaf ingress-stats-shared-policers {
                                type yang:counter32;
                                description
                                    "Indicates the the subset of floating policer stats which are
                                     currently in use by shared policers for stats collection.";
                            }

                        } // container floating-policers-entries

                        container dedicated-policers-entries {
                            description "Enter the dedicated-policers-entries context";

                            leaf total {
                                type yang:counter32;
                                description
                                    "Indicates the number of total number of ingress dedicated
                                     policers supported on the core.";
                            }

                            leaf stats-total {
                                type yang:counter32;
                                description
                                    "Indicates the number of total number of ingress dedicated
                                     policers stats supported on the core.";
                            }

                            leaf allocated {
                                type yang:counter32;
                                description
                                    "Indicates the number of total number of  ingress dedicated
                                     policers currently allocated on the core.";
                            }

                            leaf stats-allocated {
                                type yang:counter32;
                                description
                                    "Indicates the number of total number of  ingress dedicated
                                     policers stats currently allocated on the core.";
                            }

                        } // container dedicated-policers-entries

                        container eight-queue-vlan-voq-entries {
                            description "Enter the eight-queue-vlan-voq-entries context";

                            leaf total {
                                type yang:counter32;
                                description
                                    "Indicates the number of total number of vlan voqs
                                     supported on the core.";
                            }

                            leaf allocated {
                                type yang:counter32;
                                description
                                    "Indicates the number of total number of vlan voqs
                                     allocated on the core.";
                            }

                        } // container eight-queue-vlan-voq-entries

                        container sap-entries {
                            description "Enter the sap-entries context";

                            leaf total {
                                type yang:counter32;
                                description
                                    "Indicates the number of total number of provisioned sap
                                     entries supported on the core.";
                            }

                            leaf allocated {
                                type yang:counter32;
                                description
                                    "Indicates the number of total number of provisioned sap
                                     entries allocated on the core.";
                            }

                        } // container sap-entries

                        container shared-policer-entries {
                            description "Enter the shared-policer-entries context";

                            leaf total {
                                type yang:counter32;
                                description
                                    "Indicates the number of total number of shared policers
                                     entries supported on the core.";
                            }

                            leaf allocated {
                                type yang:counter32;
                                description
                                    "Indicates the number of total number of shared policers
                                     entries allocated on the core.";
                            }

                            leaf stats-total {
                                type yang:counter32;
                                description
                                    "Indicates the number of total number of shared policers
                                     stats entries supported on the core.";
                            }

                            leaf stats-allocated {
                                type yang:counter32;
                                description
                                    "Indicates the number of total number of shared policers
                                     stats entries allocated on the core.";
                            }

                        } // container shared-policer-entries

                        container four-queue-vlan-voq-entries {
                            description "Enter the four-queue-vlan-voq-entries context";

                            leaf total {
                                type yang:counter32;
                                description
                                    "Indicates the number of total number of 4-queue vlan qos
                                     supported on the core.";
                            }

                            leaf allocated {
                                type yang:counter32;
                                description
                                    "Indicates the number of total number of 4-queue vlan qos
                                     allocated on the core.";
                            }

                        } // container four-queue-vlan-voq-entries

                        container filter-shared-policer-entries {
                            description "Enter the filter-shared-policer-entries context";

                            leaf total {
                                type yang:counter32;
                                description
                                    "Indicates the number of total number of filter shared policers
                                     entries supported on the core.";
                            }

                            leaf allocated {
                                type yang:counter32;
                                description
                                    "Indicates the number of total number of filter shared policers
                                     entries allocated on the core.";
                            }

                            leaf stats-total {
                                type yang:counter32;
                                description
                                    "Indicates the number of total number of filter shared policers
                                     stats entries supported on the core.";
                            }

                            leaf stats-allocated {
                                type yang:counter32;
                                description
                                    "Indicates the number of total number of filter shared policers
                                     stats entries allocated on the core.";
                            }

                        } // container filter-shared-policer-entries

                        container scheduler-flow-entries {
                            description "Enter the scheduler-flow-entries context";

                            leaf total {
                                type yang:counter32;
                                description
                                    "Indicates the number of total number of scheduler flow
                                     supported on the core.";
                            }

                            leaf allocated {
                                type yang:counter32;
                                description
                                    "Indicates the number of total number of scheduler flow
                                     allocated on the core.";
                            }

                        } // container scheduler-flow-entries

                        container scheduler-interfaces-entries {
                            description "Enter the scheduler-interfaces-entries context";

                            leaf total {
                                type yang:counter32;
                                description
                                    "Indicates the number of total number of scheduler interfaces
                                     supported on the core.";
                            }

                            leaf allocated {
                                type yang:counter32;
                                description
                                    "Indicates the number of total number of scheduler interfaces
                                     allocated on the core.";
                            }

                        } // container scheduler-interfaces-entries

                    } // container ingress-egress

                    container dram {
                        description "Enter the dram context";

                        leaf free-bdb {
                            type yang:counter64;
                            description
                                "Indicates the number of free DRAM bundle descriptor buffers
                                 (BDB) on the core.";
                        }

                        leaf minimum-free-bdb {
                            type yang:counter64;
                            description
                                "Indicates the minimum number of free DRAM BDBs on the core since
                                 the last read from the device.";
                        }

                        leaf lowest-free-bdb {
                            type yang:counter64;
                            description
                                "Indicates the lowest number of free DRAM BDBs on the core
                                 since it was last polled.";
                        }

                        leaf total-bdb {
                            type yang:counter64;
                            description "Indicates the total number of DRAM BDBs on the core.";
                        }

                        container bandwidth {
                            description "Enter the bandwidth context";

                            leaf max-consecutive-poll-blocked {
                                type yang:counter64;
                                description
                                    "Indicates the number of DRAM bandwidth maximum consecutive polls
                                     blocked on the core.";
                            }

                            leaf packet-rejects-last-poll {
                                type yang:counter64;
                                description
                                    "Indicates the number of DRAM bandwidth packets that were rejected
                                     due to resource exhaustion since last poll on the core.";
                            }

                            leaf total-packet-rejects {
                                type yang:counter64;
                                description
                                    "Indicates the cumulative total number of DRAM bandwidth packet
                                     rejects on the core.";
                            }

                        } // container bandwidth

                    } // container dram

                    container mesh-fabric-bandwidth {
                        description "Enter the mesh-fabric-bandwidth context";

                        leaf assert-congestion-fp1 {
                            type yang:counter64;
                            description "Indicates the assert congestion count between this FP and FP1.";
                        }

                        leaf assert-congestion-fp2 {
                            type yang:counter64;
                            description "Indicates the assert congestion count between this FP and FP2.";
                        }

                        leaf assert-congestion-fp3 {
                            type yang:counter64;
                            description "Indicates the assert congestion count between this FP and FP3.";
                        }

                    } // container mesh-fabric-bandwidth

                    container processing-pipeline {
                        description "Enter the processing-pipeline context";

                        leaf max-consecutive-poll-nif-prd-drops {
                            type yang:counter64;
                            description
                                "Indicates the the maximum number of core processing pipeline
                                 consecutive polls during NIF PRD drops on the core.";
                        }

                        leaf nif-prd-drops-last-poll {
                            type yang:counter64;
                            description
                                "Indicates the number of core processing pipeline NIF PRD drops
                                 since the last poll on the core.";
                        }

                        leaf total-nif-prd-drops {
                            type yang:counter64;
                            description
                                "Indicates the cumulative total number of all core processing pipeline
                                 NIF PRD drops on the core.";
                        }

                    } // container processing-pipeline

                    container sram {
                        description "Enter the sram context";

                        leaf free-buffer {
                            type yang:counter64;
                            description "Indicates the number of free SRAM buffers on the core.";
                        }

                        leaf minimum-free-buffer {
                            type yang:counter64;
                            description
                                "Indicates the minimum number of free SRAM buffers on the core
                                 since the last read from the device.";
                        }

                        leaf lowest-free-buffer {
                            type yang:counter64;
                            description
                                "Indicates the lowest number of free SRAM buffers on the core
                                 since it was last polled.";
                        }

                        leaf total-buffer {
                            type yang:counter64;
                            description "Indicates the total number of SRAM buffers on the core.";
                        }

                        leaf free-pdb {
                            type yang:counter64;
                            description
                                "Indicates the number of free SRAM packet descriptor buffers
                                 (PDB) on the FP.";
                        }

                        leaf minimum-free-pdb {
                            type yang:counter64;
                            description
                                "Indicates the minimum number of free SRAM PDBs on the core
                                 since the last read from the device.";
                        }

                        leaf lowest-free-pdb {
                            type yang:counter64;
                            description
                                "Indicates the lowest number of free SRAM PDBs on the core
                                 since it was last polled.";
                        }

                        leaf total-pdb {
                            type yang:counter64;
                            description "Indicates the total number of SRAM PDBs on the core.";
                        }

                    } // container sram

                } // container resource-usage

            } // list core

            container egress {
                description "Enter the egress context";

                list burst-control-group {
                    key "bcg-visitation-time";
                    description "Enter the burst-control-group list instance";

                    leaf bcg-visitation-time {
                        type types-sros:named-item-255;
                        description
                            "The unique value which uniquely identifies the visitation time of the burst control
                             group within a specific IOM card in the system.";
                    }

                    container recalc-info {
                        description "Enter the recalc-info context";

                        leaf num-queue {
                            type uint32;
                            description "The number of queues associsted to this burst control group.";
                        }

                        leaf at-risk {
                            type boolean;
                            description "The burst control group is at risk or not.";
                        }

                        leaf current {
                            type string;
                            description "The burst control group worst seen current time.";
                        }

                        leaf worst-case {
                            type string;
                            description "The burst control group worst seen ever time.";
                        }

                        leaf avg-last-readings {
                            type string;
                            description "The burst control group last seen ten readings.";
                        }

                        leaf avg-worst-seen-readings {
                            type string;
                            description "The burst control group last ten worst seen readings.";
                        }

                        leaf worst-possible-ever {
                            type string;
                            description "The burst control group worst ever configuration at 100%% scheduling predicted readings.";
                        }

                        leaf worst-possible-current {
                            type string;
                            description "The burst control group worst current map at 100%% scheduling predicted readings.";
                        }

                        leaf worst-provisioned-ever {
                            type string;
                            description "The burst control group worst ever configuration at provisioned predicted readings.";
                        }

                        leaf worst-provisioned-current {
                            type string;
                            description "The burst control group worst current map at provisioned predicted readings.";
                        }

                    } // container recalc-info

                } // list burst-control-group

            } // container egress

            container hi-bw-mcast-src {
                description "Enter the hi-bw-mcast-src context";

                leaf tap-count {
                    type uint32;
                    description
                        "Indicates the number of high bandwidth multicast traffic taps
                         on this forwarding plane.";
                }

            } // container hi-bw-mcast-src

            container ingress {
                description "Enter the ingress context";

                container access {
                    description "Enter the access context";

                    list queue-group {
                        key "queue-group-name instance-id";
                        description "Enter the queue-group list instance";

                        leaf queue-group-name {
                            type leafref {
                                path "../../../../../../qos/queue-group-templates/ingress/queue-group/ingress-queue-group-name";
                            }
                            description "Specifies the queue-group name.";
                        }

                        leaf instance-id {
                            type uint16 {
                                range "1..65535";
                            }
                            description "Specifies the instance identifier.";
                        }

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        list policer {
                            key "policer-id";
                            description "Enter the policer list instance";

                            leaf policer-id {
                                type types-qos:ingress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-priority-no-cir {

                                        container offered-priority-no-cir {
                                            description "Enter the offered-priority-no-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf high-priority-dropped-packets {
                                                type yang:counter64;
                                                description "The number of high-priority packets dropped by the packet processor to traffic manager";
                                            }

                                            leaf high-priority-dropped-octets {
                                                type yang:counter64;
                                                description "The number of high-priority octets dropped by the packet processor to traffic manager";
                                            }

                                            leaf low-priority-dropped-packets {
                                                type yang:counter64;
                                                description "The number of low-priority packets dropped by the packet processor to traffic manager";
                                            }

                                            leaf low-priority-dropped-octets {
                                                type yang:counter64;
                                                description "The number of low-priority octets dropped by the packet processor to traffic manager";
                                            }

                                            leaf high-priority-forwarded-packets {
                                                type yang:counter64;
                                                description "The number of high-priority packets forwarded by the packet processor to traffic manager";
                                            }

                                            leaf high-priority-forwarded-octets {
                                                type yang:counter64;
                                                description "The number of high-priority octets forwarded by the packet processor to traffic manager";
                                            }

                                            leaf low-priority-forwarded-packets {
                                                type yang:counter64;
                                                description "The number of low-priority packets forwarded by the packet processor to traffic manager";
                                            }

                                            leaf low-priority-forwarded-octets {
                                                type yang:counter64;
                                                description "The number of low-priority octets forwarded by the packet processor to traffic manager";
                                            }

                                        } // container offered-priority-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-priority-cir {

                                        container offered-priority-cir {
                                            description "Enter the offered-priority-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-priority-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-profile-cir {

                                        container offered-limited-profile-cir {
                                            description "Enter the offered-limited-profile-cir context";

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-limited-profile-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf uncolor-offered-packets {
                                                type yang:counter64;
                                                description "The number of out-of-rofile packets offered by the packet processor to traffic manager";
                                            }

                                            leaf uncolor-offered-octets {
                                                type yang:counter64;
                                                description "The number of out-of-profile octets offered by the packet processor to traffic manager";
                                            }

                                        } // container offered-limited-capped-cir

                                    }
                                }
                            } // container statistics

                            container hardware-policer {
                                description "Enter the hardware-policer context";

                                leaf adapted-admin-cbs {
                                    type int64;
                                    units "bytes";
                                    description "Admin CBS.";
                                }

                                leaf adapted-admin-mbs {
                                    type int64;
                                    units "bytes";
                                    description "Admin MBS.";
                                }

                                leaf adapted-hp-only {
                                    type int64;
                                    units "bytes";
                                    description "Hi Prio Only.";
                                }

                                leaf depth {
                                    type int64;
                                    units "bytes";
                                    description "Depth.";
                                }

                                leaf operational-cir {
                                    type types-qos:int32-max;
                                    description "Oper CIR.";
                                }

                                leaf operational-fir {
                                    type types-qos:int32-max;
                                    description "Oper FIR.";
                                }

                                leaf operational-pir {
                                    type types-qos:int32-max;
                                    description "Oper PIR.";
                                }

                            } // container hardware-policer

                        } // list policer

                    } // list queue-group

                } // container access

                container mcast-path-management {
                    description "Enter the mcast-path-management context";

                    leaf primary-in-use-bandwidth {
                        type uint32;
                        units "kilobps";
                        description
                            "Indicates the in use ingress multicast bandwidth for the primary
                             forwarding path.";
                    }

                    leaf secondary-in-use-bandwidth {
                        type uint32;
                        units "kilobps";
                        description
                            "Indicates the in use ingress multicast bandwidth for the secondary
                             forwarding path.";
                    }

                    leaf blackhole-in-use-bandwidth {
                        type uint32;
                        units "kilobps";
                        description
                            "Indicates the bandwidth of the ingress multicast traffic that
                             is being black holed on the forwarding plane.";
                    }

                } // container mcast-path-management

                container network {
                    description "Enter the network context";

                    list queue-group {
                        key "queue-group-name instance-id";
                        description "Enter the queue-group list instance";

                        leaf queue-group-name {
                            type leafref {
                                path "../../../../../../qos/queue-group-templates/ingress/queue-group/ingress-queue-group-name";
                            }
                            description "Specifies the queue-group name.";
                        }

                        leaf instance-id {
                            type uint16 {
                                range "1..65535";
                            }
                            description "Specifies the instance identifier.";
                        }

                        container policer-control-policy {
                            description "Enter the policer-control-policy context";

                            list arbiter {
                                key "arbiter-name";
                                description "Enter the arbiter list instance";

                                leaf arbiter-name {
                                    type types-sros:named-item;
                                    description "Specifies the arbiter name.";
                                }

                                container statistics {
                                    description "Enter the statistics context";

                                    leaf forwarded-packets {
                                        type yang:counter64;
                                        description "The number of forwarded packets.";
                                    }

                                    leaf forwarded-octets {
                                        type yang:counter64;
                                        description "The number of forwarded octets.";
                                    }

                                } // container statistics

                            } // list arbiter

                        } // container policer-control-policy

                        list policer {
                            key "policer-id";
                            description "Enter the policer list instance";

                            leaf policer-id {
                                type types-qos:ingress-policer-id;
                                description "The unique identifier for the policer.";
                            }

                            container statistics {
                                description "Enter the statistics context";

                                choice stat-mode {
                                    case minimal {

                                        container minimal {
                                            description "Enter the minimal context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf all-dropped-packets {
                                                type yang:counter64;
                                                description "The number of all the priority packets dropped by the packet processor to traffic manager";
                                            }

                                            leaf all-dropped-octets {
                                                type yang:counter64;
                                                description "The number of all the priority octets dropped by the packet processor to traffic manager";
                                            }

                                            leaf all-forwarded-packets {
                                                type yang:counter64;
                                                description "The number of all the priority packets forwarded by the packet processor to traffic manager";
                                            }

                                            leaf all-forwarded-octets {
                                                type yang:counter64;
                                                description "The number of all the priority octets forwarded by the packet processor to traffic manager";
                                            }

                                        } // container minimal

                                    }
                                    case offered-profile-no-cir {

                                        container offered-profile-no-cir {
                                            description "Enter the offered-profile-no-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-no-cir

                                    }
                                    case offered-priority-no-cir {

                                        container offered-priority-no-cir {
                                            description "Enter the offered-priority-no-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf high-priority-dropped-packets {
                                                type yang:counter64;
                                                description "The number of high-priority packets dropped by the packet processor to traffic manager";
                                            }

                                            leaf high-priority-dropped-octets {
                                                type yang:counter64;
                                                description "The number of high-priority octets dropped by the packet processor to traffic manager";
                                            }

                                            leaf low-priority-dropped-packets {
                                                type yang:counter64;
                                                description "The number of low-priority packets dropped by the packet processor to traffic manager";
                                            }

                                            leaf low-priority-dropped-octets {
                                                type yang:counter64;
                                                description "The number of low-priority octets dropped by the packet processor to traffic manager";
                                            }

                                            leaf high-priority-forwarded-packets {
                                                type yang:counter64;
                                                description "The number of high-priority packets forwarded by the packet processor to traffic manager";
                                            }

                                            leaf high-priority-forwarded-octets {
                                                type yang:counter64;
                                                description "The number of high-priority octets forwarded by the packet processor to traffic manager";
                                            }

                                            leaf low-priority-forwarded-packets {
                                                type yang:counter64;
                                                description "The number of low-priority packets forwarded by the packet processor to traffic manager";
                                            }

                                            leaf low-priority-forwarded-octets {
                                                type yang:counter64;
                                                description "The number of low-priority octets forwarded by the packet processor to traffic manager";
                                            }

                                        } // container offered-priority-no-cir

                                    }
                                    case offered-profile-cir {

                                        container offered-profile-cir {
                                            description "Enter the offered-profile-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-cir

                                    }
                                    case offered-priority-cir {

                                        container offered-priority-cir {
                                            description "Enter the offered-priority-cir context";

                                            leaf high-priority-offered-packets {
                                                type yang:counter64;
                                                description "The number of high-priority packets offered by the packet processor to traffic manager";
                                            }

                                            leaf high-priority-offered-octets {
                                                type yang:counter64;
                                                description "The number of high-priority octets offered by the packet processor to traffic manager";
                                            }

                                            leaf low-priority-offered-packets {
                                                type yang:counter64;
                                                description "The number of low-priority packets offered by the packet processor to traffic manager";
                                            }

                                            leaf low-priority-offered-octets {
                                                type yang:counter64;
                                                description "The number of low-priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-priority-cir

                                    }
                                    case offered-total-cir {

                                        container offered-total-cir {
                                            description "Enter the offered-total-cir context";

                                            leaf all-offered-packets {
                                                type yang:counter64;
                                                description "The number of all the priority packets offered by the packet processor to traffic manager";
                                            }

                                            leaf all-offered-octets {
                                                type yang:counter64;
                                                description "The number of all the priority octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-total-cir

                                    }
                                    case offered-limited-profile-cir {

                                        container offered-limited-profile-cir {
                                            description "Enter the offered-limited-profile-cir context";

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-limited-profile-cir

                                    }
                                    case offered-profile-capped-cir {

                                        container offered-profile-capped-cir {
                                            description "Enter the offered-profile-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf out-profile-offered-packets {
                                                type yang:counter64;
                                                description "The number of out-of-profile packets offered by the packet processor to traffic manager";
                                            }

                                            leaf out-profile-offered-octets {
                                                type yang:counter64;
                                                description "The number of out-of-profile octets offered by the packet processor to traffic manager";
                                            }

                                            leaf uncolor-offered-packets {
                                                type yang:counter64;
                                                description "The number of uncolor packets offered by the packet processor to traffic manager";
                                            }

                                            leaf uncolor-offered-octets {
                                                type yang:counter64;
                                                description "The number of uncolor octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                        } // container offered-profile-capped-cir

                                    }
                                    case offered-limited-capped-cir {

                                        container offered-limited-capped-cir {
                                            description "Enter the offered-limited-capped-cir context";

                                            leaf in-profile-offered-packets {
                                                type yang:counter64;
                                                description "The number of in-profile packets offered by the packet processor to traffic manager";
                                            }

                                            leaf in-profile-offered-octets {
                                                type yang:counter64;
                                                description "The number of in-profile octets offered by the packet processor to traffic manager";
                                            }

                                            leaf in-profile-dropped-packets {
                                                type yang:counter64;
                                                description "The number of in-profile packets dropped by the packet processor to traffic manager";
                                            }

                                            leaf in-profile-dropped-octets {
                                                type yang:counter64;
                                                description "The number of in-profile octets dropped by the packet processor to traffic manager";
                                            }

                                            leaf out-profile-dropped-packets {
                                                type yang:counter64;
                                                description "The number of out-of-profile packets dropped by the packet processor to traffic manager";
                                            }

                                            leaf out-profile-dropped-octets {
                                                type yang:counter64;
                                                description "The number of out-of-profile octets dropped by the packet processor to traffic manager";
                                            }

                                            leaf in-profile-forwarded-packets {
                                                type yang:counter64;
                                                description "The number of in-profile packets forwarded by the packet processor to traffic manager";
                                            }

                                            leaf in-profile-forwarded-octets {
                                                type yang:counter64;
                                                description "The number of in-profile octets forwarded by the packet processor to traffic manager";
                                            }

                                            leaf out-profile-forwarded-packets {
                                                type yang:counter64;
                                                description "The number of out-of-profile packets forwarded by the packet processor to traffic manager";
                                            }

                                            leaf out-profile-forwarded-octets {
                                                type yang:counter64;
                                                description "The number of out-of-profile octets forwarded by the packet processor to traffic manager";
                                            }

                                            leaf uncolor-offered-packets {
                                                type yang:counter64;
                                                description "The number of out-of-rofile packets offered by the packet processor to traffic manager";
                                            }

                                            leaf uncolor-offered-octets {
                                                type yang:counter64;
                                                description "The number of out-of-profile octets offered by the packet processor to traffic manager";
                                            }

                                        } // container offered-limited-capped-cir

                                    }
                                }
                            } // container statistics

                            container hardware-policer {
                                description "Enter the hardware-policer context";

                                leaf adapted-admin-cbs {
                                    type int64;
                                    units "bytes";
                                    description "Admin CBS.";
                                }

                                leaf adapted-admin-mbs {
                                    type int64;
                                    units "bytes";
                                    description "Admin MBS.";
                                }

                                leaf adapted-hp-only {
                                    type int64;
                                    units "bytes";
                                    description "Hi Prio Only.";
                                }

                                leaf depth {
                                    type int64;
                                    units "bytes";
                                    description "Depth.";
                                }

                                leaf operational-cir {
                                    type types-qos:int32-max;
                                    description "Oper CIR.";
                                }

                                leaf operational-fir {
                                    type types-qos:int32-max;
                                    description "Oper FIR.";
                                }

                                leaf operational-pir {
                                    type types-qos:int32-max;
                                    description "Oper PIR.";
                                }

                            } // container hardware-policer

                        } // list policer

                    } // list queue-group

                    list queue {
                        key "queue-id";
                        description "Enter the queue list instance";

                        leaf queue-id {
                            type types-qos:ingress-queue-id;
                            description "The unique identifier for the queue.";
                        }

                        list hardware-queue {
                            key "source-tap-offset dest-card dest-fp dest-tap-offset";
                            description "Enter the hardware-queue list instance";

                            leaf source-tap-offset {
                                type int32;
                                description "Source TAP.";
                            }

                            leaf dest-card {
                                type int32;
                                description "Card number";
                            }

                            leaf dest-fp {
                                type int32;
                                description "FP number";
                            }

                            leaf dest-tap-offset {
                                type int32;
                                description "Destination TAP.";
                            }

                            leaf adapted-admin-mbs {
                                type int64;
                                units "bytes";
                                description "Admin MBS.";
                            }

                            leaf adapted-admin-cbs {
                                type int64;
                                units "bytes";
                                description "Admin CBS.";
                            }

                            leaf operational-mbs {
                                type int64;
                                units "bytes";
                                description "Oper MBS.";
                            }

                            leaf depth {
                                type union {
                                    type enumeration {
                                        enum max                            { value -1; }
                                    }
                                    type int64;
                                }
                                description "Depth CIR.";
                            }

                            leaf operational-cir {
                                type union {
                                    type enumeration {
                                        enum max                            { value -1; }
                                    }
                                    type int64;
                                }
                                description "Oper CIR.";
                            }

                            leaf operational-fir {
                                type union {
                                    type enumeration {
                                        enum max                            { value -1; }
                                    }
                                    type int64;
                                }
                                description "Oper FIR.";
                            }

                            leaf operational-pir {
                                type union {
                                    type enumeration {
                                        enum max                            { value -1; }
                                    }
                                    type int64;
                                }
                                description "Oper PIR.";
                            }

                            leaf exceed-droptail {
                                type union {
                                    type int64 {
                                        range "0..max";
                                    }
                                    type enumeration {
                                        enum auto                           { value -1; }
                                    }
                                }
                                description "Exceed droptail.";
                            }

                            leaf high-droptail {
                                type union {
                                    type int64 {
                                        range "0..max";
                                    }
                                    type enumeration {
                                        enum auto                           { value -1; }
                                    }
                                }
                                description "High droptail.";
                            }

                            leaf high-plus-droptail {
                                type union {
                                    type int64 {
                                        range "0..max";
                                    }
                                    type enumeration {
                                        enum auto                           { value -1; }
                                    }
                                }
                                description "Highplus droptail.";
                            }

                            leaf low-droptail {
                                type union {
                                    type int64 {
                                        range "0..max";
                                    }
                                    type enumeration {
                                        enum auto                           { value -1; }
                                    }
                                }
                                description "Low droptail.";
                            }

                            leaf operational-exceed-burst {
                                type types-qos:int64-max;
                                description "Oper burst exceed.";
                            }

                            leaf operational-max-transmit-data-size {
                                type types-qos:int64-max;
                                description "Oper max transmit data size.";
                            }

                            leaf operational-burst-fir {
                                type types-qos:int64-max;
                                description "Oper burst FIR.";
                            }

                        } // list hardware-queue

                    } // list queue

                    list pool {
                        key "name";
                        description "Enter the pool list instance";

                        leaf name {
                            type types-sros:named-item;
                            description "Specifies the unique name of the pool for the FP.";
                        }

                        container pool-depth {
                            description "Enter the pool-depth context";

                            leaf elapsed-time {
                                type types-sros:time-interval;
                                description "Indicated the elapsed time.";
                            }

                            leaf pool-polling-interval {
                                type types-sros:time-interval;
                                description "Indicates the pool polling interval.";
                            }

                            leaf reserved-pool-last-violation {
                                type yang:date-and-time;
                                description "Indicates the last violation time for reserved pool buffers in use.";
                            }

                            leaf reserved-pool-total-threshold-violations {
                                type yang:counter32;
                                description "Indicates the total threshold violations for reserved pool buffers in use.";
                            }

                            leaf shared-pool-last-violation {
                                type yang:date-and-time;
                                description "Indicates the last violation time for shared pool buffers in use.";
                            }

                            leaf shared-pool-total-threshold-violations {
                                type yang:counter32;
                                description "Indicates the total threshold violations for shared pool buffers in use.";
                            }

                            leaf total-pool-last-violation {
                                type yang:date-and-time;
                                description "Indicates the last violation time for total pool buffers in use.";
                            }

                            leaf total-pool-total-threshold-violations {
                                type yang:counter32;
                                description "Indicates the total threshold violations for total pool buffers in use.";
                            }

                            container total-pool {
                                description "Enter the total-pool context";

                                leaf depth-0-to-10-percent {
                                    type decimal64 {
                                        fraction-digits 2;
                                    }
                                    description "Indicated the depth 0 to 10 percent.";
                                }

                                leaf depth-11-to-20-percent {
                                    type decimal64 {
                                        fraction-digits 2;
                                    }
                                    description "Indicated the depth 0 to 20 percent.";
                                }

                                leaf depth-21-to-30-percent {
                                    type decimal64 {
                                        fraction-digits 2;
                                    }
                                    description "Indicated the depth 0 to 30 percent.";
                                }

                                leaf depth-31-to-40-percent {
                                    type decimal64 {
                                        fraction-digits 2;
                                    }
                                    description "Indicated the depth 0 to 40 percent.";
                                }

                                leaf depth-41-to-50-percent {
                                    type decimal64 {
                                        fraction-digits 2;
                                    }
                                    description "Indicated the depth 0 to 50 percent.";
                                }

                                leaf depth-51-to-60-percent {
                                    type decimal64 {
                                        fraction-digits 2;
                                    }
                                    description "Indicated the depth 0 to 60 percent.";
                                }

                                leaf depth-61-to-70-percent {
                                    type decimal64 {
                                        fraction-digits 2;
                                    }
                                    description "Indicated the depth 0 to 70 percent.";
                                }

                                leaf depth-71-to-80-percent {
                                    type decimal64 {
                                        fraction-digits 2;
                                    }
                                    description "Indicated the depth 0 to 80 percent.";
                                }

                                leaf depth-81-to-90-percent {
                                    type decimal64 {
                                        fraction-digits 2;
                                    }
                                    description "Indicated the depth 0 to 90 percent.";
                                }

                                leaf depth-91-to-100-percent {
                                    type decimal64 {
                                        fraction-digits 2;
                                    }
                                    description "Indicated the depth 0 to 100 percent.";
                                }

                            } // container total-pool

                            container shared-pool {
                                description "Enter the shared-pool context";

                                leaf depth-0-to-10-percent {
                                    type decimal64 {
                                        fraction-digits 2;
                                    }
                                    description "Indicated the depth 0 to 10 percent.";
                                }

                                leaf depth-11-to-20-percent {
                                    type decimal64 {
                                        fraction-digits 2;
                                    }
                                    description "Indicated the depth 0 to 20 percent.";
                                }

                                leaf depth-21-to-30-percent {
                                    type decimal64 {
                                        fraction-digits 2;
                                    }
                                    description "Indicated the depth 0 to 30 percent.";
                                }

                                leaf depth-31-to-40-percent {
                                    type decimal64 {
                                        fraction-digits 2;
                                    }
                                    description "Indicated the depth 0 to 40 percent.";
                                }

                                leaf depth-41-to-50-percent {
                                    type decimal64 {
                                        fraction-digits 2;
                                    }
                                    description "Indicated the depth 0 to 50 percent.";
                                }

                                leaf depth-51-to-60-percent {
                                    type decimal64 {
                                        fraction-digits 2;
                                    }
                                    description "Indicated the depth 0 to 60 percent.";
                                }

                                leaf depth-61-to-70-percent {
                                    type decimal64 {
                                        fraction-digits 2;
                                    }
                                    description "Indicated the depth 0 to 70 percent.";
                                }

                                leaf depth-71-to-80-percent {
                                    type decimal64 {
                                        fraction-digits 2;
                                    }
                                    description "Indicated the depth 0 to 80 percent.";
                                }

                                leaf depth-81-to-90-percent {
                                    type decimal64 {
                                        fraction-digits 2;
                                    }
                                    description "Indicated the depth 0 to 90 percent.";
                                }

                                leaf depth-91-to-100-percent {
                                    type decimal64 {
                                        fraction-digits 2;
                                    }
                                    description "Indicated the depth 0 to 100 percent.";
                                }

                            } // container shared-pool

                            container reserved-pool {
                                description "Enter the reserved-pool context";

                                leaf depth-0-to-10-percent {
                                    type decimal64 {
                                        fraction-digits 2;
                                    }
                                    description "Indicated the depth 0 to 10 percent.";
                                }

                                leaf depth-11-to-20-percent {
                                    type decimal64 {
                                        fraction-digits 2;
                                    }
                                    description "Indicated the depth 0 to 20 percent.";
                                }

                                leaf depth-21-to-30-percent {
                                    type decimal64 {
                                        fraction-digits 2;
                                    }
                                    description "Indicated the depth 0 to 30 percent.";
                                }

                                leaf depth-31-to-40-percent {
                                    type decimal64 {
                                        fraction-digits 2;
                                    }
                                    description "Indicated the depth 0 to 40 percent.";
                                }

                                leaf depth-41-to-50-percent {
                                    type decimal64 {
                                        fraction-digits 2;
                                    }
                                    description "Indicated the depth 0 to 50 percent.";
                                }

                                leaf depth-51-to-60-percent {
                                    type decimal64 {
                                        fraction-digits 2;
                                    }
                                    description "Indicated the depth 0 to 60 percent.";
                                }

                                leaf depth-61-to-70-percent {
                                    type decimal64 {
                                        fraction-digits 2;
                                    }
                                    description "Indicated the depth 0 to 70 percent.";
                                }

                                leaf depth-71-to-80-percent {
                                    type decimal64 {
                                        fraction-digits 2;
                                    }
                                    description "Indicated the depth 0 to 80 percent.";
                                }

                                leaf depth-81-to-90-percent {
                                    type decimal64 {
                                        fraction-digits 2;
                                    }
                                    description "Indicated the depth 0 to 90 percent.";
                                }

                                leaf depth-91-to-100-percent {
                                    type decimal64 {
                                        fraction-digits 2;
                                    }
                                    description "Indicated the depth 0 to 100 percent.";
                                }

                            } // container reserved-pool

                            container usage-alarm-thresholds {
                                description "Enter the usage-alarm-thresholds context";

                                leaf total-pool-usage-threshold-exceeded {
                                    type boolean;
                                    description
                                        "Specifies if total pool buffer usage is in violation state and is
                                         above the configured threshold percentage. When true it is above the
                                         thresholds. When false it is below the thresholds.";
                                }

                                leaf shared-pool-usage-threshold-exceeded {
                                    type boolean;
                                    description
                                        "Specifies if shared pool buffer usage is in violation state and is
                                         above the configured threshold percentage. When true it is above the
                                         thresholds. When false it is below the thresholds.";
                                }

                                leaf reserved-pool-usage-threshold-exceeded {
                                    type boolean;
                                    description
                                        "Specifies if reserved pool buffer usage is in violation state and is
                                         above the configured threshold percentage. When true it is above the
                                         thresholds. When false it is below the thresholds.";
                                }

                            } // container usage-alarm-thresholds

                        } // container pool-depth

                        container pool-usage {
                            description "Enter the pool-usage context";

                            leaf total-pool-size {
                                type uint32;
                                units "kilobytes";
                                description "Total buffer pools size.";
                            }

                            leaf total-pool-in-use {
                                type uint32;
                                units "kilobytes";
                                description "Total buffer pools size in use.";
                            }

                            leaf shared-pool-size {
                                type uint32;
                                units "kilobytes";
                                description "Total shared pools size.";
                            }

                            leaf shared-pool-in-use {
                                type uint32;
                                units "kilobytes";
                                description "Total shared pools size in use.";
                            }

                            leaf reserved-pool-size {
                                type uint32;
                                units "kilobytes";
                                description "Total reserved pools size.";
                            }

                            leaf reserved-pool-in-use {
                                type uint32;
                                units "kilobytes";
                                description "Total reserved pools size in use.";
                            }

                            leaf total-queues-added {
                                type uint32;
                                description "Total queues added.";
                            }

                            leaf total-queues-deleted {
                                type uint32;
                                description "Total queues deleted.";
                            }

                            leaf current-queues {
                                type uint32;
                                description "Current queues.";
                            }

                        } // container pool-usage

                        container statistics {
                            description "Enter the statistics context";

                            leaf forward-packets {
                                type yang:counter64;
                                description "The number of packets forwarded.";
                            }

                            leaf forward-octets {
                                type yang:counter64;
                                description "The number of octets forwarded.";
                            }

                            leaf discard-other-packets {
                                type yang:counter64;
                                description "The number of packets dropped due to queue tail drop or lack of buffer from pool.";
                            }

                            leaf discard-other-octets {
                                type yang:counter64;
                                description "The number of octets dropped due to queue tail drop or lack of buffer from pool.";
                            }

                            leaf discard-pool-exceed-slope-packets {
                                type yang:counter64;
                                description "The number of dropped pool exceed slope packets.";
                            }

                            leaf discard-pool-exceed-slope-octets {
                                type yang:counter64;
                                description "The number of dropped pool exceed slope octets.";
                            }

                            leaf discard-pool-low-slope-packets {
                                type yang:counter64;
                                description "The number of dropped pool low slope packets.";
                            }

                            leaf discard-pool-low-slope-octets {
                                type yang:counter64;
                                description "The number of dropped pool low slope octets.";
                            }

                            leaf discard-pool-high-slope-packets {
                                type yang:counter64;
                                description "The number of dropped pool high slope packets.";
                            }

                            leaf discard-pool-high-slope-octets {
                                type yang:counter64;
                                description "The number of dropped pool high slope octets.";
                            }

                            leaf discard-pool-highplus-slope-packets {
                                type yang:counter64;
                                description "The number of dropped pool highplus slope packets.";
                            }

                            leaf discard-pool-highplus-slope-octets {
                                type yang:counter64;
                                description "The number of dropped pool highplus slope octets.";
                            }

                            leaf discard-pool-shared-packets {
                                type yang:counter64;
                                description "The number of dropped pool fairness packets.";
                            }

                            leaf discard-pool-shared-octets {
                                type yang:counter64;
                                description "The number of dropped pool fairness octets.";
                            }

                            leaf discard-pool-total-packets {
                                type yang:counter64;
                                description "The number of dropped pool exhaust packets.";
                            }

                            leaf discard-pool-total-octets {
                                type yang:counter64;
                                description "The number of dropped pool exhaust octets.";
                            }

                            leaf discard-queue-tail-drop-packets {
                                type yang:counter64;
                                description "The number of dropped queue tail packets.";
                            }

                            leaf discard-queue-tail-drop-octets {
                                type yang:counter64;
                                description "The number of dropped queue tail octets.";
                            }

                            leaf total-packets {
                                type yang:counter64;
                                description "The number of total packets.";
                            }

                            leaf total-octets {
                                type yang:counter64;
                                description "The number of total octets.";
                            }

                        } // container statistics

                    } // list pool

                } // container network

                container policy-accounting {
                    description "Enter the policy-accounting context";

                    leaf classes-in-use {
                        type uint32;
                        description "Indicates the total number of policy accounting class resources currently in use.";
                    }

                    leaf policers-in-use {
                        type uint32;
                        description "Indicates the total number of policy accounting policer resources currently in use.";
                    }

                } // container policy-accounting

                container dist-cpu-protection {
                    description "Enter the dist-cpu-protection context";

                    container dynamic-policer {
                        description "Enter the dynamic-policer context";

                        leaf in-use {
                            type uint32;
                            description "Number of dynamic-policers in-use";
                        }

                        leaf high-water-mark-hit-count {
                            type uint32;
                            description "High water-mark hit-count";
                        }

                        leaf high-water-mark-hit-time {
                            type yang:date-and-time;
                            description "High water-mark hit-time";
                        }

                        leaf allocation-fail-count {
                            type uint32;
                            description "Count of allocation fails for dynamic-policers";
                        }

                    } // container dynamic-policer

                } // container dist-cpu-protection

                list burst-control-group {
                    key "bcg-visitation-time";
                    description "Enter the burst-control-group list instance";

                    leaf bcg-visitation-time {
                        type types-sros:named-item-255;
                        description
                            "The unique value which uniquely identifies the visitation time of the burst control
                             group within a specific IOM card in the system.";
                    }

                    container recalc-info {
                        description "Enter the recalc-info context";

                        leaf num-queue {
                            type uint32;
                            description "The number of queues associsted to this burst control group.";
                        }

                        leaf at-risk {
                            type boolean;
                            description "The burst control group is at risk or not.";
                        }

                        leaf current {
                            type string;
                            description "The burst control group worst seen current time.";
                        }

                        leaf worst-case {
                            type string;
                            description "The burst control group worst seen ever time.";
                        }

                        leaf avg-last-readings {
                            type string;
                            description "The burst control group last seen ten readings.";
                        }

                        leaf avg-worst-seen-readings {
                            type string;
                            description "The burst control group last ten worst seen readings.";
                        }

                        leaf worst-possible-ever {
                            type string;
                            description "The burst control group worst ever configuration at 100%% scheduling predicted readings.";
                        }

                        leaf worst-possible-current {
                            type string;
                            description "The burst control group worst current map at 100%% scheduling predicted readings.";
                        }

                        leaf worst-provisioned-ever {
                            type string;
                            description "The burst control group worst ever configuration at provisioned predicted readings.";
                        }

                        leaf worst-provisioned-current {
                            type string;
                            description "The burst control group worst current map at provisioned predicted readings.";
                        }

                    } // container recalc-info

                } // list burst-control-group

            } // container ingress

            container input-output {
                description "Enter the input-output context";

                list statistics {
                    key "statistics-type";
                    description "Enter the statistics list instance";

                    leaf statistics-type {
                        type enumeration {
                            enum cumulative                     { value 1; }
                            enum since-last-cleared             { value 2; }
                        }
                        description "The type of statistics represented.";
                    }

                    leaf traffic-class-0-policer-count-red {
                        type yang:counter64;
                        description "Number of inbound packets marked as red by traffic class 0.";
                    }

                    leaf traffic-class-0-policer-count-yellow {
                        type yang:counter64;
                        description "Number of inbound packets marked as yellow by traffic class 0.";
                    }

                    leaf traffic-class-0-policer-count-green {
                        type yang:counter64;
                        description "Number of inbound packets marked as green by traffic class 0.";
                    }

                    leaf traffic-class-0-policer-count-rered {
                        type yang:counter64;
                        description "Number of inbound packets reclassified as red by traffic class 0.";
                    }

                    leaf traffic-class-0-policer-count-reyellow {
                        type yang:counter64;
                        description "Number of inbound packets reclassified as yellow by traffic class 0.";
                    }

                    leaf traffic-class-1-policer-count-red {
                        type yang:counter64;
                        description "Number of inbound packets marked as red by traffic class 1.";
                    }

                    leaf traffic-class-1-policer-count-yellow {
                        type yang:counter64;
                        description "Number of inbound packets marked as yellow by traffic class 1.";
                    }

                    leaf traffic-class-1-policer-count-green {
                        type yang:counter64;
                        description "Number of inbound packets marked as green by traffic class 1.";
                    }

                    leaf traffic-class-1-policer-count-rered {
                        type yang:counter64;
                        description "Number of inbound packets reclassified as red by traffic class 1.";
                    }

                    leaf traffic-class-1-policer-count-reyellow {
                        type yang:counter64;
                        description "Number of inbound packets reclassified as yellow by traffic class 1.";
                    }

                    leaf traffic-class-2-policer-count-red {
                        type yang:counter64;
                        description "Number of inbound packets marked as red by traffic class 2.";
                    }

                    leaf traffic-class-2-policer-count-yellow {
                        type yang:counter64;
                        description "Number of inbound packets marked as yellow by traffic class 2.";
                    }

                    leaf traffic-class-2-policer-count-green {
                        type yang:counter64;
                        description "Number of inbound packets marked as green by traffic class 2.";
                    }

                    leaf traffic-class-2-policer-count-rered {
                        type yang:counter64;
                        description "Number of inbound packets reclassified as red by traffic class 2.";
                    }

                    leaf traffic-class-2-policer-count-reyellow {
                        type yang:counter64;
                        description "Number of inbound packets reclassified as yellow by traffic class 2.";
                    }

                    leaf traffic-class-3-policer-count-red {
                        type yang:counter64;
                        description "Number of inbound packets marked as red by traffic class 3.";
                    }

                    leaf traffic-class-3-policer-count-yellow {
                        type yang:counter64;
                        description "Number of inbound packets marked as yellow by traffic class 3.";
                    }

                    leaf traffic-class-3-policer-count-green {
                        type yang:counter64;
                        description "Number of inbound packets marked as green by traffic class 3.";
                    }

                    leaf traffic-class-3-policer-count-rered {
                        type yang:counter64;
                        description "Number of inbound packets reclassified as red by traffic class 3.";
                    }

                    leaf traffic-class-3-policer-count-reyellow {
                        type yang:counter64;
                        description "Number of inbound packets reclassified as yellow by traffic class 3.";
                    }

                    leaf traffic-class-4-policer-count-red {
                        type yang:counter64;
                        description "Number of inbound packets marked as red by traffic class 4.";
                    }

                    leaf traffic-class-4-policer-count-yellow {
                        type yang:counter64;
                        description "Number of inbound packets marked as yellow by traffic class 4.";
                    }

                    leaf traffic-class-4-policer-count-green {
                        type yang:counter64;
                        description "Number of inbound packets marked as green by traffic class 4.";
                    }

                    leaf traffic-class-4-policer-count-rered {
                        type yang:counter64;
                        description "Number of inbound packets reclassified as red by traffic class 4.";
                    }

                    leaf traffic-class-4-policer-count-reyellow {
                        type yang:counter64;
                        description "Number of inbound packets reclassified as yellow by traffic class 4.";
                    }

                    leaf traffic-class-5-policer-count-red {
                        type yang:counter64;
                        description "Number of inbound packets marked as red by traffic class 5.";
                    }

                    leaf traffic-class-5-policer-count-yellow {
                        type yang:counter64;
                        description "Number of inbound packets marked as yellow by traffic class 5.";
                    }

                    leaf traffic-class-5-policer-count-green {
                        type yang:counter64;
                        description "Number of inbound packets marked as green by traffic class 5.";
                    }

                    leaf traffic-class-5-policer-count-rered {
                        type yang:counter64;
                        description "Number of inbound packets reclassified as red by traffic class 5.";
                    }

                    leaf traffic-class-5-policer-count-reyellow {
                        type yang:counter64;
                        description "Number of inbound packets reclassified as yellow by traffic class 5.";
                    }

                    leaf traffic-class-6-policer-count-red {
                        type yang:counter64;
                        description "Number of inbound packets marked as red by traffic class 6.";
                    }

                    leaf traffic-class-6-policer-count-yellow {
                        type yang:counter64;
                        description "Number of inbound packets marked as yellow by traffic class 6.";
                    }

                    leaf traffic-class-6-policer-count-green {
                        type yang:counter64;
                        description "Number of inbound packets marked as green by traffic class 6.";
                    }

                    leaf traffic-class-6-policer-count-rered {
                        type yang:counter64;
                        description "Number of inbound packets reclassified as red by traffic class 6.";
                    }

                    leaf traffic-class-6-policer-count-reyellow {
                        type yang:counter64;
                        description "Number of inbound packets reclassified as yellow by traffic class 6.";
                    }

                    leaf traffic-class-7-policer-count-red {
                        type yang:counter64;
                        description "Number of inbound packets marked as red by traffic class 7.";
                    }

                    leaf traffic-class-7-policer-count-yellow {
                        type yang:counter64;
                        description "Number of inbound packets marked as yellow by traffic class 7.";
                    }

                    leaf traffic-class-7-policer-count-green {
                        type yang:counter64;
                        description "Number of inbound packets marked as green by traffic class 7.";
                    }

                    leaf traffic-class-7-policer-count-rered {
                        type yang:counter64;
                        description "Number of inbound packets reclassified as red by traffic class 7.";
                    }

                    leaf traffic-class-7-policer-count-reyellow {
                        type yang:counter64;
                        description "Number of inbound packets reclassified as yellow by traffic class 7.";
                    }

                } // list statistics

            } // container input-output

            list oversubscribed-resource {
                key "resource-type";
                description "Enter the oversubscribed-resource list instance";

                leaf resource-type {
                    type enumeration {
                        enum sram-buf                       { value 1; }
                        enum sram-pdb                       { value 2; }
                        enum dram-bdb                       { value 3; }
                        enum dram-bandwidth                 { value 4; }
                        enum core-process-pipeline          { value 5; }
                        enum mesh-fabric-bandwidth          { value 6; }
                    }
                    description "Specifies the FP resource which may be oversubscribed.";
                }

                leaf detected {
                    type uint32;
                    description
                        "Indicates the number of seconds it has been detected that the resource
                         has been oversubscribed.";
                }

            } // list oversubscribed-resource

            container statistics {
                description "Enter the statistics context";

                leaf ingress-fcs-error {
                    type yang:counter32;
                    description
                        "Indicates the number of times the complex experienced a FCS
                         error in the ingress direction since startup, last clear,
                         or card reboot.";
                }

                leaf ingress-fcs-error-time {
                    type yang:date-and-time;
                    description "Indicates the last time ingress-fcs-error incremented.";
                }

                leaf egress-fcs-error {
                    type yang:counter32;
                    description
                        "Indicates the number of times the complex experienced a FCS
                         error in the egress direction since startup, last clear, or
                         card reboot.";
                }

                leaf egress-fcs-error-time {
                    type yang:date-and-time;
                    description "Indicates the last time egress-fcs-error incremented.";
                }

                leaf memory-parity-error {
                    type yang:counter32;
                    description
                        "Indicates the number of times the complex experienced a memory
                         parity error since startup, last clear, or card reboot.";
                }

                leaf memory-parity-error-time {
                    type yang:date-and-time;
                    description "Indicates the last time memory-parity-error incremented.";
                }

                leaf cam-error {
                    type yang:counter32;
                    description
                        "Indicates the number of times the complex experienced a CAM
                         error since startup, last clear, or card reboot.";
                }

                leaf cam-error-time {
                    type yang:date-and-time;
                    description "Indicates the last time cam-error incremented.";
                }

                leaf buffer-memory-error {
                    type yang:counter32;
                    description
                        "Indicates the number of times the complex experienced a buffer
                         memory error since startup, last clear, or card reboot.";
                }

                leaf buffer-memory-error-time {
                    type yang:date-and-time;
                    description "Indicates the last time buffer-memory-error incremented.";
                }

                leaf statistics-memory-error {
                    type yang:counter32;
                    description
                        "Indicates the number of times the complex experienced a
                         statistics memory error since startup, last clear, or card
                         reboot.";
                }

                leaf statistics-memory-error-time {
                    type yang:date-and-time;
                    description "Indicates the last time statistics-memory-error incremented.";
                }

                leaf internal-memory-error {
                    type yang:counter32;
                    description
                        "Indicates the number of times the complex experienced an
                         internal memory error since startup, last clear, or card
                         reboot.";
                }

                leaf internal-memory-error-time {
                    type yang:date-and-time;
                    description "Indicates the last time internal-memory-error incremented.";
                }

                leaf internal-datapath-error {
                    type yang:counter32;
                    description
                        "Indicates the number of times the complex experienced an
                         internal datapath error since startup, last clear, or card
                         reboot.";
                }

                leaf internal-datapath-error-time {
                    type yang:date-and-time;
                    description "Indicates the last time internal-datapath-error incremented.";
                }

                leaf internal-datapath-cell-error {
                    type yang:counter32;
                    description
                        "Indicates the number of times the complex experienced an
                         internal datapath cell error since startup, last clear, or
                         card reboot.";
                }

                leaf internal-datapath-cell-error-time {
                    type yang:date-and-time;
                    description
                        "Indicates the last time internal-datapath-cell-error
                         incremented.";
                }

                leaf source-slots-egress-fcs-error {
                    type types-card:card-slot-bitmap;
                    description
                        "Indicates the source slots reported from the last time
                         egress-fcs-error incremented.";
                }

                leaf egress-encap-exceeded {
                    type yang:counter64;
                    units "packets";
                    description
                        "Addition of egress encapsulation headers would have exceeded
                         the maximum frame size.";
                }

                leaf egress-mtu-exceeded {
                    type yang:counter64;
                    units "packets";
                    description
                        "Protocol supports packet fragmentation but fragmentation was
                         blocked (for example packet is IPv6 or packet is IPv4 and DF
                         set to one).";
                }

                leaf egress-frame-too-big-for-port {
                    type yang:counter64;
                    units "packets";
                    description
                        "Final check before transmitting has detected frame exceeded
                         the port MTU.";
                }

                leaf tchip-parity-error {
                    type yang:counter32;
                    description
                        "Indicates the number of times the TChip experienced a
                         parity error since startup, last clear, or card reboot.";
                }

                leaf tchip-parity-error-time {
                    type yang:date-and-time;
                    description "Indicates the last time tchip-parity-error incremented.";
                }

            } // container statistics

            container resource-usage {
                description "Enter the resource-usage context";

                leaf resource-oversubscribed {
                    type bits {
                        bit sram-buf                       { position 0; }
                        bit sram-pdb                       { position 1; }
                        bit dram-bdb                       { position 2; }
                        bit dram-bandwidth                 { position 3; }
                        bit core-processing-pipeline       { position 4; }
                        bit mesh-fabric-bandwidth          { position 5; }
                    }
                    description
                        "Indicates which resources are oversubscribed on this FP.
                         When no bits are set, none of the FP's resources are exhausted.";
                }

                container sap-ingress-qos-policies {
                    description "Enter the sap-ingress-qos-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container sap-ingress-qos-policies

                container dynamic-egress-classification {
                    description "Enter the dynamic-egress-classification context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-sap-egress {
                        description "Enter the in-use-by-sap-egress context";

                        leaf allocated {
                            type yang:counter32;
                            description "The total number of resources that are currently allocated on this FP.";
                        }

                    } // container in-use-by-sap-egress

                    container in-use-by-network-egress {
                        description "Enter the in-use-by-network-egress context";

                        leaf allocated {
                            type yang:counter32;
                            description "The total number of resources that are currently allocated on this FP.";
                        }

                    } // container in-use-by-network-egress

                } // container dynamic-egress-classification

                container ingress-queues {
                    description "Enter the ingress-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-queues

                container egress-queues {
                    description "Enter the egress-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-queues

                container ingress-policers {
                    description "Enter the ingress-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-policers

                container ingress-policer-stat-entries {
                    description "Enter the ingress-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-policer-stat-entries

                container egress-policers {
                    description "Enter the egress-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-policers

                container egress-policer-stat-entries {
                    description "Enter the egress-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-policer-stat-entries

                container qos-ingress-root-arbiters {
                    description "Enter the qos-ingress-root-arbiters context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container qos-ingress-root-arbiters

                container qos-egress-root-arbiters {
                    description "Enter the qos-egress-root-arbiters context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container qos-egress-root-arbiters

                container egress-qos-bypass {
                    description "Enter the egress-qos-bypass context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-qos-bypass

                container dynamic-queues {
                    description "Enter the dynamic-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-queues

                container dynamic-policers {
                    description "Enter the dynamic-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-policers

                container dynamic-policer-stat-entries {
                    description "Enter the dynamic-policer-stat-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container in-use-by-ingress {
                        description "Enter the in-use-by-ingress context";

                        leaf allocated {
                            type yang:counter32;
                            description "The total number of resources that are currently allocated on this FP.";
                        }

                    } // container in-use-by-ingress

                    container in-use-by-egress {
                        description "Enter the in-use-by-egress context";

                        leaf allocated {
                            type yang:counter32;
                            description "The total number of resources that are currently allocated on this FP.";
                        }

                    } // container in-use-by-egress

                } // container dynamic-policer-stat-entries

                container egress-user-queues {
                    description "Enter the egress-user-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-user-queues

                container egress-user-policers {
                    description "Enter the egress-user-policers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-user-policers

                container ingress-ip-acl-qos-entries {
                    status obsolete;
                    description "Enter the ingress-ip-acl-qos-entries context";

                    leaf total {
                        status obsolete;
                        type yang:counter32;
                        description "The total number of resources supported on this FP.";
                    }

                    leaf allocated {
                        status obsolete;
                        type yang:counter32;
                        description "The total number of resources that are currently allocated on this FP.";
                    }

                    leaf free {
                        status obsolete;
                        type yang:counter32;
                        description "The total number of resources that are remaining free on this FP.";
                    }

                } // container ingress-ip-acl-qos-entries

                container ingress-ip-filter-entries {
                    description "Enter the ingress-ip-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-filter-entries

                container ingress-ip-qos-entries {
                    description "Enter the ingress-ip-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-qos-entries

                container ingress-ipv6-filter-entries {
                    description "Enter the ingress-ipv6-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-filter-entries

                container ingress-ipv6-qos-entries {
                    description "Enter the ingress-ipv6-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-qos-entries

                container egress-ip-acl-qos-entries {
                    status obsolete;
                    description "Enter the egress-ip-acl-qos-entries context";

                    leaf total {
                        status obsolete;
                        type yang:counter32;
                        description "The total number of resources supported on this FP.";
                    }

                    leaf allocated {
                        status obsolete;
                        type yang:counter32;
                        description "The total number of resources that are currently allocated on this FP.";
                    }

                    leaf free {
                        status obsolete;
                        type yang:counter32;
                        description "The total number of resources that are remaining free on this FP.";
                    }

                } // container egress-ip-acl-qos-entries

                container egress-ip-filter-entries {
                    description "Enter the egress-ip-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-filter-entries

                container egress-ip-qos-entries {
                    description "Enter the egress-ip-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-qos-entries

                container egress-ipv6-filter-entries {
                    description "Enter the egress-ipv6-filter-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-filter-entries

                container egress-ipv6-qos-entries {
                    description "Enter the egress-ipv6-qos-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-qos-entries

                container ingress-ip-filter-policies {
                    description "Enter the ingress-ip-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ip-filter-policies

                container ingress-ipv6-filter-policies {
                    description "Enter the ingress-ipv6-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container ingress-ipv6-filter-policies

                container egress-ip-filter-policies {
                    description "Enter the egress-ip-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ip-filter-policies

                container egress-ipv6-filter-policies {
                    description "Enter the egress-ipv6-filter-policies context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-ipv6-filter-policies

                container sap-ingqgrp-redirlst-entries {
                    description "Enter the sap-ingqgrp-redirlst-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container sap-ingqgrp-redirlst-entries

                container dynamic-service-entries {
                    description "Enter the dynamic-service-entries context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container encap-group-members {
                        description "Enter the encap-group-members context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container encap-group-members

                    container egress-network-queue-group-mappings {
                        description "Enter the egress-network-queue-group-mappings context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container egress-network-queue-group-mappings

                    container sapinst-egrqgrp-redirlst-entries {
                        description "Enter the sapinst-egrqgrp-redirlst-entries context";

                        leaf total {
                            type yang:counter32;
                            description "The total number of resources supported on this FP.";
                        }

                        leaf allocated {
                            type yang:counter32;
                            description "The total number of resources that are currently allocated on this FP.";
                        }

                        leaf free {
                            type yang:counter32;
                            description "The total number of resources that are remaining free on this FP.";
                        }

                    } // container sapinst-egrqgrp-redirlst-entries

                } // container dynamic-service-entries

                container dynamic-wred-pools {
                    description "Enter the dynamic-wred-pools context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container dynamic-wred-pools

                container egress-hs-turbo-queue-group {
                    description "Enter the egress-hs-turbo-queue-group context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-hs-turbo-queue-group

                container egress-hs-queue-group {
                    description "Enter the egress-hs-queue-group context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container egress-hs-queue-group

                container hs-primary-shapers {
                    description "Enter the hs-primary-shapers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                    container hs-explicit-primary-shapers {
                        description "Enter the hs-explicit-primary-shapers context";

                        leaf allocated {
                            type yang:counter32;
                            description "The total number of resources that are currently allocated on this FP";
                        }

                    } // container hs-explicit-primary-shapers

                    container hs-managed-primary-shapers {
                        description "Enter the hs-managed-primary-shapers context";

                        leaf allocated {
                            type yang:counter32;
                            description "The total number of resources that are currently allocated on this FP";
                        }

                    } // container hs-managed-primary-shapers

                } // container hs-primary-shapers

                container hs-secondary-shapers {
                    description "Enter the hs-secondary-shapers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container hs-secondary-shapers

                container fast-depth-monitored-queues {
                    description "Enter the fast-depth-monitored-queues context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container fast-depth-monitored-queues

                container assigned-non-shaper-queues {
                    description "Enter the assigned-non-shaper-queues context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container assigned-non-shaper-queues

                container hw-aggregate-shaper-qset-size1 {
                    status obsolete;
                    description "Enter the hw-aggregate-shaper-qset-size1 context";

                    leaf total {
                        status obsolete;
                        type yang:counter32;
                        description "The total number of resources supported on this FP.";
                    }

                    leaf allocated {
                        status obsolete;
                        type yang:counter32;
                        description "The total number of resources that are currently allocated on this FP.";
                    }

                    leaf free {
                        status obsolete;
                        type yang:counter32;
                        description "The total number of resources that are remaining free on this FP.";
                    }

                } // container hw-aggregate-shaper-qset-size1

                container hw-aggregate-shaper-qset-size2 {
                    description "Enter the hw-aggregate-shaper-qset-size2 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size2

                container hw-aggregate-shaper-qset-size3 {
                    description "Enter the hw-aggregate-shaper-qset-size3 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size3

                container hw-aggregate-shaper-qset-size4 {
                    description "Enter the hw-aggregate-shaper-qset-size4 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size4

                container hw-aggregate-shaper-qset-size5 {
                    description "Enter the hw-aggregate-shaper-qset-size5 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size5

                container hw-aggregate-shaper-qset-size6 {
                    description "Enter the hw-aggregate-shaper-qset-size6 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size6

                container hw-aggregate-shaper-qset-size7 {
                    description "Enter the hw-aggregate-shaper-qset-size7 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size7

                container hw-aggregate-shaper-qset-size8 {
                    description "Enter the hw-aggregate-shaper-qset-size8 context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shaper-qset-size8

                container hw-aggregate-shapers {
                    description "Enter the hw-aggregate-shapers context";

                    leaf total {
                        type yang:counter32;
                        description "The total number of resources.";
                    }

                    leaf allocated {
                        type yang:counter32;
                        description "The number of resources that are currently allocated.";
                    }

                    leaf free {
                        type yang:counter32;
                        description "The number of free resources that are currently available.";
                    }

                } // container hw-aggregate-shapers

                container hw-aggregate-shaper-schedulers {
                    description "Enter the hw-aggregate-shaper-schedulers context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container hw-aggregate-shaper-schedulers

                container hw-aggregate-shaper-qset-size {
                    status obsolete;
                    description "Enter the hw-aggregate-shaper-qset-size context";

                    leaf total {
                        status obsolete;
                        type yang:counter32;
                        description "The total number of resources supported on this FP.";
                    }

                    leaf allocated {
                        status obsolete;
                        type yang:counter32;
                        description "The total number of resources that are currently allocated on this FP.";
                    }

                    leaf free {
                        status obsolete;
                        type yang:counter32;
                        description "The total number of resources that are remaining free on this FP.";
                    }

                } // container hw-aggregate-shaper-qset-size

                container hw-aggregate-shaper-def-qset-size {
                    description "Enter the hw-aggregate-shaper-def-qset-size context";

                    leaf saps {
                        type uint32;
                        description
                            "The default queue set size for this sap on this FP when
                             hardware aggregate shaper is enabled";
                    }

                    leaf subscribers {
                        type uint32;
                        description
                            "The default queue set size for this subscribers on this FP when
                             hardware aggregate shaper is enabled";
                    }

                    leaf queue-groups {
                        type uint32;
                        description
                            "The default queue set size for this queue groups on this FP when
                             hardware aggregate shaper is enabled";
                    }

                } // container hw-aggregate-shaper-def-qset-size

                container fdb {
                    description "Enter the fdb context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container fdb

                container port-forwarding-ids {
                    description "Enter the port-forwarding-ids context";

                    leaf total {
                        type yang:counter32;
                        description "The total number of resources supported on this FP.";
                    }

                    leaf allocated {
                        type yang:counter32;
                        description "The total number of resources that are currently allocated on this FP.";
                    }

                    leaf free {
                        type yang:counter32;
                        description "The total number of resources that are remaining free on this FP.";
                    }

                } // container port-forwarding-ids

                container ixr {
                    description "Enter the ixr context";

                    container egress-global-lif-map {
                        description "Enter the egress-global-lif-map context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                    } // container egress-global-lif-map

                    container large-exact-match {
                        description "Enter the large-exact-match context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                    } // container large-exact-match

                    container large-exact-match-1 {
                        description "Enter the large-exact-match-1 context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                    } // container large-exact-match-1

                    container large-exact-match-2 {
                        description "Enter the large-exact-match-2 context";

                        leaf total {
                            type yang:counter32;
                            description "The total number of resources.";
                        }

                        leaf allocated {
                            type yang:counter32;
                            description "The number of resources that are currently allocated.";
                        }

                        leaf free {
                            type yang:counter32;
                            description "The number of free resources that are currently available.";
                        }

                    } // container large-exact-match-2

                    container ingress-decapsulation {
                        description "Enter the ingress-decapsulation context";

                        container ingress-termination-a {
                            description "Enter the ingress-termination-a context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // container ingress-termination-a

                        container ingress-termination-b {
                            description "Enter the ingress-termination-b context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // container ingress-termination-b

                        container ingress-endpoint-1 {
                            description "Enter the ingress-endpoint-1 context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // container ingress-endpoint-1

                        container ingress-endpoint-2 {
                            description "Enter the ingress-endpoint-2 context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // container ingress-endpoint-2

                        container ingress-endpoint-3 {
                            description "Enter the ingress-endpoint-3 context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                        } // container ingress-endpoint-3

                    } // container ingress-decapsulation

                    container egress-encapsulation {
                        description "Enter the egress-encapsulation context";

                        container banks {
                            description "Enter the banks context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            container routed {
                                description "Enter the routed context";

                                leaf allocated {
                                    type yang:counter32;
                                    description "The number of resources that are currently allocated.";
                                }

                            } // container routed

                            container tdm {
                                description "Enter the tdm context";

                                leaf allocated {
                                    type yang:counter32;
                                    description "The number of resources that are currently allocated.";
                                }

                            } // container tdm

                            container port-vlan-translation {
                                description "Enter the port-vlan-translation context";

                                leaf allocated {
                                    type yang:counter32;
                                    description "The number of resources that are currently allocated.";
                                }

                            } // container port-vlan-translation

                            container arp {
                                description "Enter the arp context";

                                leaf allocated {
                                    type yang:counter32;
                                    description "The number of resources that are currently allocated.";
                                }

                            } // container arp

                            container label-push {
                                description "Enter the label-push context";

                                leaf allocated {
                                    type yang:counter32;
                                    description "The number of resources that are currently allocated.";
                                }

                            } // container label-push

                            container label-swap-push {
                                description "Enter the label-swap-push context";

                                leaf allocated {
                                    type yang:counter32;
                                    description "The number of resources that are currently allocated.";
                                }

                            } // container label-swap-push

                            container port-vlan-translation-ext {
                                description "Enter the port-vlan-translation-ext context";

                                leaf allocated {
                                    type yang:counter32;
                                    description "The number of resources that are currently allocated.";
                                }

                            } // container port-vlan-translation-ext

                            container arp-ext {
                                description "Enter the arp-ext context";

                                leaf allocated {
                                    type yang:counter32;
                                    description "The number of resources that are currently allocated.";
                                }

                            } // container arp-ext

                            container label-push-ext {
                                description "Enter the label-push-ext context";

                                leaf allocated {
                                    type yang:counter32;
                                    description "The number of resources that are currently allocated.";
                                }

                            } // container label-push-ext

                            container label-swap-push-ext {
                                description "Enter the label-swap-push-ext context";

                                leaf allocated {
                                    type yang:counter32;
                                    description "The number of resources that are currently allocated.";
                                }

                            } // container label-swap-push-ext

                        } // container banks

                        container entries {
                            description "Enter the entries context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            container routed {
                                description "Enter the routed context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container routed

                            container tdm {
                                description "Enter the tdm context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container tdm

                            container port-vlan-translation {
                                description "Enter the port-vlan-translation context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container port-vlan-translation

                            container arp {
                                description "Enter the arp context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container arp

                            container label-push {
                                description "Enter the label-push context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-push

                            container label-swap-push {
                                description "Enter the label-swap-push context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-swap-push

                            container port-vlan-translation-ext {
                                description "Enter the port-vlan-translation-ext context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container port-vlan-translation-ext

                            container arp-ext {
                                description "Enter the arp-ext context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container arp-ext

                            container label-push-ext {
                                description "Enter the label-push-ext context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-push-ext

                            container label-swap-push-ext {
                                description "Enter the label-swap-push-ext context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-swap-push-ext

                        } // container entries

                        list cluster {
                            key "set";
                            description "Enter the cluster list instance";

                            leaf set {
                                type enumeration {
                                    enum set-0                          { value 0; }
                                    enum set-1                          { value 1; }
                                    enum set-2                          { value 2; }
                                    enum set-3                          { value 3; }
                                    enum set-4                          { value 4; }
                                    enum none                           { value 9999; }
                                }
                                description
                                    "A Set is a group of Cluster or Link-List Banks. A Set of Cluster or Link-List
                                     Banks are associated with Phases";
                            }

                            container banks {
                                description "Enter the banks context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container banks

                            list phase {
                                key "phase";
                                description "Enter the phase list instance";

                                leaf phase {
                                    type enumeration {
                                        enum phase-1                        { value 1; }
                                        enum phase-2                        { value 2; }
                                        enum phase-3                        { value 3; }
                                        enum phase-4                        { value 4; }
                                        enum phase-5                        { value 5; }
                                        enum phase-6                        { value 6; }
                                        enum phase-7                        { value 7; }
                                        enum phase-8                        { value 8; }
                                    }
                                    description
                                        "A Phase is a stage in the egress processing pipeline. Each Phase can use
                                         a particular Set or Sets of Clusters and Link-Lists Banks. A Set of Clusters
                                         and Link-Lists Banks can be shared between Phases.";
                                }

                                container banks {
                                    description "Enter the banks context";

                                    leaf total {
                                        type yang:counter32;
                                        description "The total number of resources.";
                                    }

                                    leaf allocated {
                                        type yang:counter32;
                                        description "The number of resources that are currently allocated.";
                                    }

                                    leaf free {
                                        type yang:counter32;
                                        description "The number of free resources that are currently available.";
                                    }

                                } // container banks

                                container linked-data {
                                    description "Enter the linked-data context";

                                    leaf available-lifs {
                                        type types-card:ixr-resource-fp-available-lifs;
                                        description "Shows the available LIF types for the given Cluster Set.";
                                    }

                                    container banks {
                                        description "Enter the banks context";

                                        leaf allocated {
                                            type yang:counter32;
                                            description "The number of resources that are currently allocated.";
                                        }

                                    } // container banks

                                    container entries {
                                        description "Enter the entries context";

                                        leaf total {
                                            type yang:counter32;
                                            description "The total number of resources.";
                                        }

                                        leaf allocated {
                                            type yang:counter32;
                                            description "The number of resources that are currently allocated.";
                                        }

                                        leaf free {
                                            type yang:counter32;
                                            description "The number of free resources that are currently available.";
                                        }

                                    } // container entries

                                } // container linked-data

                                container non-linked-data {
                                    description "Enter the non-linked-data context";

                                    leaf available-lifs {
                                        type types-card:ixr-resource-fp-available-lifs;
                                        description "Shows the available LIF types for the given Cluster Set.";
                                    }

                                    container banks {
                                        description "Enter the banks context";

                                        leaf allocated {
                                            type yang:counter32;
                                            description "The number of resources that are currently allocated.";
                                        }

                                    } // container banks

                                    container entries {
                                        description "Enter the entries context";

                                        leaf total {
                                            type yang:counter32;
                                            description "The total number of resources.";
                                        }

                                        leaf allocated {
                                            type yang:counter32;
                                            description "The number of resources that are currently allocated.";
                                        }

                                        leaf free {
                                            type yang:counter32;
                                            description "The number of free resources that are currently available.";
                                        }

                                    } // container entries

                                } // container non-linked-data

                            } // list phase

                        } // list cluster

                        list link-list {
                            key "set";
                            description "Enter the link-list list instance";

                            leaf set {
                                type enumeration {
                                    enum set-0                          { value 0; }
                                    enum set-1                          { value 1; }
                                    enum set-2                          { value 2; }
                                    enum set-3                          { value 3; }
                                    enum set-4                          { value 4; }
                                    enum none                           { value 9999; }
                                }
                                description
                                    "A Set is a group of Cluster or Link-List Banks. A Set of Cluster or Link-List
                                     Banks are associated with Phases";
                            }

                            container banks {
                                description "Enter the banks context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container banks

                            list phase {
                                key "phase";
                                description "Enter the phase list instance";

                                leaf phase {
                                    type enumeration {
                                        enum phase-1                        { value 1; }
                                        enum phase-2                        { value 2; }
                                        enum phase-3                        { value 3; }
                                        enum phase-4                        { value 4; }
                                        enum phase-5                        { value 5; }
                                        enum phase-6                        { value 6; }
                                        enum phase-7                        { value 7; }
                                        enum phase-8                        { value 8; }
                                    }
                                    description
                                        "A Phase is a stage in the egress processing pipeline. Each Phase can use
                                         a particular Set or Sets of Clusters and Link-Lists Banks. A Set of Clusters
                                         and Link-Lists Banks can be shared between Phases.";
                                }

                                container linked-data {
                                    description "Enter the linked-data context";

                                    container banks {
                                        description "Enter the banks context";

                                        leaf allocated {
                                            type yang:counter32;
                                            description "The number of resources that are currently allocated.";
                                        }

                                    } // container banks

                                    container entries {
                                        description "Enter the entries context";

                                        leaf total {
                                            type yang:counter32;
                                            description "The total number of resources.";
                                        }

                                        leaf allocated {
                                            type yang:counter32;
                                            description "The number of resources that are currently allocated.";
                                        }

                                        leaf free {
                                            type yang:counter32;
                                            description "The number of free resources that are currently available.";
                                        }

                                    } // container entries

                                } // container linked-data

                                container non-linked-data {
                                    description "Enter the non-linked-data context";

                                    container banks {
                                        description "Enter the banks context";

                                        leaf allocated {
                                            type yang:counter32;
                                            description "The number of resources that are currently allocated.";
                                        }

                                    } // container banks

                                    container entries {
                                        description "Enter the entries context";

                                        leaf total {
                                            type yang:counter32;
                                            description "The total number of resources.";
                                        }

                                        leaf allocated {
                                            type yang:counter32;
                                            description "The number of resources that are currently allocated.";
                                        }

                                        leaf free {
                                            type yang:counter32;
                                            description "The number of free resources that are currently available.";
                                        }

                                    } // container entries

                                } // container non-linked-data

                                container linked-list {
                                    description "Enter the linked-list context";

                                    container banks {
                                        description "Enter the banks context";

                                        leaf allocated {
                                            type yang:counter32;
                                            description "The number of resources that are currently allocated.";
                                        }

                                    } // container banks

                                    container entries {
                                        description "Enter the entries context";

                                        leaf total {
                                            type yang:counter32;
                                            description "The total number of resources.";
                                        }

                                        leaf allocated {
                                            type yang:counter32;
                                            description "The number of resources that are currently allocated.";
                                        }

                                        leaf free {
                                            type yang:counter32;
                                            description "The number of free resources that are currently available.";
                                        }

                                    } // container entries

                                } // container linked-list

                            } // list phase

                        } // list link-list

                    } // container egress-encapsulation

                    container egress-encapsulation-extension {
                        description "Enter the egress-encapsulation-extension context";

                        container banks {
                            description "Enter the banks context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            container port-vlan-translation {
                                description "Enter the port-vlan-translation context";

                                leaf allocated {
                                    type yang:counter32;
                                    description "The number of resources that are currently allocated.";
                                }

                            } // container port-vlan-translation

                            container arp {
                                description "Enter the arp context";

                                leaf allocated {
                                    type yang:counter32;
                                    description "The number of resources that are currently allocated.";
                                }

                            } // container arp

                            container label-push {
                                description "Enter the label-push context";

                                leaf allocated {
                                    type yang:counter32;
                                    description "The number of resources that are currently allocated.";
                                }

                            } // container label-push

                            container label-swap-push {
                                description "Enter the label-swap-push context";

                                leaf allocated {
                                    type yang:counter32;
                                    description "The number of resources that are currently allocated.";
                                }

                            } // container label-swap-push

                        } // container banks

                        container entries {
                            description "Enter the entries context";

                            leaf total {
                                type yang:counter32;
                                description "The total number of resources.";
                            }

                            leaf allocated {
                                type yang:counter32;
                                description "The number of resources that are currently allocated.";
                            }

                            leaf free {
                                type yang:counter32;
                                description "The number of free resources that are currently available.";
                            }

                            container port-vlan-translation {
                                description "Enter the port-vlan-translation context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container port-vlan-translation

                            container arp {
                                description "Enter the arp context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container arp

                            container label-push {
                                description "Enter the label-push context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-push

                            container label-swap-push {
                                description "Enter the label-swap-push context";

                                leaf total {
                                    type yang:counter32;
                                    description "The total number of resources.";
                                }

                                leaf allocated {
                                    type yang:counter32;
                                    description "The number of resources that are currently allocated.";
                                }

                                leaf free {
                                    type yang:counter32;
                                    description "The number of free resources that are currently available.";
                                }

                            } // container label-swap-push

                        } // container entries

                    } // container egress-encapsulation-extension

                } // container ixr

            } // container resource-usage

            list tap {
                key "tap-number";
                description "Enter the tap list instance";

                leaf tap-number {
                    type uint32 {
                        range "1..8";
                    }
                    description
                        "The unique value which uniquely identifies the tap number of the tap corresponding
                         to the forwarding plane within a specific IOM card in the system.";
                }

                container ingress {
                    description "Enter the ingress context";

                    list per-egress-dst {
                        key "dst-card-number dst-fp-number dst-tap-number";
                        description "Enter the per-egress-dst list instance";

                        leaf dst-card-number {
                            type types-card:iom-card-slot;
                            description "The unique value which identifies this destination IOM slot within a chassis in the system.";
                        }

                        leaf dst-fp-number {
                            type uint32 {
                                range "1..12";
                            }
                            description
                                "The unique value which uniquely identifies the destination forwarding plane within
                                 a specific IOM card in the system.";
                        }

                        leaf dst-tap-number {
                            type uint32 {
                                range "1..8";
                            }
                            description
                                "The unique value which uniquely identifies the destination number of the tap corresponding
                                 to the forwarding plane within a specific IOM card in the system.";
                        }

                        container statistics {
                            description "Enter the statistics context";

                            leaf expedite-forwarded-packets {
                                type yang:counter64;
                                description "The number of expedited forwarded packets.";
                            }

                            leaf expedite-forwarded-octets {
                                type yang:counter64;
                                description "The number of expedited forwarded octets.";
                            }

                            leaf best-effort-forwarded-packets {
                                type yang:counter64;
                                description "The number of best effort forwarded packets.";
                            }

                            leaf best-effort-forwarded-octets {
                                type yang:counter64;
                                description "The number of best effort forwarded octets.";
                            }

                        } // container statistics

                    } // list per-egress-dst

                } // container ingress

            } // list tap

        } // list fp

    } // grouping state-card-fp

}
