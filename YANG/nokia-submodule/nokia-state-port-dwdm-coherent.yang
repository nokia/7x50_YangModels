submodule nokia-state-port-dwdm-coherent {

    yang-version "1.1";

    belongs-to nokia-state { prefix "state"; }

    import ietf-yang-types                { prefix "yang"; }
    import nokia-sros-yang-extensions     { prefix "sros-ext"; }
    import nokia-types-port               { prefix "types-port"; }

    sros-ext:sros-major-release "rel26";
    organization "Nokia";
    contact
        "Nokia SR OS Support
         Web: <http://www.nokia.com>";
    description
        "Nokia YANG Data model with operational state for dense wavelength division multiplexing coherent ports on SR OS based routers.

         Copyright 2016 Nokia. All rights reserved. Reproduction of this document
         is authorized on the condition that the foregoing copyright notice is included.

         This nokia-state-port-dwdm-coherent YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping state-port-dwdm-coherent {
        container coherent {
            description "Enter the coherent context";

            leaf current-alarms {
                type types-port:coherent-optical-alarm;
                description "Indicates the coherent optical alarms currently active on the port.";
            }

            leaf reported-alarms {
                type types-port:coherent-optical-alarm;
                description
                    "Indicates the monitored coherent optical alarms raised on the port.
                     This leaf reports any 'current-alarms' that respect what is configured
                     by 'report-alarm'.";
            }

            leaf defect-points {
                type types-port:coherent-optical-defect-point;
                description
                    "Indicates the coherent optical defect points currently active
                     on the port.";
            }

            leaf module-operating-channel {
                status obsolete;
                type types-port:optical-dwdm-extended-channel;
                description
                    "Indicates the DWDM ITU channel at which the coherent optical module
                     is operating.

                     This leaf was obsoleted in release 22.2.";
            }

            leaf module-state {
                type enumeration {
                    enum reset                          { value 0; }
                    enum init                           { value 1; }
                    enum low-power                      { value 2; }
                    enum high-power-up                  { value 3; }
                    enum high-power-down                { value 4; }
                    enum tx-off                         { value 5; }
                    enum tx-turn-off                    { value 6; }
                    enum tx-turn-on                     { value 7; }
                    enum ready                          { value 8; }
                    enum fault                          { value 9; }
                }
                description
                    "Indicates the state of the coherent optical module.

                     Values:
                         reset           - The MDIO (Management Data Input/Output) interface
                                           is held in a high impedance state and all module
                                           circuits are in low-power mode.
                         init            - The MDIO remains in high impedance and the module
                                           registers are initialized.
                         low-power       - All high-power consuming circuits are in their
                                           low-power condition.
                         high-power-up   - The module powers up all the functional circuitry
                                           and completes all required initialization of the
                                           module hardware.
                         high-power-down - The module powers down power-consuming circuitry
                                           that can be switched to a low-power state.
                         tx-off          - The transmitter is turned off, but all other
                                           parts of the module remain high powered and
                                           functional.
                         tx-turn-off     - The module turns off the network transmitter.
                         tx-turn-on      - The module enables the transmitter.
                         ready           - The module is in a steady-state, ready for
                                           passing data.
                         fault           - A module fault has occurred and as a result the
                                           module is put into its low-power mode.";
            }

            leaf module-tx-turn-up-states {
                type bits {
                    bit init                           { position 0; }
                    bit laser-turn-up                  { position 1; }
                    bit laser-ready-off                { position 2; }
                    bit laser-ready                    { position 3; }
                    bit modulator-converge             { position 4; }
                    bit output-power-adjust            { position 5; }
                }
                description
                    "Indicates the completed transmitted turn-up states of the coherent
                     optical module.

                     Values:
                         init                - The entry state, in which configuration of
                                               the transmitted path is performed.
                         laser-turn-up       - This state begins the process of tuning the
                                               transmitted laser and locking devices on the
                                               transmitted path.
                         laser-ready-off     - When the laser is ready for operation, but
                                               light emission is suppressed, this state is
                                               entered.
                         laser-ready         - This state brings the laser to full power and
                                               frequency lock.
                         modulator-converge  - This state enables the transmitted modulator
                                               driver and waits for convergence of the
                                               modulator automatic bias control loop.
                         output-power-adjust - This state sets and controls the transmitted
                                               output power using a VOA.";
            }

            leaf module-rx-turn-up-states {
                type bits {
                    bit init                           { position 0; }
                    bit laser-ready                    { position 1; }
                    bit wait-for-input                 { position 2; }
                    bit adc-signal                     { position 3; }
                    bit optical-lock                   { position 4; }
                    bit demod-lock                     { position 5; }
                }
                description
                    "Indicates the completed received turn-up states of the coherent
                     optical module.

                     Values:
                         init           - The entry state, in which configuration of the RX
                                          path is performed.
                         laser-ready    - The RX LO (Local Oscillator) laser is tuned.
                         wait-for-input - The RX input tap is monitored for power that
                                          exceeds the LOS threshold.
                         adc-signal     - When RX input power above LOS is detected, the
                                          module transitions to the ADC Signal
                                          (Analog-to-Digital Converter Signal) state. In the
                                          ADC Signal state the module calibrates the
                                          optical ADCs.
                         optical-lock   - This state (and state demod-lock) reflects DSP
                                          operations by the demodulator.
                         demod-lock     - In this state, RX path turn-up is achieved.";
            }

            leaf rx-electrical-snr-x-polarization {
                type int32;
                units "centibels";
                description
                    "Indicates the network received electrical SNR (Signal-to-Noise Ratio)
                     of X polarization.";
            }

            leaf rx-electrical-snr-y-polarization {
                type int32;
                units "centibels";
                description
                    "Indicates the network received electrical SNR (Signal-to-Noise Ratio)
                     of Y polarization.";
            }

            leaf rx-quality-margin {
                type int32;
                units "centibels";
                description "Indicates the received quality margin.";
            }

            leaf rx-optical-snr-x-polarization {
                type int32;
                units "centibels";
                description
                    "Indicates the network received estimated optical SNR
                     (Signal-to-Noise Ratio) of X polarization.";
            }

            leaf rx-optical-snr-y-polarization {
                type int32;
                units "centibels";
                description
                    "Indicates the network received estimated optical SNR
                     (Signal-to-Noise Ratio) of Y polarization.";
            }

            container statistics {
                description "Enter the statistics context";

                leaf elapsed-seconds {
                    type yang:counter32;
                    units "seconds";
                    description
                        "Indicates the number of elapsed seconds since the start of
                         coherent optical stats collection after the last port
                         statistics cleared.";
                }

                container received {
                    description "Enter the received context";

                    container bit-error-rate {
                        description "Enter the bit-error-rate context";

                        leaf current {
                            type decimal64 {
                                fraction-digits 18;
                            }
                            description
                                "Indicates the current BER received since the last port statistics
                                 clear.";
                        }

                        leaf average {
                            type decimal64 {
                                fraction-digits 18;
                            }
                            description
                                "Indicates the average BER received since the last port statistics
                                 clear.";
                        }

                        leaf minimum {
                            type decimal64 {
                                fraction-digits 18;
                            }
                            description
                                "Indicates the minimum BER received since the last port statistics
                                 clear.";
                        }

                        leaf maximum {
                            type decimal64 {
                                fraction-digits 18;
                            }
                            description
                                "Indicates the maximum BER received since the last port statistics
                                 clear.";
                        }

                    } // container bit-error-rate

                    container electrical-signal-to-noise-ratio {
                        description "Enter the electrical-signal-to-noise-ratio context";

                        leaf current {
                            type yang:gauge32;
                            units "centibels";
                            description
                                "Indicates the current SNR received since the last port statistics
                                 clear.";
                        }

                        leaf average {
                            type yang:gauge32;
                            units "centibels";
                            description
                                "Indicates the average SNR received since the last port statistics
                                 clear.";
                        }

                        leaf minimum {
                            type yang:gauge32;
                            units "centibels";
                            description
                                "Indicates the minimum SNR received since the last port statistics
                                 clear.";
                        }

                        leaf maximum {
                            type yang:gauge32;
                            units "centibels";
                            description
                                "Indicates the maximum SNR received since the last port statistics
                                 clear.";
                        }

                    } // container electrical-signal-to-noise-ratio

                    container optical-signal-to-noise-ratio {
                        description "Enter the optical-signal-to-noise-ratio context";

                        leaf current {
                            type yang:gauge32;
                            units "centibels";
                            description
                                "Indicates the current SNR received since the last port statistics
                                 clear.";
                        }

                        leaf average {
                            type yang:gauge32;
                            units "centibels";
                            description
                                "Indicates the average SNR received since the last port statistics
                                 clear.";
                        }

                        leaf minimum {
                            type yang:gauge32;
                            units "centibels";
                            description
                                "Indicates the minimum SNR received since the last port statistics
                                 clear.";
                        }

                        leaf maximum {
                            type yang:gauge32;
                            units "centibels";
                            description
                                "Indicates the maximum SNR received since the last port statistics
                                 clear.";
                        }

                    } // container optical-signal-to-noise-ratio

                    container chromatic-dispersion {
                        description "Enter the chromatic-dispersion context";

                        leaf current {
                            type int32;
                            units "picoseconds per nanometer";
                            description
                                "Indicates the current chromatic dispersion received since the last port
                                 statistics clear.";
                        }

                        leaf average {
                            type int32;
                            units "picoseconds per nanometer";
                            description
                                "Indicates the average chromatic dispersion received since the last port
                                 statistics clear.";
                        }

                        leaf minimum {
                            type int32;
                            units "picoseconds per nanometer";
                            description
                                "Indicates the minimum chromatic dispersion received since the last port
                                 statistics clear.";
                        }

                        leaf maximum {
                            type int32;
                            units "picoseconds per nanometer";
                            description
                                "Indicates the maximum chromatic dispersion received since the last port
                                 statistics clear.";
                        }

                    } // container chromatic-dispersion

                    container differential-group-delay {
                        description "Enter the differential-group-delay context";

                        leaf current {
                            type yang:gauge32;
                            units "picoseconds";
                            description
                                "Indicates the current differential group delay received since the
                                 last port statistics clear.";
                        }

                        leaf average {
                            type yang:gauge32;
                            units "picoseconds";
                            description
                                "Indicates the average differential group delay received since the
                                 last port statistics clear.";
                        }

                        leaf minimum {
                            type yang:gauge32;
                            units "picoseconds";
                            description
                                "Indicates the minimum differential group delay received since the
                                 last port statistics clear.";
                        }

                        leaf maximum {
                            type yang:gauge32;
                            units "picoseconds";
                            description
                                "Indicates the maximum differential group delay received since the
                                 last port statistics clear.";
                        }

                    } // container differential-group-delay

                    container frequency-offset {
                        description "Enter the frequency-offset context";

                        leaf current {
                            type int32;
                            units "megahertz";
                            description
                                "Indicates the current frequency offset received since the
                                 last port statistics clear.";
                        }

                        leaf average {
                            type int32;
                            units "megahertz";
                            description
                                "Indicates the average frequency offset received since the
                                 last port statistics clear.";
                        }

                        leaf minimum {
                            type int32;
                            units "megahertz";
                            description
                                "Indicates the minimum frequency offset received since the
                                 last port statistics clear.";
                        }

                        leaf maximum {
                            type int32;
                            units "megahertz";
                            description
                                "Indicates the maximum frequency offset received since the
                                 last port statistics clear.";
                        }

                    } // container frequency-offset

                    container quality {
                        description "Enter the quality context";

                        leaf current {
                            type int32;
                            units "centibels";
                            description
                                "Indicates the current quality received since the last port statistics
                                 clear.";
                        }

                        leaf average {
                            type int32;
                            units "centibels";
                            description
                                "Indicates the average quality received since the last port statistics
                                 clear.";
                        }

                        leaf minimum {
                            type int32;
                            units "centibels";
                            description
                                "Indicates the minimum quality received since the last port statistics
                                 clear.";
                        }

                        leaf maximum {
                            type int32;
                            units "centibels";
                            description
                                "Indicates the maximum quality received since the last port statistics
                                 clear.";
                        }

                    } // container quality

                    container power {
                        description "Enter the power context";

                        leaf current {
                            type int32;
                            units "millibel-milliwatts";
                            description
                                "Indicates the current power received since the last port statistics
                                 clear. For supporting hardware, this indicates the per-channel power.";
                        }

                        leaf average {
                            type int32;
                            units "millibel-milliwatts";
                            description
                                "Indicates the average power received since the last port statistics
                                 clear. For supporting hardware, this indicates the per-channel power.";
                        }

                        leaf minimum {
                            type int32;
                            units "millibel-milliwatts";
                            description
                                "Indicates the minimum power received since the last port statistics
                                 clear. For supporting hardware, this indicates the per-channel power.";
                        }

                        leaf maximum {
                            type int32;
                            units "millibel-milliwatts";
                            description
                                "Indicates the maximum power received since the last port statistics
                                 clear. For supporting hardware, this indicates the per-channel power.";
                        }

                    } // container power

                    container total-power {
                        description "Enter the total-power context";

                        leaf current {
                            type int32;
                            units "millibel-milliwatts";
                            description
                                "Indicates the current total power received since the last port statistics
                                 clear.";
                        }

                        leaf average {
                            type int32;
                            units "millibel-milliwatts";
                            description
                                "Indicates the average total power received since the last port statistics
                                 clear.";
                        }

                        leaf minimum {
                            type int32;
                            units "millibel-milliwatts";
                            description
                                "Indicates the minimum total power received since the last port statistics
                                 clear.";
                        }

                        leaf maximum {
                            type int32;
                            units "millibel-milliwatts";
                            description
                                "Indicates the maximum total power received since the last port statistics
                                 clear.";
                        }

                    } // container total-power

                    container polarization-dependent-loss {
                        description "Enter the polarization-dependent-loss context";

                        leaf current {
                            type yang:gauge32;
                            units "centibels";
                            description
                                "Indicates the current Polarization Dependent Loss received since the last port
                                 statistics clear.";
                        }

                        leaf average {
                            type yang:gauge32;
                            units "centibels";
                            description
                                "Indicates the average Polarization Dependent Loss received since the last port
                                 statistics clear.";
                        }

                        leaf minimum {
                            type yang:gauge32;
                            units "centibels";
                            description
                                "Indicates the minimum Polarization Dependent Loss received since the last port
                                 statistics clear.";
                        }

                        leaf maximum {
                            type yang:gauge32;
                            units "centibels";
                            description
                                "Indicates the maximum Polarization Dependent Loss received since the last port
                                 statistics clear.";
                        }

                    } // container polarization-dependent-loss

                    container state-of-polarization-rate-of-change {
                        description "Enter the state-of-polarization-rate-of-change context";

                        leaf current {
                            type decimal64 {
                                fraction-digits 1;
                            }
                            units "kiloradians per second";
                            description
                                "Indicates the current State of Polarization Rate-of-Change received since the
                                 last port statistics clear.";
                        }

                        leaf average {
                            type decimal64 {
                                fraction-digits 1;
                            }
                            units "kiloradians per second";
                            description
                                "Indicates the average State of Polarization Rate-of-Change received since the
                                 last port statistics clear.";
                        }

                        leaf minimum {
                            type decimal64 {
                                fraction-digits 1;
                            }
                            units "kiloradians per second";
                            description
                                "Indicates the minimum State of Polarization Rate-of-Change received since the
                                 last port statistics clear.";
                        }

                        leaf maximum {
                            type decimal64 {
                                fraction-digits 1;
                            }
                            units "kiloradians per second";
                            description
                                "Indicates the maximum State of Polarization Rate-of-Change received since the
                                 last port statistics clear.";
                        }

                    } // container state-of-polarization-rate-of-change

                    container media-frame-error-count {
                        description "Enter the media-frame-error-count context";

                        leaf current {
                            type yang:gauge64;
                            description
                                "Indicates the current Media Frame Rate Error Count received since the
                                 last port statistics clear.";
                        }

                        leaf average {
                            type yang:gauge64;
                            description
                                "Indicates the average Media Frame Rate Error Count received since the
                                 last port statistics clear.";
                        }

                        leaf minimum {
                            type yang:gauge64;
                            description
                                "Indicates the minimum Media Frame Rate Error Count received since the
                                 last port statistics clear.";
                        }

                        leaf maximum {
                            type yang:gauge64;
                            description
                                "Indicates the maximum Media Frame Rate Error Count received since the
                                 last port statistics clear.";
                        }

                    } // container media-frame-error-count

                    container second-order-polarization-mode-dispersion {
                        description "Enter the second-order-polarization-mode-dispersion context";

                        leaf current {
                            type decimal64 {
                                fraction-digits 2;
                            }
                            units "picoseconds squared";
                            description
                                "Indicates the current Second Order Polarization Mode Dispersion
                                 received since the last port statistics clear.";
                        }

                        leaf average {
                            type decimal64 {
                                fraction-digits 2;
                            }
                            units "picoseconds squared";
                            description
                                "Indicates the average Second Order Polarization Mode Dispersion
                                 received since the last port statistics clear.";
                        }

                        leaf minimum {
                            type decimal64 {
                                fraction-digits 2;
                            }
                            units "picoseconds squared";
                            description
                                "Indicates the minimum Second Order Polarization Mode Dispersion
                                 received since the last port statistics clear.";
                        }

                        leaf maximum {
                            type decimal64 {
                                fraction-digits 2;
                            }
                            units "picoseconds squared";
                            description
                                "Indicates the maximum Second Order Polarization Mode Dispersion
                                 received since the last port statistics clear.";
                        }

                    } // container second-order-polarization-mode-dispersion

                } // container received

                container transmitted {
                    description "Enter the transmitted context";

                    container power {
                        description "Enter the power context";

                        leaf current {
                            type int32;
                            units "millibel-milliwatts";
                            description
                                "Indicates the current power transmitted since the last port statistics
                                 clear.";
                        }

                        leaf average {
                            type int32;
                            units "millibel-milliwatts";
                            description
                                "Indicates the average power transmitted since the last port statistics
                                 clear.";
                        }

                        leaf minimum {
                            type int32;
                            units "millibel-milliwatts";
                            description
                                "Indicates the minimum power transmitted since the last port statistics
                                 clear.";
                        }

                        leaf maximum {
                            type int32;
                            units "millibel-milliwatts";
                            description
                                "Indicates the maximum power transmitted since the last port statistics
                                 clear.";
                        }

                    } // container power

                } // container transmitted

            } // container statistics

            container transmit-power {
                description "Enter the transmit-power context";

                leaf minimum {
                    type int32;
                    units "millibel-milliwatts";
                    description
                        "Indicates the minimum configurable transmit power for the equipped
                         optical module.";
                }

                leaf maximum {
                    type int32;
                    units "millibel-milliwatts";
                    description
                        "Indicates the maximum configurable transmit power for the equipped
                         optical module.";
                }

            } // container transmit-power

        } // container coherent

    } // grouping state-port-dwdm-coherent

}
