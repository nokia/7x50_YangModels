submodule nokia-state-saa {

    yang-version "1.1";

    belongs-to nokia-state { prefix "state"; }

    import ietf-yang-types                { prefix "yang"; }
    import nokia-sros-yang-extensions     { prefix "sros-ext"; }
    import nokia-types-oam                { prefix "types-oam"; }
    import nokia-types-sros               { prefix "types-sros"; }

    sros-ext:sros-major-release "rel23";
    organization "Nokia";
    contact
        "Nokia SR OS Support
         Web: <http://www.nokia.com>";
    description
        "Nokia YANG Data model with operational state for Service Assurance Agent (SAA) on SR OS based routers.

         Copyright 2016 Nokia. All rights reserved. Reproduction of this document
         is authorized on the condition that the foregoing copyright notice is included.

         This nokia-state-saa YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2024-10-11";

    grouping state-saa {
        container saa {
            description "Enter the saa context";

            list owner {
                key "owner-name test";
                description "Enter the owner list instance";

                leaf owner-name {
                    type types-sros:named-item;
                    description "Optional owner name of the SAA operation";
                }

                leaf test {
                    type types-sros:named-item;
                    description "SAA test name";
                }

                container statistics {
                    description "Enter the statistics context";

                    leaf runs-since-last-clear {
                        type yang:counter32;
                        description "Number of times this SAA test has started";
                    }

                    leaf number-of-failed-test-runs {
                        type yang:counter32;
                        description "Number of times this SAA test has failed";
                    }

                    leaf last-test-result {
                        type types-oam:test-result;
                        description
                            "Completion status of the most recent test run. If this SAA
                             test is currently in progress, this object indicates the result of the previous
                             test run, if any.";
                    }

                    leaf newest-test-run {
                        type uint32;
                        description "Most recently completed instance of this SAA test";
                    }

                    container thresholds {
                        description "Enter the thresholds context";

                        list jitter {
                            key "measurement-direction threshold-direction";
                            description "Enter the jitter list instance";

                            leaf measurement-direction {
                                type enumeration {
                                    enum inbound                        { value 1; }
                                    enum outbound                       { value 2; }
                                    enum round-trip                     { value 3; }
                                }
                                description "Direction of the measurement";
                            }

                            leaf threshold-direction {
                                type enumeration {
                                    enum rising                         { value 1; }
                                    enum falling                        { value 2; }
                                }
                                description "Direction of the threshold crossing";
                            }

                            leaf last-event {
                                type yang:date-and-time;
                                description
                                    "Last time a threshold notification was generated as a result of
                                     crossing the specified threshold";
                            }

                            leaf run-number {
                                type uint32;
                                description
                                    "Test run index of the SAA test for which the specified threshold
                                     notification was generated as a result of crossing the specified threshold";
                            }

                            leaf threshold-value {
                                type int32;
                                units "microseconds";
                                description "Statistic that caused the specified threshold notification to be generated";
                            }

                        } // list jitter

                        list latency {
                            key "measurement-direction threshold-direction";
                            description "Enter the latency list instance";

                            leaf measurement-direction {
                                type enumeration {
                                    enum inbound                        { value 1; }
                                    enum outbound                       { value 2; }
                                    enum round-trip                     { value 3; }
                                }
                                description "Direction of the measurement";
                            }

                            leaf threshold-direction {
                                type enumeration {
                                    enum rising                         { value 1; }
                                    enum falling                        { value 2; }
                                }
                                description "Direction of the threshold crossing";
                            }

                            leaf last-event {
                                type yang:date-and-time;
                                description
                                    "Last time a threshold notification was generated as a result of
                                     crossing the specified threshold";
                            }

                            leaf run-number {
                                type uint32;
                                description
                                    "Test run index of the SAA test for which the specified threshold
                                     notification was generated as a result of crossing the specified threshold";
                            }

                            leaf threshold-value {
                                type int32;
                                units "microseconds";
                                description "Statistic that caused the specified threshold notification to be generated";
                            }

                        } // list latency

                        list loss {
                            key "measurement-direction threshold-direction";
                            description "Enter the loss list instance";

                            leaf measurement-direction {
                                type enumeration {
                                    enum inbound                        { value 1; }
                                    enum outbound                       { value 2; }
                                    enum round-trip                     { value 3; }
                                }
                                description "Direction of the measurement";
                            }

                            leaf threshold-direction {
                                type enumeration {
                                    enum rising                         { value 1; }
                                    enum falling                        { value 2; }
                                }
                                description "Direction of the threshold crossing";
                            }

                            leaf last-event {
                                type yang:date-and-time;
                                description
                                    "Last time a threshold notification was generated as a result of
                                     crossing the specified threshold";
                            }

                            leaf run-number {
                                type uint32;
                                description
                                    "Test run index of the SAA test for which the specified threshold
                                     notification was generated as a result of crossing the specified threshold";
                            }

                            leaf threshold-value {
                                type int32;
                                units "packets";
                                description "Statistic that caused the specified threshold notification to be generated";
                            }

                        } // list loss

                    } // container thresholds

                    container ping-common {
                        description "Enter the ping-common context";

                        list test-run {
                            key "run-number";
                            description "Enter the test-run list instance";

                            leaf run-number {
                                type uint32;
                                description "SAA test run number";
                            }

                            leaf execution-state {
                                type enumeration {
                                    enum running                        { value 1; }
                                    enum not-running                    { value 2; }
                                }
                                description "Test run is running, ran to completion, or was stopped by the user";
                            }

                            leaf sent {
                                type uint32;
                                units "packets";
                                description "Number of probes sent for the specified test run";
                            }

                            leaf received {
                                type uint32;
                                units "packets";
                                description "Number of responses received for the specified test run";
                            }

                            leaf loss {
                                type decimal64 {
                                    range "0.000..100.000";
                                    fraction-digits 3;
                                }
                                units "percent";
                                description "Percentage of packets that failed to be transmitted or timed out";
                            }

                            leaf failed-transmissions {
                                type uint32;
                                units "packets";
                                description "Number of probes that failed to be sent for the specified test run";
                            }

                            leaf timeouts {
                                type uint32;
                                units "packets";
                                description "Number of probes that timed out for the specified test run";
                            }

                            leaf total-failures {
                                type uint32;
                                units "packets";
                                description
                                    "Number of probes that failed to be transmitted plus the number
                                     of probes that timed out";
                            }

                            list summary {
                                key "summary-type";
                                description "Enter the summary list instance";

                                leaf summary-type {
                                    type enumeration {
                                        enum outbound                       { value 1; }
                                        enum inbound                        { value 2; }
                                        enum round-trip                     { value 3; }
                                    }
                                    description "Delay direction";
                                }

                                leaf delay-minimum {
                                    type int32;
                                    units "microseconds";
                                    description "Minimum delay in the specified direction";
                                }

                                leaf delay-maximum {
                                    type int32;
                                    units "microseconds";
                                    description "Maximum delay in the specified direction";
                                }

                                leaf delay-average {
                                    type int32;
                                    units "microseconds";
                                    description "Average delay in the specified direction";
                                }

                                leaf jitter {
                                    type uint32;
                                    units "microseconds";
                                    description "Amount of jitter for the specified test run in the specified direction";
                                }

                            } // list summary

                            list probe {
                                key "probe-index";
                                description "Enter the probe list instance";

                                leaf probe-index {
                                    type uint32;
                                    description "Probe index number";
                                }

                                leaf outbound {
                                    type int32;
                                    units "microseconds";
                                    description "Outbound trip time for the specified probe";
                                }

                                leaf inbound {
                                    type int32;
                                    units "microseconds";
                                    description "Inbound trip time for the specified probe";
                                }

                                leaf round-trip {
                                    type uint32;
                                    units "microseconds";
                                    description "Round trip time for the specified probe";
                                }

                                leaf return-code {
                                    type types-oam:ping-return-code;
                                    description "OAM return code received in the probe response";
                                }

                                leaf response-status {
                                    type types-oam:response-status;
                                    description "OAM response status for the specified probe";
                                }

                                leaf responder-source-address {
                                    type types-sros:ip-address;
                                    description "IP address of the responder";
                                }

                            } // list probe

                        } // list test-run

                    } // container ping-common

                } // container statistics

            } // list owner

        } // container saa

    } // grouping state-saa

}
