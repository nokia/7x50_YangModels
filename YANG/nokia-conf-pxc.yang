submodule nokia-conf-pxc {

    yang-version "1.1";

    belongs-to nokia-conf { prefix "conf"; }

    import nokia-sros-yang-extensions     { prefix "sros-ext"; }
    import nokia-types-services           { prefix "types-services"; }
    import nokia-types-sros               { prefix "types-sros"; }

    include nokia-conf-groups;
    include nokia-conf-lag;
    include nokia-conf-port;
    include nokia-conf-qos;


    sros-ext:sros-major-release "rel21";

    organization "Nokia";

    contact
        "Nokia SR OS Support
         Web: <http://www.nokia.com>";

    description
        "Nokia YANG Data model to configure ports cross connects (PXC) on SR OS based routers.

         Copyright 2016 Nokia. All rights reserved. Reproduction of this document
         is authorized on the condition that the foregoing copyright notice is included.

         This nokia-conf-pxc YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-26";

    grouping conf-pxc-port-xc {
        container port-xc {
            description "Enter the port-xc context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list pxc {
                key "pxc-id";
                description "Enter the pxc list instance";

                leaf pxc-id {
                    type uint32 {
                        range "1..64";
                    }
                    description "Unique Identifier for the PXC";
                }

                leaf admin-state {
                    type types-sros:admin-state;
                    default "disable";
                    description "Administrative state of the PXC";
                }

                leaf description {
                    type types-sros:description;
                    description "Text description";
                }

                leaf port-id {
                    type leafref {
                        path "../../../port/port-id";
                    }
                    sros-ext:immutable;
                    description "PXC port ID";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list pxc

        } // container port-xc

    } // grouping conf-pxc-port-xc

    grouping conf-pxc-fwd-path-ext {
        container fwd-path-ext {
            description "Enter the fwd-path-ext context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container sdp-id-range {
                presence "Enable the sdp-id-range context";
                description "Enable the sdp-id-range context";

                leaf start {
                    type types-services:sdp-id;
                    mandatory true;
                    description "Lower bound of the SDP ID range";
                }

                leaf end {
                    type types-services:sdp-id;
                    mandatory true;
                    description "Upper bound of the SDP ID range";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container sdp-id-range

            list fpe {
                key "fpe-id";
                description "Enter the fpe list instance";

                leaf fpe-id {
                    type uint32 {
                        range "1..64";
                    }
                    description "FPE ID";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice fpe-path-type {
                    case single-path {

                        container path {
                            description "Enter the path context";

                            choice path-type {
                                case port-xc {

                                    leaf pxc {
                                        type leafref {
                                            path "../../../../port-xc/pxc/pxc-id";
                                        }
                                        description "Dedicated PXC ID used by the FPE path";
                                    }

                                }
                                case lag {

                                    leaf xc-lag-a {
                                        type leafref {
                                            path "../../../../lag/lag-name";
                                        }
                                        description "PXC LAG identifier dedicated to the FPE path";
                                    }

                                    leaf xc-lag-b {
                                        type leafref {
                                            path "../../../../lag/lag-name";
                                        }
                                        description "PXC LAG identifier dedicated to the FPE path";
                                    }

                                }
                            }
                        } // container path

                    }
                    case multi-path {

                        container multi-path {
                            presence "Enable the multi-path context";
                            description "Enter the multi-path context";

                            list path {
                                key "path-id";
                                description "Enter the path list instance";

                                leaf path-id {
                                    type uint32 {
                                        range "1..64";
                                    }
                                    description "Multipath FPE forwarding path ID";
                                }

                                leaf-list apply-groups {
                                    type leafref {
                                        path "../../../../../groups/group/name";
                                    }
                                    max-elements 8;
                                    ordered-by user;
                                    description "Apply a configuration group at this level";
                                }

                                leaf-list apply-groups-exclude {
                                    type leafref {
                                        path "../../../../../groups/group/name";
                                    }
                                    max-elements 8;
                                    ordered-by user;
                                    description "Exclude a configuration group at this level";
                                }

                                choice path-type {
                                    case port-xc {

                                        leaf pxc {
                                            type leafref {
                                                path "../../../../../port-xc/pxc/pxc-id";
                                            }
                                            description "Dedicated PXC ID used by the FPE path";
                                        }

                                    }
                                    case lag {

                                        leaf xc-lag-a {
                                            type leafref {
                                                path "../../../../../lag/lag-name";
                                            }
                                            description "PXC LAG identifier dedicated to the FPE path";
                                        }

                                        leaf xc-lag-b {
                                            type leafref {
                                                path "../../../../../lag/lag-name";
                                            }
                                            description "PXC LAG identifier dedicated to the FPE path";
                                        }

                                    }
                                }
                            } // list path

                        } // container multi-path

                    }
                }
                container application {
                    description "Enter the application context";

                    leaf pw-port {
                        type boolean;
                        default "false";
                        description "Use FPE to set up FPE PW cross-connect";
                    }

                    leaf sub-mgmt-extension {
                        type boolean;
                        default "false";
                        description "Enable FPE for subscrber management extensions";
                    }

                    container vxlan-termination {
                        presence "Enable the vxlan-termination context";
                        description "Enter the vxlan-termination context";

                        leaf router-instance {
                            type string;
                            default "Base";
                            description "Router name or VPRN service name";
                        }

                    } // container vxlan-termination

                    container srv6 {
                        presence "Enable the srv6 context";
                        description "Enter the srv6 context";

                        leaf type {
                            type enumeration {
                                enum "origination"                  { value 1; }
                                enum "termination"                  { value 2; }
                            }
                            description "SRv6 FPE application type";
                        }

                        container interface-a {
                            description "Enter the interface-a context";

                            container qos {
                                description "Enter the qos context";

                                leaf network-policy {
                                    type leafref {
                                        path "../../../../../../../qos/network/network-policy-name";
                                    }
                                    description "Network QoS policy applied to the SRv6 FPE interfaces";
                                }

                            } // container qos

                        } // container interface-a

                        container interface-b {
                            description "Enter the interface-b context";

                            leaf mtu {
                                type uint32 {
                                    range "0 | 1280..9786";
                                }
                                description "MTU size of SRv6 origination FPE interface-b";
                            }

                            container qos {
                                description "Enter the qos context";

                                leaf network-policy {
                                    type leafref {
                                        path "../../../../../../../qos/network/network-policy-name";
                                    }
                                    description "Network QoS policy applied to the SRv6 FPE interfaces";
                                }

                            } // container qos

                        } // container interface-b

                    } // container srv6

                } // container application

            } // list fpe

        } // container fwd-path-ext

    } // grouping conf-pxc-fwd-path-ext

}
