submodule nokia-state-port-eth-egress {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel21";

    organization "Nokia";

    contact
        "Nokia SR OS Support
         Web: <http://www.nokia.com>";

    description
        "Nokia YANG Data model with operational state for egress capabilities for ethernet ports on SR OS based routers.

         Copyright 2016 Nokia. All rights reserved. Reproduction of this document
         is authorized on the condition that the foregoing copyright notice is included.

         This nokia-state-port-eth-egress YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-08-31";

    grouping state-port-eth-egress {
        container egress {
            description "Enter the egress context";

            container port-scheduler-policy {
                description "Enter the port-scheduler-policy context";

                container statistics {
                    description "Enter the statistics context";

                    leaf total-forwarded-octets {
                        type yang:counter64;
                        description "Indicates the total number of octets forwarded.";
                    }

                    leaf total-forwarded-packets {
                        type yang:counter64;
                        description "Indicates the total number of packets forwarded.";
                    }

                    leaf total-dropped-octets {
                        type yang:counter64;
                        description "Indicates the total number of octets dropped.";
                    }

                    leaf total-dropped-packets {
                        type yang:counter64;
                        description "Indicates the total number of packets dropped.";
                    }

                    list level {
                        key "priority-level";
                        description "Enter the level list instance";

                        leaf priority-level {
                            type uint32 {
                                range "1..8";
                            }
                            description "Specifies the priority level of the port scheduler policy.";
                        }

                        leaf forwarded-octets {
                            type yang:counter64;
                            description "Indicates the number of octets forwarded for this level.";
                        }

                        leaf forwarded-packets {
                            type yang:counter64;
                            description "Indicates the number of packets forwarded for this level.";
                        }

                        leaf dropped-octets {
                            type yang:counter64;
                            description "Indicates the number of octets dropped for this level.";
                        }

                        leaf dropped-packets {
                            type yang:counter64;
                            description "Indicates the number of packets dropped for this level.";
                        }

                    } // list level

                } // container statistics

            } // container port-scheduler-policy

            list hs-secondary-shaper {
                key "secondary-shaper-name";
                description "Enter the hs-secondary-shaper list instance";

                leaf secondary-shaper-name {
                    type types-sros:named-item;
                    description "Secondary shaper name";
                }

                container aggregate {
                    description "Enter the aggregate context";

                    container statistics {
                        description "Enter the statistics context";

                        leaf forwarded-octets {
                            type yang:counter64;
                            description "Indicates the number of octets forwarded.";
                        }

                        leaf forwarded-packets {
                            type yang:counter64;
                            description "Indicates the number of packets forwarded.";
                        }

                    } // container statistics

                } // container aggregate

                list class {
                    key "class-number";
                    description "Enter the class list instance";

                    leaf class-number {
                        type uint32 {
                            range "1..6";
                        }
                        description "HS secondary shaper class ID";
                    }

                    container statistics {
                        description "Enter the statistics context";

                        leaf forwarded-octets {
                            type yang:counter64;
                            description "Indicates the number of octets forwarded.";
                        }

                        leaf forwarded-packets {
                            type yang:counter64;
                            description "Indicates the number of packets forwarded.";
                        }

                    } // container statistics

                } // list class

            } // list hs-secondary-shaper

        } // container egress

    } // grouping state-port-eth-egress

}
