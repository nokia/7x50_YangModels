submodule nokia-conf-port-connector {

    yang-version "1.1";

    belongs-to nokia-conf { prefix "conf"; }

    import nokia-sros-yang-extensions     { prefix "sros-ext"; }

    include nokia-conf-groups;


    sros-ext:sros-major-release "rel21";

    organization "Nokia";

    contact
        "Nokia SR OS Support
         Web: <http://www.nokia.com>";

    description
        "Nokia YANG Data model to configure connector ports on SR OS based routers.

         Copyright 2016 Nokia. All rights reserved. Reproduction of this document
         is authorized on the condition that the foregoing copyright notice is included.

         This nokia-conf-port-connector YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-08-12";

    grouping conf-port-connector {
        container connector {
            description "Enter the connector context";

            leaf breakout {
                type enumeration {
                    enum "c1-40g"                       { value 2; }
                    enum "c4-10g"                       { value 3; }
                    enum "c1-100g"                      { value 4; }
                    enum "c4-25g"                       { value 5; }
                    enum "c10-10g"                      { value 6; }
                    enum "c1-400g"                      { value 8; }
                    enum "c2-100g"                      { value 9; }
                    enum "c4-100g"                      { value 10; }
                    enum "c1-10g"                       { value 11; }
                    enum "c1-25g"                       { value 13; }
                    enum "c1-50g"                       { value 14; }
                    enum "c8-50g"                       { value 15; }
                    enum "c3-100g"                      { value 17; }
                }
                sros-ext:immutable;
                description "Port breakout of the transceiver used in the connector";
            }

            leaf rs-fec-mode {
                type enumeration {
                    enum "cl91-514-528"                 { value 1; }
                    enum "cl91-514-544"                 { value 2; }
                }
                description "RS-FEC mode for the Ethernet connector";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

        } // container connector

    } // grouping conf-port-connector

}
