module nokia-li-notifications {

    yang-version "1.1";

    namespace "urn:nokia.com:sros:ns:yang:sr:li-notifications";

    prefix "li-notif";

    import ietf-inet-types                { prefix "inet"; }
    import ietf-netconf                   { prefix "nc"; }
    import ietf-netconf-notifications     { prefix "ietf-ncn"; }
    import nokia-sros-yang-extensions     { prefix "sros-ext"; }
    import nokia-types-log                { prefix "types-log"; }
    import nokia-types-sros               { prefix "types-sros"; }

    sros-ext:sros-major-release "rel26";
    organization "Nokia";
    contact
        "Nokia SR OS Support
         Web: <http://www.nokia.com>";
    description
        "Description of the li notifications which are available in the system and can be
         sent out by the logger.

         Copyright 2016 Nokia. All rights reserved. Reproduction of this document
         is authorized on the condition that the foregoing copyright notice is included.

         This nokia-li-notifications YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    augment /ietf-ncn:netconf-config-change/ietf-ncn:edit {
        ///netconf-config-change/edit/value
        leaf value {
            type string;
            description "The new value of the target.";
        }

    }

    ///sros-li-config-change-event
    notification sros-li-config-change-event {
        description
            "Generated when the li configuration of the system gets created,
             modified or deleted.";

        ///sros-li-config-change-event/sequence-number
        leaf sequence-number {
            type uint64;
            description
                "A sequence number to indicate the ordering of log events in the log-id.
                 If the event is replayed, the sequence number is replayed as well.";
        }

        ///sros-li-config-change-event/severity
        leaf severity {
            type types-log:severity-level;
            description "The severity level of the log event.";
        }

        ///sros-li-config-change-event/application
        leaf application {
            type types-log:application;
            description "The name of the application that reports the log event.";
        }

        ///sros-li-config-change-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-li-config-change-event/event-name
        leaf event-name {
            type types-sros:named-item;
            description "The name of the log event that was generated.";
        }

        ///sros-li-config-change-event/router-name
        leaf router-name {
            type types-sros:named-item-or-empty;
            description "The router context name that generated the log event.";
        }

        ///sros-li-config-change-event/subject
        leaf subject {
            type types-sros:named-item;
            description
                "The router context name that generated the log event.
                 The subject is the entity that originated the event, such as the Port ID.";
        }

        ///sros-li-config-change-event/message
        leaf message {
            type string {
                length "1..4100";
            }
            description "The log event message.";
        }

        ///sros-li-config-change-event/event-params
        anyxml event-params {
            description "The event specific data splitted in parameters.";

        } // anyxml event-params

    } // notification sros-li-config-change-event

    ///sros-li-state-change-event
    notification sros-li-state-change-event {
        description "Generated on li state changes in the system.";

        ///sros-li-state-change-event/sequence-number
        leaf sequence-number {
            type uint64;
            description
                "A sequence number to indicate the ordering of log events in the log-id.
                 If the event is replayed, the sequence number is replayed as well.";
        }

        ///sros-li-state-change-event/severity
        leaf severity {
            type types-log:severity-level;
            description "The severity level of the log event.";
        }

        ///sros-li-state-change-event/application
        leaf application {
            type types-log:application;
            description "The name of the application that reports the log event.";
        }

        ///sros-li-state-change-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-li-state-change-event/event-name
        leaf event-name {
            type types-sros:named-item;
            description "The name of the log event that was generated.";
        }

        ///sros-li-state-change-event/router-name
        leaf router-name {
            type types-sros:named-item-or-empty;
            description "The router context name that generated the log event.";
        }

        ///sros-li-state-change-event/subject
        leaf subject {
            type types-sros:named-item;
            description
                "The router context name that generated the log event.
                 The subject is the entity that originated the event, such as the Port ID.";
        }

        ///sros-li-state-change-event/message
        leaf message {
            type string {
                length "1..4100";
            }
            description "The log event message.";
        }

        ///sros-li-state-change-event/event-params
        anyxml event-params {
            description "The event specific data splitted in parameters.";

        } // anyxml event-params

    } // notification sros-li-state-change-event

    ///sros-li-command-accounting-event
    notification sros-li-command-accounting-event {
        description "Generated when a user executes a li command on a management interface.";

        ///sros-li-command-accounting-event/sequence-number
        leaf sequence-number {
            type uint64;
            description
                "A sequence number to indicate the ordering of log events in the log-id.
                 If the event is replayed, the sequence number is replayed as well.";
        }

        ///sros-li-command-accounting-event/severity
        leaf severity {
            type types-log:severity-level;
            description "The severity level of the log event.";
        }

        ///sros-li-command-accounting-event/application
        leaf application {
            type types-log:application;
            description "The name of the application that reports the log event.";
        }

        ///sros-li-command-accounting-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-li-command-accounting-event/event-name
        leaf event-name {
            type types-sros:named-item;
            description "The name of the log event that was generated.";
        }

        ///sros-li-command-accounting-event/router-name
        leaf router-name {
            type types-sros:named-item-or-empty;
            description "The router context name that generated the log event.";
        }

        ///sros-li-command-accounting-event/subject
        leaf subject {
            type types-sros:named-item;
            description
                "The router context name that generated the log event.
                 The subject is the entity that originated the event, such as the Port ID.";
        }

        ///sros-li-command-accounting-event/message
        leaf message {
            type string {
                length "1..4100";
            }
            description "The log event message.";
        }

        ///sros-li-command-accounting-event/event-params
        anyxml event-params {
            description "The event specific data splitted in parameters.";

        } // anyxml event-params

    } // notification sros-li-command-accounting-event

    ///sros-li-md-rpc-accounting-event
    notification sros-li-md-rpc-accounting-event {
        description "Generated when a user executes a li RPC on a management interface.";

        ///sros-li-md-rpc-accounting-event/sequence-number
        leaf sequence-number {
            type uint64;
            description
                "A sequence number to indicate the ordering of log events in the log-id.
                 If the event is replayed, the sequence number is replayed as well.";
        }

        ///sros-li-md-rpc-accounting-event/severity
        leaf severity {
            type types-log:severity-level;
            description "The severity level of the log event.";
        }

        ///sros-li-md-rpc-accounting-event/application
        leaf application {
            type types-log:application;
            description "The name of the application that reports the log event.";
        }

        ///sros-li-md-rpc-accounting-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-li-md-rpc-accounting-event/event-name
        leaf event-name {
            type types-sros:named-item;
            description "The name of the log event that was generated.";
        }

        ///sros-li-md-rpc-accounting-event/router-name
        leaf router-name {
            type types-sros:named-item-or-empty;
            description "The router context name that generated the log event.";
        }

        ///sros-li-md-rpc-accounting-event/subject
        leaf subject {
            type types-sros:named-item;
            description
                "The router context name that generated the log event.
                 The subject is the entity that originated the event, such as the Port ID.";
        }

        ///sros-li-md-rpc-accounting-event/message
        leaf message {
            type string {
                length "1..4100";
            }
            description "The log event message.";
        }

        ///sros-li-md-rpc-accounting-event/event-params
        anyxml event-params {
            description "The event specific data splitted in parameters.";

        } // anyxml event-params

    } // notification sros-li-md-rpc-accounting-event

    ///sros-li-log-generic-event
    notification sros-li-log-generic-event {
        description
            "Generated on any event that is generated in the system
             that is not modeled by a more specific event.";

        ///sros-li-log-generic-event/sequence-number
        leaf sequence-number {
            type uint64;
            description
                "A sequence number to indicate the ordering of log events in the log-id.
                 If the event is replayed, the sequence number is replayed as well.";
        }

        ///sros-li-log-generic-event/severity
        leaf severity {
            type types-log:severity-level;
            description "The severity level of the log event.";
        }

        ///sros-li-log-generic-event/application
        leaf application {
            type types-log:application;
            description "The name of the application that reports the log event.";
        }

        ///sros-li-log-generic-event/event-id
        leaf event-id {
            type uint32 {
                range "1..max";
            }
            description
                "The id the event that was generated.
                 Each log event type has a unique identifying number.  This number is
                 unique within a particular software application, such as IP, MPLS,
                 OSPF, etc.; but it is not necessarily unique across different software
                 applications.  That is MPLS event #1001 may be different from OSPF
                 event #1001.";
        }

        ///sros-li-log-generic-event/event-name
        leaf event-name {
            type types-sros:named-item;
            description "The name of the log event that was generated.";
        }

        ///sros-li-log-generic-event/router-name
        leaf router-name {
            type types-sros:named-item-or-empty;
            description "The router context name that generated the log event.";
        }

        ///sros-li-log-generic-event/subject
        leaf subject {
            type types-sros:named-item;
            description
                "The router context name that generated the log event.
                 The subject is the entity that originated the event, such as the Port ID.";
        }

        ///sros-li-log-generic-event/message
        leaf message {
            type string {
                length "1..4100";
            }
            description "The log event message.";
        }

        ///sros-li-log-generic-event/event-params
        anyxml event-params {
            description "The event specific data splitted in parameters.";

        } // anyxml event-params

    } // notification sros-li-log-generic-event

    ///netconf-li-config-change
    notification netconf-li-config-change {
        description
            "Generated when the NETCONF server detects that the
             <running> or <startup> configuration datastore
             has been changed for LI by a management session.
             The notification summarizes the edits that
             have been detected.

             The server MAY choose to also generate this
             notification while loading a datastore during the
             boot process for the device.";

        ///netconf-li-config-change/datastore
        leaf datastore {
            type enumeration {
                enum running {
                    value 0;
                    description "The <running> datastore has changed.";
                }
                enum startup {
                    value 1;
                    description "The <startup> datastore has changed";
                }
            }
            default "running";
            description "Indicates which configuration datastore has changed.";
        }

        ///netconf-li-config-change/changed-by
        container changed-by {
            description
                "Indicates the source of the change.
                 If caused by internal action, then the
                 empty leaf 'server' will be present.
                 If caused by a management session, then
                 the name, remote host address, and session ID
                 of the session that made the change will be reported.";

            ///netconf-li-config-change/changed-by/server-or-user
            choice server-or-user {
                mandatory true;
                ///netconf-li-config-change/changed-by/server-or-user/by-user
                case by-user {

                    ///netconf-li-config-change/changed-by/server-or-user/by-user/username
                    leaf username {
                        type string;
                        mandatory true;
                        description "Name of the user for the session.";
                    }

                    ///netconf-li-config-change/changed-by/server-or-user/by-user/session-id
                    leaf session-id {
                        type nc:session-id-or-zero-type;
                        mandatory true;
                        description
                            "Identifier of the session.
                             A NETCONF session MUST be identified by a non-zero value.
                             A non-NETCONF session MAY be identified by the value zero.";
                    }

                    ///netconf-li-config-change/changed-by/server-or-user/by-user/source-host
                    leaf source-host {
                        type inet:ip-address;
                        description "Address of the remote host for the session.";
                    }

                }
                ///netconf-li-config-change/changed-by/server-or-user/server
                case server {

                    ///netconf-li-config-change/changed-by/server-or-user/server/server
                    leaf server {
                        type empty;
                        description
                            "If present, the change was caused
                             by the server.";
                    }

                }
            }
        } // container changed-by

        ///netconf-li-config-change/edit
        list edit {
            description
                "An edit record SHOULD be present for each distinct
                 edit operation that the server has detected on
                 the target datastore.  This list MAY be omitted
                 if the detailed edit operations are not known.
                 The server MAY report entries in this list for
                 changes not made by a NETCONF session (e.g., CLI).";

            ///netconf-li-config-change/edit/target
            leaf target {
                type string;
                description
                    "Topmost node associated with the configuration change.
                     A server SHOULD set this object to the node within
                     the datastore that is being altered.  A server MAY
                     set this object to one of the ancestors of the actual
                     node that was changed, or omit this object, if the
                     exact node is not known.";
            }

            ///netconf-li-config-change/edit/operation
            leaf operation {
                type nc:edit-operation-type;
                description
                    "Type of edit operation performed.
                     A server MUST set this object to the NETCONF edit
                     operation performed on the target datastore.";
            }

        } // list edit

    } // notification netconf-li-config-change

}
