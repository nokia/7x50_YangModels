module nokia-debug-state {

    yang-version "1.1";

    namespace "urn:nokia.com:sros:ns:yang:sr:debug-state";

    prefix "debug-state";

    import nokia-sros-yang-extensions     { prefix "sros-ext"; }
    import nokia-state                    { prefix "state"; }
    import nokia-types-isa                { prefix "types-isa"; }
    import nokia-types-sros               { prefix "types-sros"; }

    sros-ext:sros-major-release "rel25";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-debug-state YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2025-03-12";

    augment /state:state {

        container debug {
            config false;
            description "Enter the debug context";

            container wlan-gw {
                description "Enter the wlan-gw context";

                list group {
                    key "id";
                    description "Enter the group list instance";

                    leaf id {
                        type types-isa:wlan-gw-group-id;
                        description "WLAN-GW group ID in the system";
                    }

                    list statistic {
                        key "type name";
                        description "Enter the statistic list instance";

                        leaf type {
                            type enumeration {
                                enum packet-error {
                                    value 0;
                                    description "Packet related error";
                                }
                                enum host-error {
                                    value 1;
                                    description "Host related error";
                                }
                                enum bd-error {
                                    value 2;
                                    description "Bridge domain related error";
                                }
                                enum forwarding {
                                    value 3;
                                    description "Number of forwarded packets";
                                }
                                enum reassembly {
                                    value 4;
                                    description "Reassembly related statistic";
                                }
                                enum aa {
                                    value 5;
                                    description "AA related statistic";
                                }
                                enum radius {
                                    value 6;
                                    description "RADIUS related statistic";
                                }
                                enum arp {
                                    value 7;
                                    description "ARP related statistic";
                                }
                                enum dhcp4 {
                                    value 8;
                                    description "DHCP related statistic";
                                }
                                enum dhcp6 {
                                    value 9;
                                    description "DHCPv6 related statistic";
                                }
                                enum icmp4 {
                                    value 10;
                                    description "ICMP related statistic";
                                }
                                enum icmp6 {
                                    value 11;
                                    description "ICMPv6 related statistic";
                                }
                            }
                            description "Type of statistic to trace";
                        }

                        leaf name {
                            type types-sros:named-item-64;
                            description "Name of the statistic to trace";
                        }

                        leaf oper-state {
                            type enumeration {
                                enum ready-for-capture              { value 0; }
                                enum packet-captured                { value 1; }
                            }
                            description "Operational state";
                        }

                    } // list statistic

                } // list group

            } // container wlan-gw

        } // container debug

    }
}
