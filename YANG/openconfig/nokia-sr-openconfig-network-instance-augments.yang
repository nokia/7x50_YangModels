module nokia-sr-openconfig-network-instance-augments {

    namespace "urn:nokia.com:sros:ns:yang:sr:openconfig-network-instance-augments";

    prefix "nokia-oc-netinst-augs";

    import nokia-sros-yang-extensions     { prefix "sros-ext"; }
    import openconfig-network-instance    { prefix "oc-netinst"; }

    sros-ext:sros-major-release "rel26";
    organization "Nokia";
    contact
        "Nokia SR OS Support
         Web: <http://www.nokia.com>";
    description
        "This module contains the list of augments against the openconfig-network-instance
         module for the Nokia SR OS based routers.

         Copyright 2016 Nokia. All rights reserved. Reproduction of this document
         is authorized on the condition that the foregoing copyright notice is included.

         This nokia-sr-openconfig-network-instance-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    augment /oc-netinst:network-instances/oc-netinst:network-instance/oc-netinst:config {
        description "Adds additional Nokia ECMP configuration to network-instance model";

        leaf ecmp {
            type uint32 {
                range "1..64";
            }
            default "1";
            description
                "The maximum number of equal cost routes allowed on this routing table instance.

                 When the number ecmp routes available at the best preference
                 value exceeds the number of ecmp allowed, then the lowest
                 next-hop IP address algorithm is used to select
                 the ecmp routes used.";
        }

    }

    augment /oc-netinst:network-instances/oc-netinst:network-instance/oc-netinst:state {
        description "Adds additional Nokia ECMP configuration to network-instance model";

        leaf ecmp {
            type uint32 {
                range "1..64";
            }
            default "1";
            description
                "The maximum number of equal cost routes allowed on this routing table instance.

                 When the number ecmp routes available at the best preference
                 value exceeds the number of ecmp allowed, then the lowest
                 next-hop IP address algorithm is used to select
                 the ecmp routes used.";
        }

    }

}
