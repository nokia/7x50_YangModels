module nokia-sr-openconfig-system-grpc-deviations {

    namespace "urn:nokia.com:sros:ns:yang:sr:openconfig-system-grpc-deviations";

    prefix "nokia-oc-sys-grpc-devs";

    import nokia-sros-yang-extensions     { prefix "sros-ext"; }
    import openconfig-inet-types          { prefix "oc-inet"; }
    import openconfig-system              { prefix "oc-sys"; }
    import openconfig-system-grpc         { prefix "oc-sys-grpc"; }

    sros-ext:sros-major-release "rel26";
    organization "Nokia";
    contact
        "Nokia SR OS Support
         Web: <http://www.nokia.com>";
    description
        "This module contains the list of deviations against the openconfig-system-grpc
         module for the Nokia SR OS based routers.

         Copyright 2016 Nokia. All rights reserved. Reproduction of this document
         is authorized on the condition that the foregoing copyright notice is included.

         This nokia-sr-openconfig-system-grpc-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    deviation /oc-sys:system/oc-sys-grpc:grpc-servers/oc-sys-grpc:grpc-server/oc-sys-grpc:config/oc-sys-grpc:name {
        deviate replace {
            type string {
                length "7";
                pattern "DEFAULT";
            }
        }
    }

    deviation /oc-sys:system/oc-sys-grpc:grpc-servers/oc-sys-grpc:grpc-server/oc-sys-grpc:config/oc-sys-grpc:services {
        deviate not-supported;
    }

    deviation /oc-sys:system/oc-sys-grpc:grpc-servers/oc-sys-grpc:grpc-server/oc-sys-grpc:config/oc-sys-grpc:certificate-id {
        deviate replace {
            type string {
                length "1..91";
                pattern "(.*\\S.*)|()";
                pattern "[^\\\\:/]*";
            }
        }
    }

    deviation /oc-sys:system/oc-sys-grpc:grpc-servers/oc-sys-grpc:grpc-server/oc-sys-grpc:config/oc-sys-grpc:metadata-authentication {
        deviate not-supported;
    }

    deviation /oc-sys:system/oc-sys-grpc:grpc-servers/oc-sys-grpc:grpc-server/oc-sys-grpc:config/oc-sys-grpc:listen-addresses {
        deviate not-supported;
    }

    deviation /oc-sys:system/oc-sys-grpc:grpc-servers/oc-sys-grpc:grpc-server/oc-sys-grpc:config/oc-sys-grpc:network-instance {
        deviate not-supported;
    }


    deviation /oc-sys:system/oc-sys-grpc:grpc-servers/oc-sys-grpc:grpc-server/oc-sys-grpc:config/oc-sys-grpc:port {
        deviate replace {
            type oc-inet:port-number {
                range "1024..49151|57400";
            }
        }
        deviate add {
            default "57400";
        }
    }

    deviation /oc-sys:system/oc-sys-grpc:grpc-servers/oc-sys-grpc:grpc-server/oc-sys-grpc:state/oc-sys-grpc:name {
        deviate replace {
            type string {
                length "7";
                pattern "DEFAULT";
            }
        }
    }

    deviation /oc-sys:system/oc-sys-grpc:grpc-servers/oc-sys-grpc:grpc-server/oc-sys-grpc:state/oc-sys-grpc:services {
        deviate not-supported;
    }

    deviation /oc-sys:system/oc-sys-grpc:grpc-servers/oc-sys-grpc:grpc-server/oc-sys-grpc:state/oc-sys-grpc:certificate-id {
        deviate replace {
            type string {
                length "1..91";
                pattern "(.*\\S.*)|()";
                pattern "[^\\\\:/]*";
            }
        }
    }

    deviation /oc-sys:system/oc-sys-grpc:grpc-servers/oc-sys-grpc:grpc-server/oc-sys-grpc:state/oc-sys-grpc:metadata-authentication {
        deviate not-supported;
    }

    deviation /oc-sys:system/oc-sys-grpc:grpc-servers/oc-sys-grpc:grpc-server/oc-sys-grpc:state/oc-sys-grpc:listen-addresses {
        deviate not-supported;
    }

    deviation /oc-sys:system/oc-sys-grpc:grpc-servers/oc-sys-grpc:grpc-server/oc-sys-grpc:state/oc-sys-grpc:network-instance {
        deviate not-supported;
    }

    deviation /oc-sys:system/oc-sys-grpc:grpc-servers/oc-sys-grpc:grpc-server {
        deviate add {
            max-elements 1;
        }
    }

}
