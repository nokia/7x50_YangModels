module nokia-sr-openconfig-terminal-device-deviations {

    namespace "urn:nokia.com:sros:ns:yang:sr:openconfig-terminal-device-deviations";

    prefix "nokia-oc-opt-term-devs";

    import nokia-sros-yang-extensions     { prefix "sros-ext"; }
    import openconfig-platform            { prefix "oc-platform"; }
    import openconfig-terminal-device     { prefix "oc-opt-term"; }

    sros-ext:sros-major-release "rel26";
    organization "Nokia";
    contact
        "Nokia SR OS Support
         Web: <http://www.nokia.com>";
    description
        "This module contains the list of deviations against the openconfig-terminal-device
         module for the Nokia SR OS based routers.

         Copyright 2016 Nokia. All rights reserved. Reproduction of this document
         is authorized on the condition that the foregoing copyright notice is included.

         This nokia-sr-openconfig-terminal-device-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    deviation /oc-opt-term:terminal-device {
        deviate not-supported;
    }

    deviation /oc-platform:components/oc-platform:component/oc-opt-term:optical-channel/oc-opt-term:config/oc-opt-term:frequency {
        deviate replace {
            type uint64 {
                range "184800000..196750000";
            }
        }
    }

    deviation /oc-platform:components/oc-platform:component/oc-opt-term:optical-channel/oc-opt-term:config/oc-opt-term:target-output-power {
        deviate add {
            default "1.00";
        }
        deviate replace {
            type decimal64 {
                range "-20..3";
                fraction-digits 2;
            }
        }
    }

    deviation /oc-platform:components/oc-platform:component/oc-opt-term:optical-channel/oc-opt-term:config/oc-opt-term:operational-mode {
        deviate add {
            default "0";
        }
        deviate replace {
            type uint16 {
                range "0..9|1021|1022|1025..1029|1033|1037|1043|1051|1061|1065|1069|1081..1083|1085|1088..1092|1169|1210|1211|1220|1221|1240|1241|2001..2011";
            }
        }
    }

    deviation /oc-platform:components/oc-platform:component/oc-opt-term:optical-channel/oc-opt-term:config/oc-opt-term:line-port {
        deviate not-supported;
    }

    deviation /oc-platform:components/oc-platform:component/oc-opt-term:optical-channel/oc-opt-term:state/oc-opt-term:frequency {
        deviate replace {
            type uint64 {
                range "184800000..196750000";
            }
        }
    }

    deviation /oc-platform:components/oc-platform:component/oc-opt-term:optical-channel/oc-opt-term:state/oc-opt-term:target-output-power {
        deviate add {
            default "1.00";
        }
        deviate replace {
            type decimal64 {
                range "-20..3";
                fraction-digits 2;
            }
        }
    }

    deviation /oc-platform:components/oc-platform:component/oc-opt-term:optical-channel/oc-opt-term:state/oc-opt-term:operational-mode {
        deviate add {
            default "0";
        }
        deviate replace {
            type uint16 {
                range "0..9|1021|1022|1025..1029|1033|1037|1043|1051|1061|1065|1069|1081..1083|1085|1088..1092|1169|1210|1211|1220|1221|1240|1241|2001..2011";
            }
        }
    }

    deviation /oc-platform:components/oc-platform:component/oc-opt-term:optical-channel/oc-opt-term:state/oc-opt-term:group-id {
        deviate not-supported;
    }

    deviation /oc-platform:components/oc-platform:component/oc-opt-term:optical-channel/oc-opt-term:state/oc-opt-term:output-power/oc-opt-term:min-time {
        deviate not-supported;
    }

    deviation /oc-platform:components/oc-platform:component/oc-opt-term:optical-channel/oc-opt-term:state/oc-opt-term:output-power/oc-opt-term:max-time {
        deviate not-supported;
    }

    deviation /oc-platform:components/oc-platform:component/oc-opt-term:optical-channel/oc-opt-term:state/oc-opt-term:input-power/oc-opt-term:min-time {
        deviate not-supported;
    }

    deviation /oc-platform:components/oc-platform:component/oc-opt-term:optical-channel/oc-opt-term:state/oc-opt-term:input-power/oc-opt-term:max-time {
        deviate not-supported;
    }

    deviation /oc-platform:components/oc-platform:component/oc-opt-term:optical-channel/oc-opt-term:state/oc-opt-term:laser-bias-current {
        deviate not-supported;
    }

    deviation /oc-platform:components/oc-platform:component/oc-opt-term:optical-channel/oc-opt-term:state/oc-opt-term:chromatic-dispersion/oc-opt-term:min-time {
        deviate not-supported;
    }

    deviation /oc-platform:components/oc-platform:component/oc-opt-term:optical-channel/oc-opt-term:state/oc-opt-term:chromatic-dispersion/oc-opt-term:max-time {
        deviate not-supported;
    }

    deviation /oc-platform:components/oc-platform:component/oc-opt-term:optical-channel/oc-opt-term:state/oc-opt-term:polarization-mode-dispersion {
        deviate not-supported;
    }

    deviation /oc-platform:components/oc-platform:component/oc-opt-term:optical-channel/oc-opt-term:state/oc-opt-term:second-order-polarization-mode-dispersion {
        deviate not-supported;
    }

    deviation /oc-platform:components/oc-platform:component/oc-opt-term:optical-channel/oc-opt-term:state/oc-opt-term:polarization-dependent-loss/oc-opt-term:min-time {
        deviate not-supported;
    }

    deviation /oc-platform:components/oc-platform:component/oc-opt-term:optical-channel/oc-opt-term:state/oc-opt-term:polarization-dependent-loss/oc-opt-term:max-time {
        deviate not-supported;
    }

    deviation /oc-platform:components/oc-platform:component/oc-opt-term:optical-channel/oc-opt-term:state/oc-opt-term:modulator-bias-xi {
        deviate not-supported;
    }

    deviation /oc-platform:components/oc-platform:component/oc-opt-term:optical-channel/oc-opt-term:state/oc-opt-term:modulator-bias-xq {
        deviate not-supported;
    }

    deviation /oc-platform:components/oc-platform:component/oc-opt-term:optical-channel/oc-opt-term:state/oc-opt-term:modulator-bias-yi {
        deviate not-supported;
    }

    deviation /oc-platform:components/oc-platform:component/oc-opt-term:optical-channel/oc-opt-term:state/oc-opt-term:modulator-bias-yq {
        deviate not-supported;
    }

    deviation /oc-platform:components/oc-platform:component/oc-opt-term:optical-channel/oc-opt-term:state/oc-opt-term:modulator-bias-x-phase {
        deviate not-supported;
    }

    deviation /oc-platform:components/oc-platform:component/oc-opt-term:optical-channel/oc-opt-term:state/oc-opt-term:modulator-bias-y-phase {
        deviate not-supported;
    }

    deviation /oc-platform:components/oc-platform:component/oc-opt-term:optical-channel/oc-opt-term:state/oc-opt-term:osnr/oc-opt-term:min-time {
        deviate not-supported;
    }

    deviation /oc-platform:components/oc-platform:component/oc-opt-term:optical-channel/oc-opt-term:state/oc-opt-term:osnr/oc-opt-term:max-time {
        deviate not-supported;
    }

    deviation /oc-platform:components/oc-platform:component/oc-opt-term:optical-channel/oc-opt-term:state/oc-opt-term:carrier-frequency-offset/oc-opt-term:min-time {
        deviate not-supported;
    }

    deviation /oc-platform:components/oc-platform:component/oc-opt-term:optical-channel/oc-opt-term:state/oc-opt-term:carrier-frequency-offset/oc-opt-term:max-time {
        deviate not-supported;
    }

    deviation /oc-platform:components/oc-platform:component/oc-opt-term:optical-channel/oc-opt-term:state/oc-opt-term:sop-roc/oc-opt-term:min-time {
        deviate not-supported;
    }

    deviation /oc-platform:components/oc-platform:component/oc-opt-term:optical-channel/oc-opt-term:state/oc-opt-term:sop-roc/oc-opt-term:max-time {
        deviate not-supported;
    }

    deviation /oc-platform:components/oc-platform:component/oc-opt-term:optical-channel/oc-opt-term:state/oc-opt-term:modulation-error-ratio {
        deviate not-supported;
    }

    deviation /oc-platform:components/oc-platform:component/oc-opt-term:optical-channel/oc-opt-term:state/oc-opt-term:fec-uncorrectable-blocks {
        deviate not-supported;
    }

    deviation /oc-platform:components/oc-platform:component/oc-opt-term:optical-channel/oc-opt-term:state/oc-opt-term:pre-fec-ber/oc-opt-term:min-time {
        deviate not-supported;
    }

    deviation /oc-platform:components/oc-platform:component/oc-opt-term:optical-channel/oc-opt-term:state/oc-opt-term:pre-fec-ber/oc-opt-term:max-time {
        deviate not-supported;
    }

    deviation /oc-platform:components/oc-platform:component/oc-opt-term:optical-channel/oc-opt-term:state/oc-opt-term:post-fec-ber {
        deviate not-supported;
    }

    deviation /oc-platform:components/oc-platform:component/oc-opt-term:optical-channel/oc-opt-term:state/oc-opt-term:q-value/oc-opt-term:min-time {
        deviate not-supported;
    }

    deviation /oc-platform:components/oc-platform:component/oc-opt-term:optical-channel/oc-opt-term:state/oc-opt-term:q-value/oc-opt-term:max-time {
        deviate not-supported;
    }

    deviation /oc-platform:components/oc-platform:component/oc-opt-term:optical-channel/oc-opt-term:state/oc-opt-term:esnr/oc-opt-term:min-time {
        deviate not-supported;
    }

    deviation /oc-platform:components/oc-platform:component/oc-opt-term:optical-channel/oc-opt-term:state/oc-opt-term:esnr/oc-opt-term:max-time {
        deviate not-supported;
    }

}
