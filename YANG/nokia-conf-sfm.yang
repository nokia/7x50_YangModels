submodule nokia-conf-sfm {

    yang-version "1.1";

    belongs-to nokia-conf { prefix "conf"; }

    import nokia-sros-yang-extensions     { prefix "sros-ext"; }
    import nokia-types-sfm                { prefix "types-sfm"; }
    import nokia-types-sros               { prefix "types-sros"; }

    include nokia-conf-groups;


    sros-ext:sros-major-release "rel21";

    organization "Nokia";

    contact
        "Nokia SR OS Support
         Web: <http://www.nokia.com>";

    description
        "Nokia YANG Data model to configure switch fabric modules on SR OS based routers.

         Copyright 2016 Nokia. All rights reserved. Reproduction of this document
         is authorized on the condition that the foregoing copyright notice is included.

         This nokia-conf-sfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2019-09-10";

    grouping conf-sfm {
        list sfm {
            key "sfm-slot";
            description "Enter the sfm list instance";

            leaf sfm-slot {
                type uint32 {
                    range "1..16";
                }
                description "Unique value to identify this SFM slot within a chassis in the system";
            }

            leaf admin-state {
                type types-sros:admin-state;
                default "enable";
                description "Administrative state of SFM";
            }

            leaf sfm-type {
                type types-sfm:sros-sfm-type;
                sros-ext:immutable;
                description "Provision the SFM type";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

        } // list sfm

    } // grouping conf-sfm

}
