module nokia-types-mcr {

    yang-version "1.1";

    namespace "urn:nokia.com:sros:ns:yang:sr:types-mcr";

    prefix "types-mcr";

    import ietf-yang-types                { prefix "yang"; }
    import nokia-sros-yang-extensions     { prefix "sros-ext"; }

    sros-ext:sros-major-release "rel26";
    organization "Nokia";
    contact
        "Nokia SR OS Support
         Web: <http://www.nokia.com>";
    description
        "Common data-types data types used in the SR OS management system.

         Copyright 2016 Nokia. All rights reserved. Reproduction of this document
         is authorized on the condition that the foregoing copyright notice is included.

         This nokia-types-mcr YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    typedef ring-node-oper-state {
        type enumeration {
            enum unknown                        { value 1; }
            enum not-provisioned                { value 2; }
            enum config-error                   { value 3; }
            enum not-tested                     { value 4; }
            enum testing                        { value 5; }
            enum connected                      { value 6; }
            enum disconnected                   { value 7; }
        }
        description "The operational state of a ring-node";
    }

    typedef ring-node-mac-address {
        type yang:mac-address;
        default "00:00:00:00:00:00";
        description "A mac-address used for access node connection verification.";
    }

    typedef ring-oper-state {
        type enumeration {
            enum unknown                        { value 1; }
            enum connected                      { value 2; }
            enum broken                         { value 3; }
            enum testing                        { value 4; }
            enum peer-detects-down              { value 5; }
            enum not-configured                 { value 6; }
        }
        description "The operational state of the ring";
    }

}
