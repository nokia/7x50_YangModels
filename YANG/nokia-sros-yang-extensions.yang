module nokia-sros-yang-extensions {

    yang-version "1.1";

    namespace "urn:nokia.com:sros:ns:yang:sr:sros-yang-extensions";

    prefix "sros-ext";

    sros-ext:sros-major-release "rel24";
    organization "Nokia";
    contact
        "Nokia SR OS Support
         Web: <http://www.nokia.com>";
    description
        "Nokia YANG Data model defining extensions on SR OS based routers.

         Copyright 2016 Nokia. All rights reserved. Reproduction of this document
         is authorized on the condition that the foregoing copyright notice is included.

         This nokia-sros-yang-extensions YANG module embodies Nokia's proprietary
         intellectual property. Nokia retains all title and ownership in the
         Specification, including any revisions.

         Nokia grants all interested parties a non-exclusive license to use
         and distribute an unmodified copy of this Specification in connection with
         management of Nokia products, and without fee, provided this
         copyright notice and license appear on all copies.

         This Specification is supplied `as is', and Nokia makes no warranty,
         either express or implied, as to the use, operation, condition, or performance
         of the Specification.";
    revision "2024-04-12";

    extension auto-restart-to-modify {
        description
            "This extension provides an annotation to configuration nodes to
             indicate that modification to an auto-restart-to-modify node in
             model-driven interfaces will cause SR OS to automatically restart
             the protocol or service in the parent node, so the new value of the
             node takes effect. Warning: this modification will cause disruption
             and affect network stability when committed.";
    } // extension auto-restart-to-modify

    extension bof-parameter-effect {
        argument "configuration-effect";
        description
            "This extension provides an annotation to BOF configuration nodes
             to indicate when the new value of a node will take effect. The
             values of some BOF configuration nodes take effect at commit time,
             while others take effect when the router boots.
                     
             These are denoted by 'commit' or 'boot' respectively.";
    } // extension bof-parameter-effect

    extension immutable {
        description
            "This extension provides an annotation to configuration leaf nodes to
             indicate that it can only be configured in the transaction in which the
             parent node, for example a list entry or presence container, is created.
             It can't be modified while the parent node exists. Modification to an
             immutable leaf in model-driven interfaces will cause SR OS to
             automatically delete the parent node and then recreate the parent node
             and all child nodes with the new value for the immutable leaf. Warning:
             this modification will cause disruption and affect network stability
             when committed.";
    } // extension immutable

    extension isa-auto-clear-on-modify {
        description
            "This extension provides an annotation to configuration nodes
             to indicate that modification to an isa-auto-clear-on-modify
             node in model-driven interfaces will cause SR OS to automatically
             clear ISA state such as flows, so the new value of the node takes
             effect. Warning: This modification will cause traffic disruption
             when committed.";
    } // extension isa-auto-clear-on-modify

    extension manual-restart-to-modify {
        description
            "This extension provides an annotation to configuration nodes to
             indicate that modification to a manual-restart-to-modify node in
             model-driven interfaces requires a manual restart of the protocol
             or service in the parent node, so the new value of the leaf takes
             effect. Warning: a manual restart will cause disruption and affect
             network stability.";
    } // extension manual-restart-to-modify

    extension sros-major-release {
        argument "major-release";
        description
            "The Nokia SR OS Major Release to which this particular instance of this YANG
             module belongs.";
    } // extension sros-major-release

    extension card-auto-reset-on-modify {
        description
            "This extension provides an annotation to configuration nodes to
             indicate that modification to a card-auto-reset-on-modify node in
             model-driven interfaces will cause the router to automatically reset
             the associated cards/XIOMs/MDAs, so the new value of the node takes
             effect. On the 7750 SR-1 platform, the configuration must be saved,
             and the router rebooted immediately after committing the configuration.
             Warning: This modification will cause traffic disruption when committed.";
    } // extension card-auto-reset-on-modify

    extension shared-model-management {
        description
            "This extension provides an annotation to configuration nodes to
             indicate shared model management capability.  If a configuration node is of 
             type list then the capability applies to a single list instance (e.g. entry) and its
             children.  If the node is of type container then it applies to the whole hierarchy.";
    } // extension shared-model-management

    extension openconfig {
        argument "shared-model-management-support";
        description
            "This extension is a sub-statement of the extension shared-model-management.
             It indicates if the sharing model management is supported with OpenConfig.
             The argument value 'true' indicates shared support; 
             whereas 'false' indicates no shared support.";
    } // extension openconfig

}
