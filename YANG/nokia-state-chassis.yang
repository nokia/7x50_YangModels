submodule nokia-state-chassis {

    yang-version "1.1";

    belongs-to nokia-state { prefix "state"; }

    import ietf-yang-types                { prefix "yang"; }
    import nokia-features                 { prefix "nokia-features"; }
    import nokia-sros-yang-extensions     { prefix "sros-ext"; }
    import nokia-types-chassis            { prefix "types-chassis"; }
    import nokia-types-sros               { prefix "types-sros"; }
    import nokia-types-system             { prefix "types-system"; }


    sros-ext:sros-major-release "rel20";

    organization "Nokia";

    contact
        "Nokia SR OS Support
         Web: <http://www.nokia.com>";

    description
        "Nokia YANG Data model with operational state for Physical Chassis related parameters on SR OS based routers.

         Copyright 2016 Nokia. All rights reserved. Reproduction of this document
         is authorized on the condition that the foregoing copyright notice is included.

         This nokia-state-chassis YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-12-09";

    grouping state-chassis {
        list chassis {
            key "chassis-class chassis-number";
            description "Enter the chassis list instance";

            leaf chassis-class {
                type types-chassis:chassis-class;
                description "Functional use of the physical chassis";
            }

            leaf chassis-number {
                type uint32 {
                    range "1..100";
                }
                description "Unique index to identify this physical chassis";
            }

            leaf name {
                type types-sros:named-item;
                description "The name for the physical chassis.";
            }

            leaf role {
                type enumeration {
                    enum "standalone"                   { value 1; }
                    enum "master"                       { value 2; }
                    enum "extension"                    { value 3; }
                    enum "ethernet-satellite"           { value 6; }
                    enum "tdm-satellite"                { value 7; }
                    enum "power-shelf"                  { value 10; }
                }
                description "The role in which the physical chassis performs while in the system.";
            }

            leaf state {
                type types-system:device-state;
                description "The device state of the physical chassis.";
            }

            leaf power-supplies {
                type uint32;
                description "The total number of power supplies that can be installed in this physical chassis.";
            }

            leaf fan-trays {
                type uint32;
                description "The total number of fan trays installed in this physical chassis.";
            }

            leaf filter-door-state {
                type enumeration {
                    enum "unknown"                      { value 0; }
                    enum "not-monitored"                { value 1; }
                    enum "closed"                       { value 2; }
                    enum "open"                         { value 3; }
                }
                description "The value of filter-door-state indicates the state of the filter door.";
            }

            container hardware-data {
                description "Enter the hardware-data context";

                leaf part-number {
                    type string {
                        length "0..32";
                    }
                    description "Indicates the part number information.";
                }

                leaf serial-number {
                    type string {
                        length "0..32";
                    }
                    description "Indicates the serial number of the hardware component.";
                }

                leaf manufacturing-date {
                    type string {
                        length "0..8";
                    }
                    description "Indicates the manufacturing date of the hardware component.";
                }

                leaf common-language-equipment-identifier {
                    type string {
                        length "0..10";
                    }
                    description "Indicates the CLEI, a unique 10-character identifier fixed by the manufacturer.";
                }

                leaf field-replaceable-unit {
                    type boolean;
                    description "Indicates whether the hardware component is a field replaceable unit or not.";
                }

                leaf oper-state {
                    type enumeration {
                        enum "unknown"                      { value 1; }
                        enum "in-service"                   { value 2; }
                        enum "out-of-service"               { value 3; }
                        enum "diagnosing"                   { value 4; }
                        enum "failed"                       { value 5; }
                        enum "booting"                      { value 6; }
                        enum "empty"                        { value 7; }
                        enum "provisioned"                  { value 8; }
                        enum "unprovisioned"                { value 9; }
                        enum "upgrade"                      { value 10; }
                        enum "downgrade"                    { value 11; }
                        enum "in-service-upgrade"           { value 12; }
                        enum "in-service-downgrade"         { value 13; }
                        enum "reset-pending"                { value 14; }
                        enum "soft-reset"                   { value 15; }
                        enum "pre-extension"                { value 16; }
                        enum "downloading"                  { value 17; }
                    }
                    description "Indicates the operational status of the hardware component.";
                }

                leaf failure-reason {
                    type string {
                        length "0..255";
                    }
                    description "Indicates the reason why a hardware component 'failed' as indicated in oper-state.";
                }

                leaf alarm-state {
                    type enumeration {
                        enum "unknown"                      { value 0; }
                        enum "alarm-active"                 { value 1; }
                        enum "alarm-cleared"                { value 2; }
                    }
                    description "Indicates the current alarm state for this hardware component.";
                }

                leaf manufacturing-deviations {
                    type string {
                        length "0..255";
                    }
                    description "Indicates the record of changes done by the manfacturing to the hardware or software which is outside the normal revision control process.";
                }

                leaf equipped-platform-type {
                    type enumeration {
                        enum "platform-unknown"             { value 0; }
                        enum "platform-7750"                { value 1; }
                        enum "platform-7450"                { value 2; }
                        enum "platform-7710"                { value 3; }
                        enum "platform-7950"                { value 4; }
                        enum "platform-7705"                { value 5; }
                        enum "platform-7250"                { value 6; }
                    }
                    description "Indicates the platform type of the installed hardware component, as read from the EEPROM.";
                }

                leaf manufacturing-assembly-number {
                    type string {
                        length "0..32";
                    }
                    description "Indicates an assembly number indicating manufacturing differences for a given part number.";
                }

                leaf power-zone-location {
                    type uint32 {
                        range "0..32";
                    }
                    description "Indicates the managed power zone that this hardware component resides.";
                }

                leaf base-mac-address {
                    type yang:mac-address;
                    description "Indicates the base MAC address of the hardware component.";
                }

                leaf software-last-boot-time {
                    type yang:date-and-time;
                    description "This indicates the date and time the software running on this hardware component was last rebooted.";
                }

            } // container hardware-data

            list fan {
                key "fan-slot";
                description "Enter the fan list instance";

                leaf fan-slot {
                    type uint32 {
                        range "1..31";
                    }
                    description "The unique identifier index for a fan tray in the chassis.";
                }

                leaf state {
                    type types-system:device-state;
                    description "The device state of the physical fan tray.";
                }

                leaf revision {
                    type enumeration {
                        enum "unknown"                      { value 0; }
                        enum "original-fan-tray"            { value 1; }
                        enum "high-flow-fan-tray"           { value 2; }
                    }
                    description "The revision of the physical fan tray.";
                }

                leaf speed {
                    type types-sros:percent;
                    description "The speed of the fans in the physical fan tray as a percentage of the maximum speed.";
                }

                leaf type {
                    type enumeration {
                        enum "chassis"                      { value 1; }
                        enum "pcm"                          { value 2; }
                    }
                    description "The type of physical fan tray.";
                }

                leaf airflow-direction {
                    type enumeration {
                        enum "unknown"                      { value 0; }
                        enum "front-to-back"                { value 1; }
                        enum "back-to-front"                { value 2; }
                    }
                    description "If the fan direction is 'front-to-back' or 'back-to-front'.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf software-last-boot-time {
                        type yang:date-and-time;
                        description "This indicates the date and time the software running on this hardware component was last rebooted.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

            } // list fan

            list power-supply {
                key "power-supply-id";
                description "Enter the power-supply list instance";

                leaf power-supply-id {
                    type uint32 {
                        range "1..31";
                    }
                    description "Unique identifier index for a power supply tray in the chassis";
                }

                leaf equipped-type {
                    type enumeration {
                        enum "none"                         { value 0; }
                        enum "dc-single"                    { value 1; }
                        enum "ac-single"                    { value 2; }
                        enum "ac-multiple"                  { value 3; }
                        enum "auto"                         { value 4; }
                        enum "dc-multiple"                  { value 5; }
                        enum "not-applicable"               { value 6; }
                    }
                    description "Indicates the type of power supply that is physically inserted into the slot.";
                }

                leaf ac-status {
                    type types-system:device-state;
                    description "The input AC voltage state of the power supply.";
                }

                leaf dc-status {
                    type types-system:device-state;
                    description "The output DC voltage state of the power supply.";
                }

                leaf temp-status {
                    type types-system:device-state;
                    description "The current temperature state of the power supply.";
                }

                leaf temp-threshold {
                    type int32;
                    units "degrees celsius";
                    description "The temperature threshold for this power supply tray in degrees celsius.";
                }

                leaf first-power-supply-status {
                    type types-system:device-state;
                    description "The overall status of an equipped power supply. For AC multiple power supplies, this represents the overall status of the first power supply in the tray (or shelf).";
                }

                leaf second-power-supply-status {
                    type types-system:device-state;
                    description "The overall status of an equipped power supply. For AC multiple power supplies, this represents the overall status of the second power supply in the tray (or shelf).";
                }

                leaf input-status {
                    type types-system:device-state;
                    description "The input voltage state of the power supply.";
                }

                leaf output-status {
                    type types-system:device-state;
                    description "The output voltage state of the power supply.";
                }

                leaf pem-type {
                    type enumeration {
                        enum "not-applicable"               { value 0; }
                        enum "unknown"                      { value 1; }
                        enum "pem"                          { value 2; }
                        enum "pem-3"                        { value 3; }
                        enum "peq"                          { value 4; }
                    }
                    description "The Power Entry Module (PEM) type installed in the PEM slot.";
                }

                leaf pem-ac-rect {
                    type bits {
                        bit ac-rect1                       { position 0; }
                        bit ac-rect2                       { position 1; }
                    }
                    description "Which Power Entry Module AC rectifiers installed in the PEM slot are in a failed state or are missing.";
                }

                leaf input-feed-down {
                    type bits {
                        bit input-feed-a                   { position 0; }
                        bit input-feed-b                   { position 1; }
                    }
                    description "Which input feeds are not supplying power.";
                }

                leaf fan-direction {
                    type enumeration {
                        enum "unknown"                      { value 0; }
                        enum "front-to-back"                { value 1; }
                        enum "back-to-front"                { value 2; }
                    }
                    description "If the fan direction is 'front-to-back' or 'back-to-front'.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                } // container hardware-data

            } // list power-supply

            list peq {
                key "peq-slot";
                description "Enter the peq list instance";

                leaf peq-slot {
                    type uint32 {
                        range "1..31";
                    }
                    description "Unique identifier index for a power supply tray in the chassis";
                }

                leaf equipped-type {
                    type types-system:peq-type-state;
                    description "Identifies the CCM type that is physically inserted into this PEQ slot in the chassis.";
                }

                leaf available-wattage {
                    type uint32;
                    units "watts";
                    description "The reported available wattage of the PEQ.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf software-last-boot-time {
                        type yang:date-and-time;
                        description "This indicates the date and time the software running on this hardware component was last rebooted.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

            } // list peq

            list power-connection-module {
                key "pcm-slot";
                description "Enter the power-connection-module list instance";

                leaf pcm-slot {
                    type uint32 {
                        range "1..12";
                    }
                    description "Unique identifier index for a power control module in the chassis";
                }

                leaf equipped-type {
                    type types-chassis:pcm-type-state;
                    description "The equipped PCM type.";
                }

                leaf input-feed-down {
                    type bits {
                        bit input-feed-a                   { position 0; }
                        bit input-feed-b2                  { position 1; }
                        bit input-feed-a2                  { position 2; }
                        bit input-feed-b                   { position 3; }
                    }
                    description "Indicates which feeds are down on the quad pcm.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf software-last-boot-time {
                        type yang:date-and-time;
                        description "This indicates the date and time the software running on this hardware component was last rebooted.";
                    }

                    leaf firmware-code-version {
                        type string {
                            length "0..255";
                        }
                        description "Indicates the software product release version number associated with the firmware version currently programmed.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

            } // list power-connection-module

            list power-module {
                key "power-module-id";
                description "Enter the power-module list instance";

                leaf power-module-id {
                    type uint32 {
                        range "1..12";
                    }
                    description "Unique identifier for a power module in chassis";
                }

                leaf equipped-type {
                    type types-chassis:power-module-type-state;
                    description "Identifies the power module type that is physically inserted into this shelf in the chassis.";
                }

                leaf output-status {
                    type enumeration {
                        enum "unknown"                      { value 0; }
                        enum "ok"                           { value 1; }
                        enum "failed"                       { value 2; }
                        enum "disabled"                     { value 3; }
                        enum "not-equipped"                 { value 4; }
                    }
                    description "The output voltage state of the power supply.";
                }

                leaf input-feed-down {
                    type bits {
                        bit input-feed-a                   { position 0; }
                        bit input-feed-b                   { position 1; }
                    }
                    description "Which input feeds are not supplying power.";
                }

                leaf available-wattage {
                    type uint32;
                    units "watts";
                    description "The reported available wattage of the power module.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf software-last-boot-time {
                        type yang:date-and-time;
                        description "This indicates the date and time the software running on this hardware component was last rebooted.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

            } // list power-module

            list power-shelf {
                if-feature nokia-features:sros-power-shelf;
                key "power-shelf-id";
                description "Enter the power-shelf list instance";

                leaf power-shelf-id {
                    type uint32 {
                        range "1..2";
                    }
                    description "Unique identifier index for a power shelf in chassis";
                }

                leaf equipped-type {
                    type types-chassis:power-shelf-type-state;
                    description "Identifies the power shelf type that is physically inserted into this chassis.";
                }

                leaf input-power-mode {
                    type uint32 {
                        range "0|60|80";
                    }
                    units "amperes";
                    description "The the input power mode of the power shelf.";
                }

                leaf output-status {
                    type enumeration {
                        enum "unknown"                      { value 0; }
                        enum "on"                           { value 1; }
                        enum "off"                          { value 2; }
                        enum "not-equipped"                 { value 3; }
                    }
                    description "The output status of the power shelf.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf software-last-boot-time {
                        type yang:date-and-time;
                        description "This indicates the date and time the software running on this hardware component was last rebooted.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

                list power-module {
                    key "power-module-id";
                    description "Enter the power-module list instance";

                    leaf power-module-id {
                        type uint32 {
                            range "1..12";
                        }
                        description "Unique identifier for a power module in chassis";
                    }

                    leaf equipped-type {
                        type types-chassis:power-module-type-state;
                        description "Identifies the power module type that is physically inserted into this shelf in the chassis.";
                    }

                    leaf output-status {
                        type enumeration {
                            enum "unknown"                      { value 0; }
                            enum "ok"                           { value 1; }
                            enum "failed"                       { value 2; }
                            enum "disabled"                     { value 3; }
                            enum "not-equipped"                 { value 4; }
                        }
                        description "The output voltage state of the power supply.";
                    }

                    leaf input-feed-down {
                        type bits {
                            bit input-feed-a                   { position 0; }
                            bit input-feed-b                   { position 1; }
                        }
                        description "Which input feeds are not supplying power.";
                    }

                    leaf available-wattage {
                        type uint32;
                        units "watts";
                        description "The reported available wattage of the power module.";
                    }

                    container hardware-data {
                        description "Enter the hardware-data context";

                        leaf part-number {
                            type string {
                                length "0..32";
                            }
                            description "Indicates the part number information.";
                        }

                        leaf serial-number {
                            type string {
                                length "0..32";
                            }
                            description "Indicates the serial number of the hardware component.";
                        }

                        leaf manufacturing-date {
                            type string {
                                length "0..8";
                            }
                            description "Indicates the manufacturing date of the hardware component.";
                        }

                        leaf common-language-equipment-identifier {
                            type string {
                                length "0..10";
                            }
                            description "Indicates the CLEI, a unique 10-character identifier fixed by the manufacturer.";
                        }

                        leaf field-replaceable-unit {
                            type boolean;
                            description "Indicates whether the hardware component is a field replaceable unit or not.";
                        }

                        leaf oper-state {
                            type enumeration {
                                enum "unknown"                      { value 1; }
                                enum "in-service"                   { value 2; }
                                enum "out-of-service"               { value 3; }
                                enum "diagnosing"                   { value 4; }
                                enum "failed"                       { value 5; }
                                enum "booting"                      { value 6; }
                                enum "empty"                        { value 7; }
                                enum "provisioned"                  { value 8; }
                                enum "unprovisioned"                { value 9; }
                                enum "upgrade"                      { value 10; }
                                enum "downgrade"                    { value 11; }
                                enum "in-service-upgrade"           { value 12; }
                                enum "in-service-downgrade"         { value 13; }
                                enum "reset-pending"                { value 14; }
                                enum "soft-reset"                   { value 15; }
                                enum "pre-extension"                { value 16; }
                                enum "downloading"                  { value 17; }
                            }
                            description "Indicates the operational status of the hardware component.";
                        }

                        leaf failure-reason {
                            type string {
                                length "0..255";
                            }
                            description "Indicates the reason why a hardware component 'failed' as indicated in oper-state.";
                        }

                        leaf alarm-state {
                            type enumeration {
                                enum "unknown"                      { value 0; }
                                enum "alarm-active"                 { value 1; }
                                enum "alarm-cleared"                { value 2; }
                            }
                            description "Indicates the current alarm state for this hardware component.";
                        }

                        leaf manufacturing-deviations {
                            type string {
                                length "0..255";
                            }
                            description "Indicates the record of changes done by the manfacturing to the hardware or software which is outside the normal revision control process.";
                        }

                        leaf equipped-platform-type {
                            type enumeration {
                                enum "platform-unknown"             { value 0; }
                                enum "platform-7750"                { value 1; }
                                enum "platform-7450"                { value 2; }
                                enum "platform-7710"                { value 3; }
                                enum "platform-7950"                { value 4; }
                                enum "platform-7705"                { value 5; }
                                enum "platform-7250"                { value 6; }
                            }
                            description "Indicates the platform type of the installed hardware component, as read from the EEPROM.";
                        }

                        leaf manufacturing-assembly-number {
                            type string {
                                length "0..32";
                            }
                            description "Indicates an assembly number indicating manufacturing differences for a given part number.";
                        }

                        leaf power-zone-location {
                            type uint32 {
                                range "0..32";
                            }
                            description "Indicates the managed power zone that this hardware component resides.";
                        }

                        leaf software-last-boot-time {
                            type yang:date-and-time;
                            description "This indicates the date and time the software running on this hardware component was last rebooted.";
                        }

                        leaf firmware-revision-status {
                            type enumeration {
                                enum "not-applicable"               { value 0; }
                                enum "acceptable"                   { value 1; }
                                enum "not-acceptable"               { value 2; }
                                enum "upgrade-pending"              { value 3; }
                                enum "upgrading"                    { value 4; }
                                enum "upgrade-next-hard-reset"      { value 5; }
                            }
                            description "Indicates the firmware/FPGA revision status for the hardware component.";
                        }

                    } // container hardware-data

                } // list power-module

            } // list power-shelf

        } // list chassis

    } // grouping state-chassis

}
