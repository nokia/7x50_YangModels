submodule nokia-state-port-eth-lldp {

    yang-version "1.1";

    belongs-to nokia-state { prefix "state"; }

    import ietf-yang-types                { prefix "yang"; }
    import nokia-sros-yang-extensions     { prefix "sros-ext"; }
    import nokia-types-lldp               { prefix "types-lldp"; }


    sros-ext:sros-major-release "rel21";

    organization "Nokia";

    contact
        "Nokia SR OS Support
         Web: <http://www.nokia.com>";

    description
        "Nokia YANG Data model with operational state for ethernet ports supporting link layer discovery protocol capabilities on SR OS based routers.

         Copyright 2016 Nokia. All rights reserved. Reproduction of this document
         is authorized on the condition that the foregoing copyright notice is included.

         This nokia-state-port-eth-lldp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-03-11";

    grouping state-port-eth-lldp {
        container lldp {
            description "Enter the lldp context";

            list dest-mac {
                key "mac-type";
                description "Enter the dest-mac list instance";

                leaf mac-type {
                    type types-lldp:mac-addr-type;
                    description "Destination MAC address type";
                }

                list remote-system {
                    key "remote-time-mark remote-index";
                    description "Enter the remote-system list instance";

                    leaf remote-time-mark {
                        type yang:timeticks;
                        description "Specifies the time filter.";
                    }

                    leaf remote-index {
                        type int32 {
                            range "1..max";
                        }
                        description "Specifies an arbitrary local integer value used to identify a particular connection instance, unique only for the indicated remote system.";
                    }

                    leaf age {
                        type yang:counter64;
                        units "seconds";
                        description "Indicates the number of seconds since the remote system was discovered.";
                    }

                    leaf chassis-id {
                        type types-lldp:chassis-id;
                        description "Indicates the chassis identifier subtype provided by the remote system. The corresponding port identifier is port-id.";
                    }

                    leaf chassis-id-subtype {
                        type types-lldp:chassis-id-subtype;
                        description "Indicates the port component associated with the remote system.";
                    }

                    leaf remote-port-id {
                        type types-lldp:lldp-port-id;
                        description "Indicates the port component associated with the remote system.";
                    }

                    leaf remote-port-id-subtype {
                        type types-lldp:lldp-port-id-subtype;
                        description "Indicates the port identifier subtype provided by the remote system. The corresponding port identifier is port-id.";
                    }

                    leaf port-description {
                        type string {
                            length "0..255";
                        }
                        description "Indicates the description of the given port associated with the remote system.";
                    }

                    leaf system-enabled-capabilities {
                        type types-lldp:system-capabilities;
                        description "Indicates which system capabilities are enabled on the remote system.";
                    }

                    leaf system-supported-capabilities {
                        type types-lldp:system-capabilities;
                        description "Indicates which system capabilities are supported on the remote system.";
                    }

                    leaf system-description {
                        type string {
                            length "0..255";
                        }
                        description "Indicates the system description of the remote system.";
                    }

                    leaf system-name {
                        type string {
                            length "0..255";
                        }
                        description "Indicates the system name of the remote system.";
                    }

                    list mgmt-address {
                        key "mgmt-address-subtype mgmt-address";
                        description "Enter the mgmt-address list instance";

                        leaf mgmt-address-subtype {
                            type union {
                                type types-lldp:address-family-numbers;
                                type int32 {
                                    range "25..255";
                                }
                            }
                            description "Specifies the type of management address identifier encoding used in mgmt-address.";
                        }

                        leaf mgmt-address {
                            type types-lldp:management-address;
                            description "Specifies the string value used to identify the management address component associated with the remote system. The purpose of this address is to contact the management entity.";
                        }

                        leaf interface-subtype {
                            type enumeration {
                                enum "unknown"                      { value 1; }
                                enum "if-index"                     { value 2; }
                                enum "system-port-number"           { value 3; }
                            }
                            description "Indicates the interface numbering type provided by the remote system. The corresponding interface number is interface-id.";
                        }

                        leaf interface-id {
                            type int32;
                            description "Indicates the integer value used to identify the interface number regarding the management address component associated with the remote system.";
                        }

                        leaf object-identifier {
                            type yang:object-identifier-128;
                            description "Indicates the OID value used to identify the type of hardware component or protocol entity associated with the management address advertised by the remote system agent.";
                        }

                    } // list mgmt-address

                } // list remote-system

                container statistics {
                    description "Enter the statistics context";

                    container transmit {
                        description "Enter the transmit context";

                        leaf frames {
                            type yang:counter32;
                            description "Indicates the number of LLDP frames transmitted.";
                        }

                        leaf length-error-frames {
                            type yang:counter32;
                            description "Indicates the number of LLDP length errors recorded.";
                        }

                    } // container transmit

                    container receive {
                        description "Enter the receive context";

                        leaf age-outs {
                            type yang:zero-based-counter32;
                            description "Indicates the number of age-outs. An age-out is the number of times the complete set of information advertised by a particular MSAP has been deleted because the information timeliness interval has expired.";
                        }

                        leaf frames {
                            type yang:counter32;
                            description "Indicates the number of LLDP frames that are received.";
                        }

                        leaf frame-discards {
                            type yang:counter32;
                            description "Indicates the number of LLDP frames that are received and then discarded for any reason. This counter can provide an indication that LLDP header formatting problems may exist with the local LLDP agent in the sending system or that LLDPDU validation problems may exist with the local LLDP agent in the receiving system.";
                        }

                        leaf frame-errors {
                            type yang:counter32;
                        }

                        leaf tlv-discards {
                            type yang:counter32;
                            description "Indicates the number of LLDP TLVs that are received and then discarded for any reason.";
                        }

                        leaf tlv-unknown {
                            type yang:counter32;
                            description "Indicates the number of LLDP TLVs that are received and not recognized. An unrecognized TLV is referred to as the TLV whose type value is in the range of reserved TLV types (000 1001 - 111 1110) in Table 9.1 of IEEE Std 802.1AB-2004. An unrecognized TLV may be a basic management TLV from a later LLDP version.";
                        }

                    } // container receive

                } // container statistics

                list tx-mgmt-address {
                    key "mgmt-address-system-type";
                    description "Enter the tx-mgmt-address list instance";

                    leaf mgmt-address-system-type {
                        type enumeration {
                            enum "oob"                          { value 0; }
                            enum "system"                       { value 1; }
                            enum "system-ipv6"                  { value 2; }
                            enum "oob-ipv6"                     { value 3; }
                        }
                        description "Management address to transmit";
                    }

                    leaf mgmt-address {
                        type types-lldp:management-address;
                        description "Indicates the management address.";
                    }

                    leaf mgmt-address-subtype {
                        type types-lldp:address-family-numbers;
                        description "Indicates the management address representation in mgmt-address. The value 'other (0)' indicates that no management address is in use.";
                    }

                } // list tx-mgmt-address

            } // list dest-mac

        } // container lldp

    } // grouping state-port-eth-lldp

}
