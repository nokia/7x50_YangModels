module nokia-oper-reset {

    yang-version "1.1";

    namespace "urn:nokia.com:sros:ns:yang:sr:oper-reset";

    prefix "oper-reset";

    import ietf-inet-types                { prefix "types-inet"; }
    import ietf-yang-types                { prefix "yang"; }
    import nokia-sros-yang-extensions     { prefix "sros-ext"; }
    import nokia-state                    { prefix "state"; }
    import nokia-types-bgp                { prefix "types-bgp"; }
    import nokia-types-cellular           { prefix "types-cellular"; }
    import nokia-types-filter             { prefix "types-filter"; }
    import nokia-types-igp                { prefix "types-igp"; }
    import nokia-types-operation          { prefix "types-operation"; }
    import nokia-types-services           { prefix "types-services"; }
    import nokia-types-sros               { prefix "types-sros"; }
    import nokia-types-subscriber-mgmt    { prefix "types-submgt"; }

    sros-ext:sros-major-release "rel26";
    organization "Nokia";
    contact
        "Nokia SR OS Support
         Web: <http://www.nokia.com>";
    description
        "Nokia YANG Data model for reset on SR OS based routers.

         Copyright 2016 Nokia. All rights reserved. Reproduction of this document
         is authorized on the condition that the foregoing copyright notice is included.

         This nokia-oper-reset YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    container reset {
        config false;
        description "Clear statistics or reset operational state";


        list lag {
            key "lag-name";
            description "Enter the lag list instance";

            leaf lag-name {
                type leafref {
                    path "/state:state/state:lag/state:lag-name";
                }
                description "LAG name, starting with lag-";
            }

            action statistics {
                description "Reset LAG statistics";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action statistics

            action lacp-statistics {
                description "Reset LACP statistics";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action lacp-statistics

            action aggregate-queue-statistics {
                description "Reset LAG aggregate queue statistics";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action aggregate-queue-statistics

            container bfd-session {
                description "Enter the bfd-session context";

                action port {
                    description "Port identifier in the LAG";

                    input {

                        leaf lag-port {
                            type leafref {
                                path "/state:state/state:lag[state:lag-name=current()/../../../lag-name]/state:port/state:port-id";
                            }
                            mandatory true;
                            description "Member port of the LAG";
                        }

                        leaf family {
                            type enumeration {
                                enum ipv4                           { value 1; }
                                enum ipv6                           { value 2; }
                            }
                            mandatory true;
                            description "BFD session family type";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action port

            } // container bfd-session

        } // list lag

        container application-assurance {
            description "Enter the application-assurance context";

            list radius-accounting-policy {
                key "name";
                description "Enter the radius-accounting-policy list instance";

                leaf name {
                    type leafref {
                        path "/state:state/state:application-assurance/state:radius-accounting-policy/state:rad-acct-plcy-name";
                    }
                    description "AA RADIUS accounting policy";
                }

                action statistics {
                    description "Reset AA RADIUS accounting policy statistics";

                    input {

                        leaf server {
                            type leafref {
                                path "/state:state/state:application-assurance/state:radius-accounting-policy[state:rad-acct-plcy-name=current()/../../name]/state:radius-accounting-server/state:server/state:server-index";
                            }
                            description "AA RADIUS accounting policy server index";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

            } // list radius-accounting-policy

            list group {
                key "aa-group-id";
                description "Enter the group list instance";

                leaf aa-group-id {
                    type leafref {
                        path "/state:state/state:application-assurance/state:group/state:aa-group-id";
                    }
                    description "AA group ID";
                }

                action status {
                    description "Reset status and statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action status

                action statistics {
                    description "Reset AA group statistics";

                    input {

                        leaf force {
                            type empty;
                            description "Force the reset action";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action cflowd {
                    description "Reset AA group cflowd";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action cflowd

                list partition {
                    key "aa-partition-id";
                    description "Enter the partition list instance";

                    leaf aa-partition-id {
                        type leafref {
                            path "/state:state/state:application-assurance/state:group[state:aa-group-id=current()/../../aa-group-id]/state:partition/state:aa-partition-id";
                        }
                        description "AA partition ID";
                    }

                    action event-log {
                        description "Reset the AA event log for the group partition";

                        input {

                            leaf name {
                                type leafref {
                                    path "/state:state/state:application-assurance/state:group[state:aa-group-id=current()/../../../aa-group-id]/state:partition[state:aa-partition-id=current()/../../aa-partition-id]/state:event-log/state:event-log-name";
                                }
                                description "Event log name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action event-log

                    action gtp {
                        description "Reset the AA GTP for the group partition";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action gtp

                } // list partition

            } // list group

        } // container application-assurance

        container saa {
            description "Enter the saa context";

            list owner {
                key "owner-name test";
                description "Enter the owner list instance";

                leaf owner-name {
                    type leafref {
                        path "/state:state/state:saa/state:owner[state:test=current()/../test]/state:owner-name";
                    }
                    description "Name of SAA test owner for which to reset statistics";
                }

                leaf test {
                    type leafref {
                        path "/state:state/state:saa/state:owner[state:owner-name=current()/../owner-name]/state:test";
                    }
                    description "Name of the SAA test for which to reset statistics";
                }

                action statistics {
                    description "Clear the SAA test statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

            } // list owner

        } // container saa

        container filter {
            description "Enter the filter context";

            action ip-filter {
                description "Reset operation on the specified IP filter";

                input {

                    leaf filter-name {
                        type leafref {
                            path "/state:state/state:filter/state:ip-filter/state:filter-name";
                        }
                        mandatory true;
                        description "IP filter name";
                    }

                    leaf entry {
                        type leafref {
                            path "/state:state/state:filter/state:ip-filter[state:filter-name=current()/../filter-name]/state:entry/state:entry-id";
                        }
                        description "Entry ID for the filter";
                    }

                    leaf direction {
                        type types-filter:filter-reset-direction;
                        description "Statistics direction for IP filter entries";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action ip-filter

            action ipv6-filter {
                description "Reset operation on the specified IPv6 filter";

                input {

                    leaf filter-name {
                        type leafref {
                            path "/state:state/state:filter/state:ipv6-filter/state:filter-name";
                        }
                        mandatory true;
                        description "IPv6 exception filter name";
                    }

                    leaf entry {
                        type leafref {
                            path "/state:state/state:filter/state:ipv6-filter[state:filter-name=current()/../filter-name]/state:entry/state:entry-id";
                        }
                        description "Entry ID for the IPv6 filter";
                    }

                    leaf direction {
                        type types-filter:filter-reset-direction;
                        description "Statistics direction of IPv6 filter entries";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action ipv6-filter

            action mac-filter {
                description "Reset operation on the specified MAC filter";

                input {

                    leaf filter-name {
                        type leafref {
                            path "/state:state/state:filter/state:mac-filter/state:filter-name";
                        }
                        mandatory true;
                        description "MAC filter name";
                    }

                    leaf entry {
                        type leafref {
                            path "/state:state/state:filter/state:mac-filter[state:filter-name=current()/../filter-name]/state:entry/state:entry-id";
                        }
                        description "Entry ID for the MAC filter";
                    }

                    leaf direction {
                        type types-filter:filter-reset-direction;
                        description "Statistics direction for MAC filter entries";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action mac-filter

            action ip-exception {
                description "Reset operation on the specified IP exception filter";

                input {

                    leaf filter-name {
                        type leafref {
                            path "/state:state/state:filter/state:ip-exception/state:filter-name";
                        }
                        mandatory true;
                        description "IP exception filter name";
                    }

                    leaf entry {
                        type leafref {
                            path "/state:state/state:filter/state:ip-exception[state:filter-name=current()/../filter-name]/state:entry/state:entry-id";
                        }
                        description "Entry ID for the filter";
                    }

                    leaf direction {
                        type types-filter:filter-reset-direction;
                        description "Statistics direction for IP exception filter entries";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action ip-exception

            action ipv6-exception {
                description "Reset operation on the specified IPv6 exception filter";

                input {

                    leaf filter-name {
                        type leafref {
                            path "/state:state/state:filter/state:ipv6-exception/state:filter-name";
                        }
                        mandatory true;
                        description "IPv6 exception filter name";
                    }

                    leaf entry {
                        type leafref {
                            path "/state:state/state:filter/state:ipv6-exception[state:filter-name=current()/../filter-name]/state:entry/state:entry-id";
                        }
                        description "Entry ID for the filter";
                    }

                    leaf direction {
                        type types-filter:filter-reset-direction;
                        description "Statistics direction for IPv6 exception filter entries";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action ipv6-exception

            action log {
                description "Reset the specified filter log";

                input {

                    leaf log-id {
                        type leafref {
                            path "/state:state/state:filter/state:log/state:log-id";
                        }
                        mandatory true;
                        description "ID of the filter log to reset";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action log

            list policer {
                key "policer-name";
                description "Enter the policer list instance";

                leaf policer-name {
                    type leafref {
                        path "/state:state/state:filter/state:policer/state:policer-name";
                    }
                    description "Filter policer name";
                }

                container instance {
                    description "Enter the instance context";

                    action system {
                        description "Enter the system context";

                        input {

                            leaf direction {
                                type types-filter:filter-reset-direction;
                                description "Filter policer instance statistics counters to be reset";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action system

                    container filter {
                        description "Enter the filter context";

                        action ip {
                            description "Reset instance statistics counters";

                            input {

                                leaf name {
                                    type leafref {
                                        path "/state:state/state:filter/state:policer[state:policer-name=current()/../../../../policer-name]/state:statistics/state:instance/state:filter/state:ip/state:name";
                                    }
                                    mandatory true;
                                    description "Filter policer instance name";
                                }

                                leaf direction {
                                    type types-filter:filter-reset-direction;
                                    description "Filter policer instance statistics counters to be reset";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action ip

                        action ipv6 {
                            description "Enter the ipv6 context";

                            input {

                                leaf name {
                                    type leafref {
                                        path "/state:state/state:filter/state:policer[state:policer-name=current()/../../../../policer-name]/state:statistics/state:instance/state:filter/state:ipv6/state:name";
                                    }
                                    mandatory true;
                                    description "Filter policer instance name";
                                }

                                leaf direction {
                                    type types-filter:filter-reset-direction;
                                    description "Filter policer instance statistics counters to be reset";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action ipv6

                    } // container filter

                    action all {
                        description "Reset counters for all policer instances";

                        input {

                            leaf direction {
                                type types-filter:filter-reset-direction;
                                description "Filter policer instance statistics counters to be reset";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                } // container instance

            } // list policer

        } // container filter

        container subscriber-management {
            description "Enter the subscriber-management context";

            container ancp {
                description "Enter the ancp context";

                action sub-string {
                    description "Delete the ANCP association for matching ANCP strings";

                    input {

                        leaf value {
                            type types-submgt:ancp-string;
                            mandatory true;
                            description "Substring to match";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sub-string

            } // container ancp

            container host-lockout {
                description "Enter the host-lockout context";

                action policy {
                    description "Delete matching host lockout contexts from the policy";

                    input {

                        leaf name {
                            type leafref {
                                path "/state:state/state:subscriber-mgmt/state:host-lockout-policy/state:name";
                            }
                            mandatory true;
                            description "Host lockout policy name";
                        }

                        leaf state {
                            type enumeration {
                                enum all                            { value 0; }
                                enum active                         { value 1; }
                                enum graceful                       { value 2; }
                            }
                            mandatory true;
                            description "Lockout state to match";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action policy

                action sap {
                    description "Delete matching host lockout contexts from the SAP";

                    input {

                        leaf sap {
                            type types-sros:sap;
                            mandatory true;
                            description "SAP ID";
                        }

                        leaf mac {
                            type types-sros:ieee-address;
                            description "MAC address to match";
                        }

                        leaf remote-id {
                            type string {
                                length "1..253";
                            }
                            description "Remote ID to match";
                        }

                        leaf circuit-id {
                            type string {
                                length "1..253";
                            }
                            description "Circuit ID to match";
                        }

                        leaf state {
                            type enumeration {
                                enum all                            { value 0; }
                                enum active                         { value 1; }
                                enum graceful                       { value 2; }
                            }
                            mandatory true;
                            description "Lockout state to match";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action sap

                action state {
                    description "Delete all host lockout contexts in the state";

                    input {

                        leaf state {
                            type enumeration {
                                enum all                            { value 0; }
                                enum active                         { value 1; }
                                enum graceful                       { value 2; }
                            }
                            mandatory true;
                            description "Lockout state";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action state

            } // container host-lockout

            container idle-only-msap {
                description "Enter the idle-only-msap context";

                action msap-policy {
                    description "Delete idle state sticky MSAPs created by the policy";

                    input {

                        leaf name {
                            type leafref {
                                path "/state:state/state:subscriber-mgmt/state:msap-policy/state:name";
                            }
                            mandatory true;
                            description "MSAP policy name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action msap-policy

                action all {
                    description "Delete all sticky MSAPs in the idle state";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

            } // container idle-only-msap

            action msap-policy {
                description "Delete MSAPs created by the policy";

                input {

                    leaf name {
                        type leafref {
                            path "/state:state/state:subscriber-mgmt/state:msap-policy/state:name";
                        }
                        mandatory true;
                        description "MSAP policy name";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action msap-policy

            list sap-template {
                key "name";
                description "Enter the sap-template list instance";

                leaf name {
                    type leafref {
                        path "/state:state/state:subscriber-mgmt/state:sap-template/state:name";
                    }
                    description "SAP template name";
                }

                action idle-saps {
                    description "Delete SAPs that use this template and have no sessions";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action idle-saps

            } // list sap-template

            action errors {
                description "Delete subscriber management errors";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action errors

            container statistics {
                description "Enter the statistics context";

                container data-trigger {
                    description "Enter the data-trigger context";

                    action system {
                        description "Reset data-trigger statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action system

                } // container data-trigger

                container sla-profile {
                    description "Enter the sla-profile context";

                    action all {
                        description "Reset all SLA profile statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action name {
                        description "Reset SLA profile statistics for the sla-profile";

                        input {

                            leaf name {
                                type leafref {
                                    path "/state:state/state:subscriber-mgmt/state:sla-profile/state:name";
                                }
                                mandatory true;
                                description "SLA profile name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action name

                } // container sla-profile

                container sub-profile {
                    description "Enter the sub-profile context";

                    action all {
                        description "Reset all subscriber profile statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action name {
                        description "Reset subscriber profile statistics for the specified sub-profile";

                        input {

                            leaf name {
                                type leafref {
                                    path "/state:state/state:subscriber-mgmt/state:sub-profile/state:name";
                                }
                                mandatory true;
                                description "Subscriber profile name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action name

                } // container sub-profile

                container svlan {
                    description "Enter the svlan context";

                    list pw-port {
                        key "pw-port-id";
                        description "Enter the pw-port list instance";

                        leaf pw-port-id {
                            type leafref {
                                path "/state:state/state:pw-port/state:pw-port-id";
                            }
                            description "PW port ID";
                        }

                        action all {
                            description "Reset all S-VLAN statistics on this PW port";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action vlan-id {
                            description "Reset the specified S-VLAN statistics on this PW port";

                            input {

                                leaf svlan-id {
                                    type leafref {
                                        path "/state:state/state:pw-port[state:pw-port-id=current()/../../pw-port-id]/state:subscriber-management/state:svlan/state:vlan-id";
                                    }
                                    mandatory true;
                                    description "VLAN ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action vlan-id

                    } // list pw-port

                    list port {
                        key "port-id";
                        description "Enter the port list instance";

                        leaf port-id {
                            type leafref {
                                path "/state:state/state:port/state:port-id";
                            }
                            description "Port ID";
                        }

                        action all {
                            description "Reset all S-VLAN statistics on this port";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action vlan-id {
                            description "Reset the specified S-VLAN statistics on this port";

                            input {

                                leaf svlan-id {
                                    type leafref {
                                        path "/state:state/state:port[state:port-id=current()/../../port-id]/state:subscriber-management/state:svlan/state:vlan-id";
                                    }
                                    mandatory true;
                                    description "VLAN ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action vlan-id

                    } // list port

                    list lag {
                        key "name";
                        description "Enter the lag list instance";

                        leaf name {
                            type leafref {
                                path "/state:state/state:lag/state:lag-name";
                            }
                            description "LAG name";
                        }

                        action all {
                            description "Reset all S-VLAN statistics on this LAG";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action vlan-id {
                            description "Reset the specified S-VLAN statistics on this LAG";

                            input {

                                leaf svlan-id {
                                    type leafref {
                                        path "/state:state/state:lag[state:lag-name=current()/../../name]/state:subscriber-management/state:svlan/state:vlan-id";
                                    }
                                    mandatory true;
                                    description "VLAN ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action vlan-id

                    } // list lag

                } // container svlan

                container accumulated {
                    description "Enter the accumulated context";

                    container active-subscribers {
                        description "Enter the active-subscribers context";

                        action no-accu-stats-policy {
                            description "Reset accumulated statistics for active subscribers";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action no-accu-stats-policy

                        action sub-profile {
                            description "Reset active subscribers statistics without a policy";

                            input {

                                leaf name {
                                    type leafref {
                                        path "/state:state/state:subscriber-mgmt/state:sub-profile/state:name";
                                    }
                                    mandatory true;
                                    description "Subscriber profile name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action sub-profile

                    } // container active-subscribers

                    action inactive-subscribers {
                        description "Reset accumulated statistics for all inactive subscribers";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action inactive-subscribers

                    action subscriber {
                        description "Reset accumulated statistics for specified subscriber";

                        input {

                            leaf name {
                                type leafref {
                                    path "/state:state/state:subscriber-mgmt/state:subscriber/state:subscriber-id";
                                }
                                mandatory true;
                                description "Subscriber ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action subscriber

                } // container accumulated

                container host-and-session {
                    description "Enter the host-and-session context";

                    container peakvalues {
                        description "Enter the peakvalues context";

                        container card {
                            description "Enter the card context";

                            action all {
                                description "Reset the peak value statistics for all cards";

                                input {

                                    leaf recursive {
                                        type empty;
                                        description "Reset the statistics recursively";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                            action slot {
                                description "Reset peak values statistics for the specified card";

                                input {

                                    leaf slot-number {
                                        type leafref {
                                            path "/state:state/state:card/state:slot-number";
                                        }
                                        mandatory true;
                                        description "Slot number";
                                    }

                                    leaf recursive {
                                        type empty;
                                        description "Reset the statistics recursively";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action slot

                        } // container card

                        container mda {
                            description "Enter the mda context";

                            action all {
                                description "Reset peak value statistics for all MDAs";

                                input {

                                    leaf recursive {
                                        type empty;
                                        description "Reset the statistics recursively";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                            list card-slot {
                                key "slot-number";
                                description "Enter the card-slot list instance";

                                leaf slot-number {
                                    type leafref {
                                        path "/state:state/state:card/state:slot-number";
                                    }
                                    description "Slot number";
                                }

                                action mda-slot {
                                    description "Reset peak value statistics for the specified MDA";

                                    input {

                                        leaf mda {
                                            type leafref {
                                                path "/state:state/state:card[state:slot-number=current()/../../slot-number]/state:mda/state:mda-slot";
                                            }
                                            mandatory true;
                                            description "MDA slot number";
                                        }

                                        leaf recursive {
                                            type empty;
                                            description "Reset the statistics recursively";
                                        }

                                    }
                                    output {

                                        leaf operation-id {
                                            type types-operation:operation-id;
                                            description "ID assigned to the operation.";
                                        }

                                        leaf start-time {
                                            type types-operation:operation-timestamp;
                                            description "Time when the operation started its execution.";
                                        }

                                        leaf results-path {
                                            type types-operation:operation-path;
                                            description "Path to the results of the operation formatted as xpath.";
                                        }

                                        leaf status {
                                            type types-operation:operation-status;
                                            description "Status of the operation";
                                        }

                                        leaf-list error-message {
                                            type types-operation:operation-message;
                                            description "Error messages reported during execution of the operation.";
                                        }

                                        leaf-list warning-message {
                                            type types-operation:operation-message;
                                            description "Warning messages reported during execution of the operation.";
                                        }

                                        leaf-list info-message {
                                            type types-operation:operation-message;
                                            description "Info messages reported during execution of the operation.";
                                        }

                                        leaf end-time {
                                            type types-operation:operation-timestamp;
                                            description "Time when the operation ended its execution.";
                                        }

                                    }
                                } // action mda-slot

                                action xiom-slot {
                                    description "Reset peak value statistics for the specified XIOM MDA";

                                    input {

                                        leaf xiom {
                                            type leafref {
                                                path "/state:state/state:card[state:slot-number=current()/../../slot-number]/state:xiom/state:xiom-slot";
                                            }
                                            mandatory true;
                                            description "XIOM slot number";
                                        }

                                        leaf mda-slot {
                                            type leafref {
                                                path "/state:state/state:card[state:slot-number=current()/../../slot-number]/state:xiom[state:xiom-slot=current()/../xiom]/state:mda/state:mda-slot";
                                            }
                                            mandatory true;
                                            description "MDA slot number";
                                        }

                                        leaf recursive {
                                            type empty;
                                            description "Reset the statistics recursively";
                                        }

                                    }
                                    output {

                                        leaf operation-id {
                                            type types-operation:operation-id;
                                            description "ID assigned to the operation.";
                                        }

                                        leaf start-time {
                                            type types-operation:operation-timestamp;
                                            description "Time when the operation started its execution.";
                                        }

                                        leaf results-path {
                                            type types-operation:operation-path;
                                            description "Path to the results of the operation formatted as xpath.";
                                        }

                                        leaf status {
                                            type types-operation:operation-status;
                                            description "Status of the operation";
                                        }

                                        leaf-list error-message {
                                            type types-operation:operation-message;
                                            description "Error messages reported during execution of the operation.";
                                        }

                                        leaf-list warning-message {
                                            type types-operation:operation-message;
                                            description "Warning messages reported during execution of the operation.";
                                        }

                                        leaf-list info-message {
                                            type types-operation:operation-message;
                                            description "Info messages reported during execution of the operation.";
                                        }

                                        leaf end-time {
                                            type types-operation:operation-timestamp;
                                            description "Time when the operation ended its execution.";
                                        }

                                    }
                                } // action xiom-slot

                            } // list card-slot

                        } // container mda

                        container port {
                            description "Enter the port context";

                            action all {
                                description "Reset peak values statistics for all ports";

                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                            action port-id {
                                description "Reset peak value statistics for the specified port";

                                input {

                                    leaf port-id {
                                        type leafref {
                                            path "/state:state/state:port/state:port-id";
                                        }
                                        mandatory true;
                                        description "Port ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action port-id

                            action lag {
                                description "Reset peak value statistics for the specified LAG";

                                input {

                                    leaf name {
                                        type leafref {
                                            path "/state:state/state:lag/state:lag-name";
                                        }
                                        mandatory true;
                                        description "LAG name";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action lag

                        } // container port

                        container pw-port {
                            description "Enter the pw-port context";

                            action all {
                                description "Reset peak value statistics for all PW ports";

                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                            action pw-port-id {
                                description "Reset peak value statistics for the PW port";

                                input {

                                    leaf pw-port-id {
                                        type leafref {
                                            path "/state:state/state:pw-port/state:pw-port-id";
                                        }
                                        mandatory true;
                                        description "PW port ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action pw-port-id

                        } // container pw-port

                        container service {
                            description "Enter the service context";

                            action all {
                                description "Reset peak value statistics for all services";

                                input {

                                    leaf recursive {
                                        type empty;
                                        description "Reset the statistics recursively";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                            list name {
                                key "service-name";
                                description "Enter the name list instance";

                                leaf service-name {
                                    type types-services:service-name;
                                    description "Service name";
                                }

                                action all {
                                    description "Reset all peak value statistics for the service";

                                    input {

                                        leaf recursive {
                                            type empty;
                                            description "Reset the statistics recursively";
                                        }

                                    }
                                    output {

                                        leaf operation-id {
                                            type types-operation:operation-id;
                                            description "ID assigned to the operation.";
                                        }

                                        leaf start-time {
                                            type types-operation:operation-timestamp;
                                            description "Time when the operation started its execution.";
                                        }

                                        leaf results-path {
                                            type types-operation:operation-path;
                                            description "Path to the results of the operation formatted as xpath.";
                                        }

                                        leaf status {
                                            type types-operation:operation-status;
                                            description "Status of the operation";
                                        }

                                        leaf-list error-message {
                                            type types-operation:operation-message;
                                            description "Error messages reported during execution of the operation.";
                                        }

                                        leaf-list warning-message {
                                            type types-operation:operation-message;
                                            description "Warning messages reported during execution of the operation.";
                                        }

                                        leaf-list info-message {
                                            type types-operation:operation-message;
                                            description "Info messages reported during execution of the operation.";
                                        }

                                        leaf end-time {
                                            type types-operation:operation-timestamp;
                                            description "Time when the operation ended its execution.";
                                        }

                                    }
                                } // action all

                                container subscriber-interface {
                                    description "Enter the subscriber-interface context";

                                    action all {
                                        description "Reset peak value stats for all subscriber interfaces";

                                        input {

                                            leaf recursive {
                                                type empty;
                                                description "Reset the statistics recursively";
                                            }

                                        }
                                        output {

                                            leaf operation-id {
                                                type types-operation:operation-id;
                                                description "ID assigned to the operation.";
                                            }

                                            leaf start-time {
                                                type types-operation:operation-timestamp;
                                                description "Time when the operation started its execution.";
                                            }

                                            leaf results-path {
                                                type types-operation:operation-path;
                                                description "Path to the results of the operation formatted as xpath.";
                                            }

                                            leaf status {
                                                type types-operation:operation-status;
                                                description "Status of the operation";
                                            }

                                            leaf-list error-message {
                                                type types-operation:operation-message;
                                                description "Error messages reported during execution of the operation.";
                                            }

                                            leaf-list warning-message {
                                                type types-operation:operation-message;
                                                description "Warning messages reported during execution of the operation.";
                                            }

                                            leaf-list info-message {
                                                type types-operation:operation-message;
                                                description "Info messages reported during execution of the operation.";
                                            }

                                            leaf end-time {
                                                type types-operation:operation-timestamp;
                                                description "Time when the operation ended its execution.";
                                            }

                                        }
                                    } // action all

                                    action name {
                                        description "Reset peak values stats for the subscriber interface";

                                        input {

                                            leaf name {
                                                type types-sros:interface-name;
                                                mandatory true;
                                                description "Subscriber interface name";
                                            }

                                            leaf recursive {
                                                type empty;
                                                description "Reset the statistics recursively";
                                            }

                                        }
                                        output {

                                            leaf operation-id {
                                                type types-operation:operation-id;
                                                description "ID assigned to the operation.";
                                            }

                                            leaf start-time {
                                                type types-operation:operation-timestamp;
                                                description "Time when the operation started its execution.";
                                            }

                                            leaf results-path {
                                                type types-operation:operation-path;
                                                description "Path to the results of the operation formatted as xpath.";
                                            }

                                            leaf status {
                                                type types-operation:operation-status;
                                                description "Status of the operation";
                                            }

                                            leaf-list error-message {
                                                type types-operation:operation-message;
                                                description "Error messages reported during execution of the operation.";
                                            }

                                            leaf-list warning-message {
                                                type types-operation:operation-message;
                                                description "Warning messages reported during execution of the operation.";
                                            }

                                            leaf-list info-message {
                                                type types-operation:operation-message;
                                                description "Info messages reported during execution of the operation.";
                                            }

                                            leaf end-time {
                                                type types-operation:operation-timestamp;
                                                description "Time when the operation ended its execution.";
                                            }

                                        }
                                    } // action name

                                } // container subscriber-interface

                                container group-interface {
                                    description "Enter the group-interface context";

                                    action all {
                                        description "Reset peak value statistics for all group interfaces";

                                        output {

                                            leaf operation-id {
                                                type types-operation:operation-id;
                                                description "ID assigned to the operation.";
                                            }

                                            leaf start-time {
                                                type types-operation:operation-timestamp;
                                                description "Time when the operation started its execution.";
                                            }

                                            leaf results-path {
                                                type types-operation:operation-path;
                                                description "Path to the results of the operation formatted as xpath.";
                                            }

                                            leaf status {
                                                type types-operation:operation-status;
                                                description "Status of the operation";
                                            }

                                            leaf-list error-message {
                                                type types-operation:operation-message;
                                                description "Error messages reported during execution of the operation.";
                                            }

                                            leaf-list warning-message {
                                                type types-operation:operation-message;
                                                description "Warning messages reported during execution of the operation.";
                                            }

                                            leaf-list info-message {
                                                type types-operation:operation-message;
                                                description "Info messages reported during execution of the operation.";
                                            }

                                            leaf end-time {
                                                type types-operation:operation-timestamp;
                                                description "Time when the operation ended its execution.";
                                            }

                                        }
                                    } // action all

                                    action name {
                                        description "Reset peak value statistics for the group interface";

                                        input {

                                            leaf name {
                                                type types-sros:interface-name;
                                                mandatory true;
                                                description "Group interface name";
                                            }

                                        }
                                        output {

                                            leaf operation-id {
                                                type types-operation:operation-id;
                                                description "ID assigned to the operation.";
                                            }

                                            leaf start-time {
                                                type types-operation:operation-timestamp;
                                                description "Time when the operation started its execution.";
                                            }

                                            leaf results-path {
                                                type types-operation:operation-path;
                                                description "Path to the results of the operation formatted as xpath.";
                                            }

                                            leaf status {
                                                type types-operation:operation-status;
                                                description "Status of the operation";
                                            }

                                            leaf-list error-message {
                                                type types-operation:operation-message;
                                                description "Error messages reported during execution of the operation.";
                                            }

                                            leaf-list warning-message {
                                                type types-operation:operation-message;
                                                description "Warning messages reported during execution of the operation.";
                                            }

                                            leaf-list info-message {
                                                type types-operation:operation-message;
                                                description "Info messages reported during execution of the operation.";
                                            }

                                            leaf end-time {
                                                type types-operation:operation-timestamp;
                                                description "Time when the operation ended its execution.";
                                            }

                                        }
                                    } // action name

                                } // container group-interface

                            } // list name

                        } // container service

                        action system {
                            description "Reset peak value statistics for the system";

                            input {

                                leaf recursive {
                                    type empty;
                                    description "Reset the statistics recursively";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action system

                    } // container peakvalues

                } // container host-and-session

                container interface {
                    description "Enter the interface context";

                    list service {
                        key "service-name";
                        description "Enter the service list instance";

                        leaf service-name {
                            type types-services:service-name;
                            description "Service name";
                        }

                        action all {
                            description "Reset traffic statistics for all service interfaces";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action group-interface {
                            description "Reset subscriber traffic stats for a group interface";

                            input {

                                leaf name {
                                    type types-sros:interface-name;
                                    mandatory true;
                                    description "Group interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action group-interface

                        action subscriber-interface {
                            description "Reset traffic statistics for the subscriber interface";

                            input {

                                leaf name {
                                    type types-sros:interface-name;
                                    mandatory true;
                                    description "Subscriber interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action subscriber-interface

                    } // list service

                } // container interface

                container gtp {
                    description "Enter the gtp context";

                    action all {
                        description "Reset GTP messaging statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                } // container gtp

                container host-tracking {
                    description "Enter the host-tracking context";

                    container subscriber {
                        description "Enter the subscriber context";

                        action all {
                            description "Reset the host-tracking statistics for all subscribers";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action id {
                            description "Reset the host-tracking stats of the subscriber";

                            input {

                                leaf name {
                                    type leafref {
                                        path "/state:state/state:subscriber-mgmt/state:subscriber/state:subscriber-id";
                                    }
                                    mandatory true;
                                    description "Subscriber ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                    } // container subscriber

                } // container host-tracking

                container pfcp {
                    description "Enter the pfcp context";

                    action association {
                        description "Reset the PFCP statistics for the specified association";

                        input {

                            leaf name {
                                type leafref {
                                    path "/state:state/state:subscriber-mgmt/state:pfcp/state:association/state:name";
                                }
                                mandatory true;
                                description "PFCP association name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action association

                } // container pfcp

                container wlan-gw {
                    description "Enter the wlan-gw context";

                    action cpm-totals {
                        description "Reset the WLAN GW statistics peak values";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action cpm-totals

                } // container wlan-gw

                container radius {
                    description "Enter the radius context";

                    container authentication {
                        description "Enter the authentication context";

                        container coa {
                            description "Enter the coa context";

                            action all {
                                description "Reset RADIUS CoA statistics";

                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action all

                        } // container coa

                    } // container authentication

                } // container radius

                container diameter {
                    description "Enter the diameter context";

                    action application-policy {
                        description "Reset Diameter application policy statistics";

                        input {

                            leaf name {
                                type types-sros:named-item;
                                mandatory true;
                                description "Diameter application policy name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action application-policy

                    container ccrt-replay {
                        description "Enter the ccrt-replay context";

                        action application-policy {
                            description "Reset CCR-T replay stats for the application policy";

                            input {

                                leaf name {
                                    type types-sros:named-item;
                                    mandatory true;
                                    description "Diameter application policy name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action application-policy

                    } // container ccrt-replay

                } // container diameter

            } // container statistics

            container sessions {
                description "Enter the sessions context";

                container pfcp {
                    description "Enter the pfcp context";

                    action session-id {
                        description "Delete the PFCP session with the local SEID";

                        input {

                            leaf local-session-id {
                                type leafref {
                                    path "/state:state/state:subscriber-mgmt/state:pfcp/state:association/state:session/state:local-session-id";
                                }
                                mandatory true;
                                description "Local assigned PFCP session ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action session-id

                    action nat-member {
                        description "Delete PFCP session matching the NAT group member ID";

                        input {

                            leaf id {
                                type leafref {
                                    path "/state:state/state:isa/state:nat-group/state:member/state:id";
                                }
                                mandatory true;
                                description "NAT group member ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action nat-member

                    action sap {
                        description "Delete the PFCP session matching the SAP and MAC";

                        input {

                            leaf sap {
                                type types-sros:sap;
                                mandatory true;
                                description "SAP ID";
                            }

                            leaf mac {
                                type types-sros:ieee-address;
                                mandatory true;
                                description "MAC address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action sap

                } // container pfcp

                container gtp {
                    description "Enter the gtp context";

                    action all {
                        description "Delete all GTP sessions";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    list apn {
                        key "apn";
                        description "Enter the apn list instance";

                        leaf apn {
                            type leafref {
                                path "/state:state/state:subscriber-mgmt/state:gtp/state:apn-policy/state:apn/state:apn-name";
                            }
                            description "Access point name";
                        }

                        action all {
                            description "Delete all GTP sessions associated with the APN";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action imsi {
                            description "Delete the GTP session with the specified IMSI";

                            input {

                                leaf imsi {
                                    type types-cellular:imsi;
                                    mandatory true;
                                    description "International Mobile Subscriber Identity";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action imsi

                    } // list apn

                    action imsi {
                        description "Delete the GTP session with the specified IMSI";

                        input {

                            leaf imsi {
                                type types-cellular:imsi;
                                mandatory true;
                                description "International Mobile Subscriber Identity";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action imsi

                } // container gtp

                container host-tracking {
                    description "Enter the host-tracking context";

                    container subscriber {
                        description "Enter the subscriber context";

                        action all {
                            description "Delete host tracking table entry for all subscribers";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action id {
                            description "Delete host tracking table entry for the subscriber";

                            input {

                                leaf name {
                                    type leafref {
                                        path "/state:state/state:subscriber-mgmt/state:subscriber/state:subscriber-id";
                                    }
                                    mandatory true;
                                    description "Subscriber ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                    } // container subscriber

                } // container host-tracking

                container diameter {
                    description "Enter the diameter context";

                    container ccrt-replay {
                        description "Enter the ccrt-replay context";

                        action application-policy {
                            description "Delete sessions in CCR-T replay mode";

                            input {

                                leaf name {
                                    type types-sros:named-item;
                                    mandatory true;
                                    description "Diameter application policy name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action application-policy

                    } // container ccrt-replay

                } // container diameter

            } // container sessions

        } // container subscriber-management

        container system {
            description "Enter the system context";

            container management-interface {
                description "Enter the management-interface context";

                container remote-management {
                    status obsolete;
                    description "Enter the remote-management context";

                    container managers {
                        status obsolete;
                        description "Enter the managers context";

                    } // container managers

                    container statistics {
                        status obsolete;
                        description "Enter the statistics context";

                    } // container statistics

                } // container remote-management

                container netconf {
                    description "Enter the netconf context";

                    container listen {
                        description "Enter the listen context";

                        action statistics {
                            description "Reset NETCONF listen server statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action statistics

                    } // container listen

                    container call-home {
                        description "Enter the call-home context";

                        container all-client {
                            description "Enter the all-client context";

                            action statistics {
                                description "Reset statistics of all NETCONF call-home clients";

                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action statistics

                        } // container all-client

                        list netconf-client {
                            key "netconf-client";
                            description "Enter the netconf-client list instance";

                            leaf netconf-client {
                                type leafref {
                                    path "/state:state/state:system/state:management-interface/state:netconf/state:call-home/state:netconf-client/state:name";
                                }
                                description "NETCONF client";
                            }

                            action statistics {
                                description "Reset NETCONF call-home client statistics";

                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action statistics

                        } // list netconf-client

                    } // container call-home

                } // container netconf

            } // container management-interface

            container security {
                description "Enter the security context";

                container cpm-filter {
                    description "Enter the cpm-filter context";

                    action ip-filter {
                        description "Reset IP filter information";

                        input {

                            leaf entry {
                                type leafref {
                                    path "/state:state/state:system/state:security/state:cpm-filter/state:ip-filter/state:entry/state:entry-id";
                                }
                                description "Entry ID for IP filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ip-filter

                    action ipv6-filter {
                        description "Reset IPv6 filter information";

                        input {

                            leaf entry {
                                type leafref {
                                    path "/state:state/state:system/state:security/state:cpm-filter/state:ipv6-filter/state:entry/state:entry-id";
                                }
                                description "Entry ID for IPv6 filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ipv6-filter

                    action mac-filter {
                        description "Reset MAC filter information";

                        input {

                            leaf entry {
                                type leafref {
                                    path "/state:state/state:system/state:security/state:cpm-filter/state:mac-filter/state:entry/state:entry-id";
                                }
                                description "Entry ID for the MAC filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mac-filter

                    action cpm-queue {
                        description "Reset CPM queue information";

                        input {

                            leaf queue-id {
                                type leafref {
                                    path "/state:state/state:system/state:security/state:cpm-queue/state:queue/state:queue-id";
                                }
                                mandatory true;
                                description "Queue ID for the CPM queue";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action cpm-queue

                } // container cpm-filter

                container management-access-filter {
                    description "Enter the management-access-filter context";

                    action ip-filter {
                        description "Reset operation on the specified IP filter";

                        input {

                            leaf entry {
                                type leafref {
                                    path "/state:state/state:system/state:security/state:management-access-filter/state:ip-filter/state:entry/state:entry-id";
                                }
                                description "Entry ID for the IP filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ip-filter

                    action ipv6-filter {
                        description "Reset operation on the specified IPv6 filter";

                        input {

                            leaf entry {
                                type leafref {
                                    path "/state:state/state:system/state:security/state:management-access-filter/state:ipv6-filter/state:entry/state:entry-id";
                                }
                                description "Entry ID for the IPv6 filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ipv6-filter

                    action mac-filter {
                        description "Reset operation on the specified MAC filter";

                        input {

                            leaf entry {
                                type leafref {
                                    path "/state:state/state:system/state:security/state:management-access-filter/state:mac-filter/state:entry/state:entry-id";
                                }
                                description "Entry ID for the MAC filter";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mac-filter

                } // container management-access-filter

            } // container security

            container script-control {
                description "Enter the script-control context";

                container script-policy {
                    description "Enter the script-policy context";

                    container completed {
                        description "Enter the completed context";

                        action all {
                            description "Delete script run entries for all script policies";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action policy {
                            description "Delete script run entries for specific policies";

                            input {

                                leaf policy-name {
                                    type leafref {
                                        path "/state:state/state:system/state:script-control/state:script-policy[state:owner=current()/../owner]/state:policy-name";
                                    }
                                    mandatory true;
                                    description "Script-policy name for run history deletion";
                                }

                                leaf owner {
                                    type leafref {
                                        path "/state:state/state:system/state:script-control/state:script-policy[state:policy-name=current()/../policy-name]/state:owner";
                                    }
                                    default "TiMOS CLI";
                                    description "Script-policy owner for run history deletion";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action policy

                    } // container completed

                } // container script-policy

            } // container script-control

            container satellite {
                description "Enter the satellite context";

                list ethernet-satellite {
                    key "satellite-id";
                    description "Enter the ethernet-satellite list instance";

                    leaf satellite-id {
                        type leafref {
                            path "/state:state/state:satellite/state:ethernet-satellite/state:satellite-id";
                        }
                        description "Satellite ID";
                    }

                    action synchronous-interface-timing {
                        description "Reset a failed reference on the Ethernet satellite";

                        input {

                            leaf reference {
                                type enumeration {
                                    enum ref1                           { value 1; }
                                    enum ref2                           { value 2; }
                                }
                                mandatory true;
                                description "Synchronous timing reference";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action synchronous-interface-timing

                } // list ethernet-satellite

            } // container satellite

            container ptp {
                description "Enter the ptp context";

                action clock-recovery {
                    description "Reset PTP clock recovery algorithm";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action clock-recovery

            } // container ptp

            container ntp {
                description "Enter the ntp context";

                action statistics {
                    description "Reset NTP statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

            } // container ntp

            action reboot-required {
                description "Clear the reboot required state";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action reboot-required

        } // container system

        container log {
            description "Enter the log context";

            action log-id {
                description "Reset the specified event log";

                input {

                    leaf name {
                        type leafref {
                            path "/state:state/state:log/state:log-id/state:name";
                        }
                        mandatory true;
                        description "Name of the event log to reset";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action log-id

            container event-handling {
                description "Enter the event-handling context";

                action information {
                    description "Reset general EHS operational data";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action information

                container handlers {
                    description "Enter the handlers context";

                    action all {
                        description "Reset statistics for all EHS handlers";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action handler {
                        description "Reset statistics for a specified EHS handler";

                        input {

                            leaf name {
                                type leafref {
                                    path "/state:state/state:log/state:event-handling/state:handler/state:name";
                                }
                                mandatory true;
                                description "Handler name to reset";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action handler

                } // container handlers

            } // container event-handling

            container log-events {
                description "Enter the log-events context";

                container repeating-events {
                    description "Enter the repeating-events context";

                    action all {
                        description "Reset operation for all repeating log events";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                } // container repeating-events

            } // container log-events

        } // container log

        list router {
            key "router-instance";
            description "Enter the router list instance";

            leaf router-instance {
                type string;
                description "Router name or VPRN service name";
            }

            container dhcp-server {
                description "Enter the dhcp-server context";

                list dhcpv4 {
                    key "server-name";
                    description "Enter the dhcpv4 list instance";

                    leaf server-name {
                        type types-sros:named-item;
                        description "Server name";
                    }

                    action statistics {
                        description "Reset DHCPv4 server statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action statistics

                    container pool-extended-statistics {
                        description "Enter the pool-extended-statistics context";

                        action all {
                            description "Reset extended statistics peak values for all pools";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action pool {
                            description "Reset extended statistics peak values for the pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container pool-extended-statistics

                    container declined-addresses {
                        description "Enter the declined-addresses context";

                        action address {
                            description "Make the specified declined addresses available";

                            input {

                                leaf address {
                                    type types-sros:ipv4-address;
                                    mandatory true;
                                    description "IPv4 address";
                                }

                                leaf mask {
                                    type uint32 {
                                        range "1..32";
                                    }
                                    description "IPv4 address mask";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action address

                        action pool {
                            description "Make declined addresses in the pool available";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container declined-addresses

                    container leases {
                        description "Enter the leases context";

                        action prefix {
                            description "Delete all DHCPv4 leases in the specified prefix";

                            input {

                                leaf prefix {
                                    type types-sros:ipv4-unicast-prefix;
                                    mandatory true;
                                    description "IPv4 prefix";
                                }

                                leaf state {
                                    type enumeration {
                                        enum offered                        { value 1; }
                                        enum stable                         { value 2; }
                                        enum force-renew-pending            { value 3; }
                                        enum remove-pending                 { value 4; }
                                        enum held                           { value 5; }
                                        enum internal                       { value 6; }
                                        enum internal-orphan                { value 7; }
                                        enum internal-offered               { value 8; }
                                        enum internal-held                  { value 9; }
                                        enum sticky                         { value 10; }
                                    }
                                    description "Lease state";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action address {
                            description "Delete the specified DHCPv4 lease";

                            input {

                                leaf address {
                                    type types-sros:ip-address;
                                    mandatory true;
                                    description "IPv4 address";
                                }

                                leaf state {
                                    type enumeration {
                                        enum offered                        { value 1; }
                                        enum stable                         { value 2; }
                                        enum force-renew-pending            { value 3; }
                                        enum remove-pending                 { value 4; }
                                        enum held                           { value 5; }
                                        enum internal                       { value 6; }
                                        enum internal-orphan                { value 7; }
                                        enum internal-offered               { value 8; }
                                        enum internal-held                  { value 9; }
                                        enum sticky                         { value 10; }
                                    }
                                    description "Lease state";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action address

                        action all {
                            description "Delete all DHCPv4 leases";

                            input {

                                leaf state {
                                    type enumeration {
                                        enum offered                        { value 1; }
                                        enum stable                         { value 2; }
                                        enum force-renew-pending            { value 3; }
                                        enum remove-pending                 { value 4; }
                                        enum held                           { value 5; }
                                        enum internal                       { value 6; }
                                        enum internal-orphan                { value 7; }
                                        enum internal-offered               { value 8; }
                                        enum internal-held                  { value 9; }
                                        enum sticky                         { value 10; }
                                    }
                                    description "Lease state";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container leases

                    container failover-pool-statistics {
                        description "Enter the failover-pool-statistics context";

                        action pool {
                            description "Reset failover statistics for the specified pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                        action all {
                            description "Reset failover statistics for all pools";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container failover-pool-statistics

                    container sticky-leases {
                        description "Enter the sticky-leases context";

                        action host-name-prefix {
                            description "Delete sticky leases associated with hostnames containing the prefix";

                            input {

                                leaf host-name-prefix {
                                    type types-sros:named-item;
                                    mandatory true;
                                    description "Hostname prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action host-name-prefix

                        action host-name {
                            description "Delete the sticky lease associated with the hostname";

                            input {

                                leaf host-name {
                                    type types-sros:named-item;
                                    mandatory true;
                                    description "Hostname";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action host-name

                    } // container sticky-leases

                    container subnet-extended-statistics {
                        description "Enter the subnet-extended-statistics context";

                        action prefix {
                            description "Reset extended statistics peak values for the specified prefix";

                            input {

                                leaf prefix {
                                    type types-sros:ipv4-unicast-prefix;
                                    mandatory true;
                                    description "IPv4 prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action pool {
                            description "Reset extended statistics peak values for all subnets in the pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container subnet-extended-statistics

                } // list dhcpv4

                list dhcpv6 {
                    key "server-name";
                    description "Enter the dhcpv6 list instance";

                    leaf server-name {
                        type types-sros:named-item;
                        description "Server name";
                    }

                    action statistics {
                        description "Reset DHCPv6 server statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action statistics

                    container pool-extended-statistics {
                        description "Enter the pool-extended-statistics context";

                        action all {
                            description "Reset extended statistics peak values for all pools";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action pool {
                            description "Reset extended statistics peak values for the specified pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container pool-extended-statistics

                    container leases {
                        description "Enter the leases context";

                        action prefix {
                            description "Delete all DHCPv6 leases in the specified prefix";

                            input {

                                leaf prefix {
                                    type types-sros:ipv6-prefix;
                                    mandatory true;
                                    description "IPv6 prefix";
                                }

                                leaf state {
                                    type enumeration {
                                        enum advertised                     { value 1; }
                                        enum stable                         { value 2; }
                                        enum remove-pending                 { value 4; }
                                        enum held                           { value 5; }
                                        enum internal                       { value 6; }
                                        enum internal-orphan                { value 7; }
                                        enum internal-offered               { value 8; }
                                        enum internal-held                  { value 9; }
                                    }
                                    description "Lease state";
                                }

                                leaf type {
                                    type enumeration {
                                        enum pd                             { value 1; }
                                        enum slaac                          { value 2; }
                                        enum wan                            { value 3; }
                                    }
                                    description "Lease type";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action address {
                            description "Delete the specified DHCPv6 lease";

                            input {

                                leaf address {
                                    type types-sros:ip-address;
                                    mandatory true;
                                    description "IPv6 address";
                                }

                                leaf state {
                                    type enumeration {
                                        enum advertised                     { value 1; }
                                        enum stable                         { value 2; }
                                        enum remove-pending                 { value 4; }
                                        enum held                           { value 5; }
                                        enum internal                       { value 6; }
                                        enum internal-orphan                { value 7; }
                                        enum internal-offered               { value 8; }
                                        enum internal-held                  { value 9; }
                                    }
                                    description "Lease state";
                                }

                                leaf type {
                                    type enumeration {
                                        enum pd                             { value 1; }
                                        enum slaac                          { value 2; }
                                        enum wan                            { value 3; }
                                    }
                                    description "Lease type";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action address

                        action all {
                            description "Delete all DHCPv6 leases";

                            input {

                                leaf state {
                                    type enumeration {
                                        enum advertised                     { value 1; }
                                        enum stable                         { value 2; }
                                        enum remove-pending                 { value 4; }
                                        enum held                           { value 5; }
                                        enum internal                       { value 6; }
                                        enum internal-orphan                { value 7; }
                                        enum internal-offered               { value 8; }
                                        enum internal-held                  { value 9; }
                                    }
                                    description "Lease state";
                                }

                                leaf type {
                                    type enumeration {
                                        enum pd                             { value 1; }
                                        enum slaac                          { value 2; }
                                        enum wan                            { value 3; }
                                    }
                                    description "Lease type";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                container results {
                                    description "Enter the results context";

                                    leaf cleared-leases {
                                        type uint32;
                                        description "cleared-leases";
                                    }

                                } // container results

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container leases

                    container failover-pool-statistics {
                        description "Enter the failover-pool-statistics context";

                        action pool {
                            description "Reset failover statistics for the specified pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                        action all {
                            description "Reset failover statistics for all pools";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container failover-pool-statistics

                    container pool-threshold-statistics {
                        description "Enter the pool-threshold-statistics context";

                        action pool {
                            description "Reset threshold statistics peak values for the pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                        action all {
                            description "Reset threshold statistics peak values for all pools";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container pool-threshold-statistics

                    container prefix-extended-statistics {
                        description "Enter the prefix-extended-statistics context";

                        action prefix {
                            description "Reset extended statistics peak values for the prefix";

                            input {

                                leaf prefix {
                                    type types-sros:ipv6-prefix;
                                    mandatory true;
                                    description "IPv6 prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action pool {
                            description "Reset extended statistics peak values for all prefixes in the pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container prefix-extended-statistics

                    container prefix-threshold-statistics {
                        description "Enter the prefix-threshold-statistics context";

                        action prefix {
                            description "Reset threshold statistics peak values for the specified prefix";

                            input {

                                leaf prefix {
                                    type types-sros:ipv6-prefix;
                                    mandatory true;
                                    description "IPv6 prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action pool {
                            description "Reset threshold statistics peak values for all prefixes in the pool";

                            input {

                                leaf pool {
                                    type types-sros:named-item;
                                    mandatory true;
                                    description "Pool name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action pool

                    } // container prefix-threshold-statistics

                } // list dhcpv6

            } // container dhcp-server

            list interface {
                key "interface-name";
                description "Enter the interface list instance";

                leaf interface-name {
                    type types-sros:interface-name;
                    description "Interface name";
                }

                action statistics {
                    description "Reset the interface traffic statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action urpf-statistics {
                    description "Reset the interface uRPF statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action urpf-statistics

                action hold-time {
                    description "Reset the IP interface activation hold timers";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action hold-time

                container mac {
                    description "Enter the mac context";

                    action all {
                        description "Reset all MAC addresses for the specified interface";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action address {
                        description "Reset specified MAC address from associated interface";

                        input {

                            leaf mac-address {
                                type yang:mac-address;
                                mandatory true;
                                description "MAC address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action address

                } // container mac

                container policy-accounting {
                    description "Enter the policy-accounting context";

                    action all {
                        description "Reset all the policy-accounting statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action class {
                        description "Reset the specified policy-accounting class";

                        input {

                            leaf name {
                                type enumeration {
                                    enum source-class                   { value 0; }
                                    enum destination-class              { value 1; }
                                }
                                mandatory true;
                                description "Policy-accounting class counters to reset";
                            }

                            choice index-or-all {
                                mandatory true;
                                case all {

                                    leaf all {
                                        type empty;
                                        description "Reset all policy-accounting class indexes";
                                    }

                                }
                                case index {

                                    leaf index {
                                        type uint32 {
                                            range "1..255";
                                        }
                                        description "Policy-accounting class index";
                                    }

                                }
                            }
                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action class

                    container policer {
                        description "Enter the policer context";

                        action all {
                            description "Reset all the policer statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action index {
                            description "Reset the specified policer";

                            input {

                                leaf policer-index {
                                    type uint32 {
                                        range "1..63";
                                    }
                                    mandatory true;
                                    description "Policer index";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action index

                    } // container policer

                } // container policy-accounting

            } // list interface

            container arp {
                description "Enter the arp context";

                action all {
                    description "Reset all ARP cache entries";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action interface {
                    description "Reset ARP cache entries for the interface";

                    input {

                        leaf interface-name {
                            type types-sros:interface-name;
                            description "Interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action interface

                action address {
                    description "Reset the ARP cache entries for the IPv4 address";

                    input {

                        leaf ipv4-address {
                            type types-sros:ipv4-address;
                            description "IPv4 address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action address

            } // container arp

            container neighbor {
                description "Enter the neighbor context";

                action all {
                    description "Reset information for all neighbors of all interfaces";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action interface {
                    description "Reset all neighbors of the router interface";

                    input {

                        leaf interface-name {
                            type types-sros:interface-name;
                            description "Interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action interface

                action address {
                    description "Reset the IPv6 neighbor information";

                    input {

                        leaf ipv6-address {
                            type types-sros:ip-address-with-zone;
                            description "IPv6 address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action address

            } // container neighbor

            container icmp {
                description "Enter the icmp context";

                action all {
                    description "Reset all ICMP router statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action global {
                    description "Reset global router statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action global

                action interface {
                    description "Reset ICMP statistics for the interface";

                    input {

                        leaf interface-name {
                            type types-sros:interface-name;
                            description "Interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action interface

            } // container icmp

            container icmp-redirect-route {
                description "Enter the icmp-redirect-route context";

                action all {
                    description "Reset all routes";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action address {
                    description "Reset the routes associated with the IP address";

                    input {

                        leaf ipv4-address {
                            type types-sros:ipv4-address;
                            description "IPv4 address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action address

            } // container icmp-redirect-route

            container icmp6 {
                description "Enter the icmp6 context";

                action all {
                    description "Reset all ICMPv6 router statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action global {
                    description "Reset ICMPv6 global router statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action global

                action interface {
                    description "Reset ICMPv6 router statistics of the interface";

                    input {

                        leaf interface-name {
                            type types-sros:interface-name;
                            description "Interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action interface

            } // container icmp6

            container icmp6-redirect-route {
                description "Enter the icmp6-redirect-route context";

                action all {
                    description "Reset all routes";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action address {
                    description "Reset routes associated with the IPv6 address";

                    input {

                        leaf ipv6-address {
                            type types-sros:ipv6-address;
                            description "IPv6 address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action address

            } // container icmp6-redirect-route

            container forwarding-table {
                description "Enter the forwarding-table context";

                action all {
                    description "Reset all router forwarding tables";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action all

                action slot {
                    description "Reset the router forwarding table for the IOM slot";

                    input {

                        leaf slot-number {
                            type leafref {
                                path "/state:state/state:card/state:slot-number";
                            }
                            description "Slot number";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action slot

            } // container forwarding-table

            action grt-lookup {
                description "Re-evaluate the route policies for GRT";

                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action grt-lookup

            container vrrp {
                description "Enter the vrrp context";

                container instances {
                    description "Enter the instances context";

                    list interface {
                        key "interface-name";
                        description "Enter the interface list instance";

                        leaf interface-name {
                            type types-sros:interface-name;
                            description "Interface name";
                        }

                        action all-vrid {
                            description "Reset all VRRP instances on the interface";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all-vrid

                        container ipv4 {
                            description "Enter the ipv4 context";

                            action vrid {
                                description "Reset the IPv4 VRRP instance";

                                input {

                                    leaf virtual-router-id {
                                        type int32;
                                        description "VRRP instance to reset";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action vrid

                        } // container ipv4

                        container ipv6 {
                            description "Enter the ipv6 context";

                            action vrid {
                                description "Reset the IPv6 VRRP instance";

                                input {

                                    leaf virtual-router-id {
                                        type int32;
                                        description "VRRP instance to reset";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action vrid

                        } // container ipv6

                    } // list interface

                } // container instances

                container statistics {
                    description "Enter the statistics context";

                    action all-statistics {
                        description "Reset statistics of VRRP instances on all interfaces";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-statistics

                    list interface {
                        key "interface-name";
                        description "Enter the interface list instance";

                        leaf interface-name {
                            type types-sros:interface-name;
                            description "Interface name";
                        }

                        action all-vrid {
                            description "Reset statistics of all VRRP instances on the interface";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all-vrid

                        container ipv4 {
                            description "Enter the ipv4 context";

                            action vrid {
                                description "Reset statistics of the IPv4 VRRP instance";

                                input {

                                    leaf virtual-router-id {
                                        type int32;
                                        description "VRRP instance to reset";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action vrid

                        } // container ipv4

                        container ipv6 {
                            description "Enter the ipv6 context";

                            action vrid {
                                description "Reset statistics of the IPv6 VRRP instance";

                                input {

                                    leaf virtual-router-id {
                                        type int32;
                                        description "VRRP instance to reset";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action vrid

                        } // container ipv6

                    } // list interface

                } // container statistics

            } // container vrrp

            list isis {
                key "isis-instance";
                description "Enter the isis list instance";

                leaf isis-instance {
                    type leafref {
                        path "/state:state/state:router[state:router-name=current()/../../router-instance]/state:isis/state:isis-instance";
                    }
                    description "IS-IS instance";
                }

                container adjacency {
                    description "Enter the adjacency context";

                    action all-adjacencies {
                        description "Reset all IS-IS adjacencies";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-adjacencies

                    action system-id {
                        description "Reset the IS-IS adjacency to a node";

                        input {

                            leaf system-id {
                                type types-igp:system-id;
                                mandatory true;
                                description "System ID for a specific node";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action system-id

                } // container adjacency

                container database {
                    description "Enter the database context";

                    action all-databases {
                        description "Reset all IS-IS databases system wide";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-databases

                    action system-id {
                        description "Reset the IS-IS database for a node";

                        input {

                            leaf system-id {
                                type types-igp:system-id;
                                mandatory true;
                                description "System ID for a specific node";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action system-id

                } // container database

                action export {
                    description "Reset and re-evaluate IS-IS route policies";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action export

                action overload {
                    description "Reset the IS-IS overload";

                    input {

                        leaf overload-type {
                            type enumeration {
                                enum fib                            { value 6; }
                                enum rtm                            { value 7; }
                                enum prefix-limit                   { value 8; }
                            }
                            mandatory true;
                            description "Overload type";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action overload

                container sid-egress-stats {
                    description "Enter the sid-egress-stats context";

                    container adj {
                        description "Enter the adj context";

                        action interface {
                            description "Reset adjacency SID statistics for an interface";

                            input {

                                leaf interface-name {
                                    type string;
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                        action all {
                            description "Reset all egress SID statistics for all adjacencies";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container adj

                    container adj-set {
                        description "Enter the adj-set context";

                        action id {
                            description "Reset adjacency set ID";

                            input {

                                leaf id {
                                    type leafref {
                                        path "/state:state/state:router[state:router-name=current()/../../../../../router-instance]/state:isis[state:isis-instance=current()/../../../../isis-instance]/state:segment-routing/state:adjacency-set/state:id";
                                        require-instance "false";
                                    }
                                    mandatory true;
                                    description "Adjacency set ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                        action all {
                            description "Reset egress SID statistics for all adjacency sets";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container adj-set

                    action all {
                        description "Reset all egress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action prefix {
                            description "Reset egress statistics for a node prefix SID";

                            input {

                                leaf ip-prefix-prefix-length {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action all {
                            description "Reset all egress node SID statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container node

                } // container sid-egress-stats

                container sid-ingress-stats {
                    description "Enter the sid-ingress-stats context";

                    container adj {
                        description "Enter the adj context";

                        action interface {
                            description "Reset ingress SID statistics for an adjacency";

                            input {

                                leaf interface-name {
                                    type string;
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                        action all {
                            description "Reset ingress SID statistics for all adjacencies";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container adj

                    container adj-set {
                        description "Enter the adj-set context";

                        action id {
                            description "Reset ingress statistics for the adjacency set ID";

                            input {

                                leaf id {
                                    type leafref {
                                        path "/state:state/state:router[state:router-name=current()/../../../../../router-instance]/state:isis[state:isis-instance=current()/../../../../isis-instance]/state:segment-routing/state:adjacency-set/state:id";
                                        require-instance "false";
                                    }
                                    mandatory true;
                                    description "Adjacency set ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                        action all {
                            description "Reset ingress SID statistics for all adjacency sets";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container adj-set

                    action all {
                        description "Reset all ingress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action prefix {
                            description "Reset ingress statistics for a node prefix SID";

                            input {

                                leaf ip-prefix-prefix-length {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                        action all {
                            description "Reset all ingress node SID statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container node

                } // container sid-ingress-stats

                action spf-log {
                    description "Reset the IS-IS SPF log";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action spf-log

                action statistics {
                    description "Reset IS-IS statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

            } // list isis

            list ospf {
                key "ospf-instance";
                description "Enter the ospf list instance";

                leaf ospf-instance {
                    type uint32;
                    description "OSPF instance";
                }

                action database {
                    description "Reset and refresh LSAs";

                    input {

                        leaf purge {
                            type empty;
                            description "Reset LSAs";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action database

                action export {
                    description "Reset and re-evaluate export policies";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action export

                action overload {
                    description "Reset the OSPF overload";

                    input {

                        leaf overload-type {
                            type enumeration {
                                enum fib                            { value 6; }
                                enum rtm                            { value 7; }
                                enum rtr-adv-lsa-limit              { value 8; }
                            }
                            mandatory true;
                            description "Overload type";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action overload

                action statistics {
                    description "Reset OSPF statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action neighbor {
                    description "Reset neighbor adjacencies";

                    input {

                        leaf router-id {
                            type types-sros:ipv4-address;
                            description "Neighbor router ID";
                        }

                        leaf interface-name {
                            type string;
                            description "Neighbor interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action neighbor

                container sid-egress-stats {
                    description "Enter the sid-egress-stats context";

                    container adj {
                        description "Enter the adj context";

                        action all {
                            description "Reset egress statistics for all adjacency SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action interface {
                            description "Reset egress adjacency SID statistics for an interface";

                            input {

                                leaf interface-name {
                                    type leafref {
                                        path "/state:state/state:router[state:router-name=current()/../../../../../router-instance]/state:ospf[state:ospf-instance=current()/../../../../ospf-instance]/state:area/state:interface/state:interface-name";
                                    }
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                    } // container adj

                    container adj-set {
                        description "Enter the adj-set context";

                        action all {
                            description "Reset egress statistics for all adjacency sets";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action id {
                            description "Reset egress statistics for an adjacency set";

                            input {

                                leaf id {
                                    type leafref {
                                        path "/state:state/state:router[state:router-name=current()/../../../../../router-instance]/state:ospf[state:ospf-instance=current()/../../../../ospf-instance]/state:segment-routing/state:adjacency-set/state:id";
                                    }
                                    mandatory true;
                                    description "Adjacency set ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                    } // container adj-set

                    action all {
                        description "Reset all egress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action all {
                            description "Reset egress statistics for all prefix SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action prefix {
                            description "Reset egress SID statistics for a prefix";

                            input {

                                leaf prefix {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                    } // container node

                } // container sid-egress-stats

                container sid-ingress-stats {
                    description "Enter the sid-ingress-stats context";

                    container adj {
                        description "Enter the adj context";

                        action all {
                            description "Reset ingress statistics for all adjacency SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action interface {
                            description "Reset ingress adjacency SID statistics on an interface";

                            input {

                                leaf interface-name {
                                    type leafref {
                                        path "/state:state/state:router[state:router-name=current()/../../../../../router-instance]/state:ospf[state:ospf-instance=current()/../../../../ospf-instance]/state:area/state:interface/state:interface-name";
                                    }
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                    } // container adj

                    container adj-set {
                        description "Enter the adj-set context";

                        action all {
                            description "Reset ingress statistics for all adjacency sets";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action id {
                            description "Reset ingress statistics for a specific adjacency set";

                            input {

                                leaf id {
                                    type leafref {
                                        path "/state:state/state:router[state:router-name=current()/../../../../../router-instance]/state:ospf[state:ospf-instance=current()/../../../../ospf-instance]/state:segment-routing/state:adjacency-set/state:id";
                                    }
                                    mandatory true;
                                    description "Adjacency set ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action id

                    } // container adj-set

                    action all {
                        description "Reset all ingress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action all {
                            description "Reset ingress statistics for all prefix SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action prefix {
                            description "Reset ingress statistics for a prefix SID";

                            input {

                                leaf prefix {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                    } // container node

                } // container sid-ingress-stats

            } // list ospf

            list ospf3 {
                key "ospf-instance";
                description "Enter the ospf3 list instance";

                leaf ospf-instance {
                    type uint32;
                    description "OSPFv3 instance";
                }

                action database {
                    description "Reset and refresh LSAs";

                    input {

                        leaf purge {
                            type empty;
                            description "Reset LSAs";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action database

                action export {
                    description "Reset and re-evaluate export policies";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action export

                action overload {
                    description "Reset the OSPF overload";

                    input {

                        leaf overload-type {
                            type enumeration {
                                enum fib                            { value 6; }
                                enum rtm                            { value 7; }
                                enum rtr-adv-lsa-limit              { value 8; }
                            }
                            mandatory true;
                            description "Overload type";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action overload

                action statistics {
                    description "Reset OSPF statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action neighbor {
                    description "Reset neighbor adjacencies";

                    input {

                        leaf router-id {
                            type types-sros:ipv4-address;
                            description "Router ID of the neighbor to reset";
                        }

                        leaf interface-name {
                            type string;
                            description "Neighbor interface name";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action neighbor

                container sid-egress-stats {
                    description "Enter the sid-egress-stats context";

                    container adj {
                        description "Enter the adj context";

                        action all {
                            description "Reset egress statistics for all adjacency SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action interface {
                            description "Reset statistics for adjacency SIDs on an interface";

                            input {

                                leaf interface-name {
                                    type leafref {
                                        path "/state:state/state:router[state:router-name=current()/../../../../../router-instance]/state:ospf3[state:ospf-instance=current()/../../../../ospf-instance]/state:area/state:interface/state:interface-name";
                                    }
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                    } // container adj

                    action all {
                        description "Reset all egress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action all {
                            description "Reset egress statistics for all prefix SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action prefix {
                            description "Reset egress statistics for SIDs of a specific prefix";

                            input {

                                leaf prefix {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                    } // container node

                } // container sid-egress-stats

                container sid-ingress-stats {
                    description "Enter the sid-ingress-stats context";

                    container adj {
                        description "Enter the adj context";

                        action all {
                            description "Reset ingress statistics for all adjacency SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action interface {
                            description "Reset statistics for adjacency SIDs on an interface";

                            input {

                                leaf interface-name {
                                    type leafref {
                                        path "/state:state/state:router[state:router-name=current()/../../../../../router-instance]/state:ospf3[state:ospf-instance=current()/../../../../ospf-instance]/state:area/state:interface/state:interface-name";
                                    }
                                    mandatory true;
                                    description "Interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action interface

                    } // container adj

                    action all {
                        description "Reset all ingress SID statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    container node {
                        description "Enter the node context";

                        action all {
                            description "Reset ingress SID statistics for all prefix SIDs";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action prefix {
                            description "Reset ingress statistics for specific prefix SIDs";

                            input {

                                leaf prefix {
                                    type union {
                                        type types-sros:ip-address;
                                        type types-sros:ip-prefix;
                                    }
                                    mandatory true;
                                    description "Node prefix";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action prefix

                    } // container node

                } // container sid-ingress-stats

            } // list ospf3

            container bfd {
                description "Enter the bfd context";

                container session {
                    description "Enter the session context";

                    container point-to-point {
                        description "Enter the point-to-point context";

                        action session-key {
                            description "Reset information for the session key";

                            input {

                                leaf src {
                                    type types-sros:ip-address;
                                    mandatory true;
                                    description "Source address";
                                }

                                leaf dst {
                                    type types-sros:ip-address;
                                    mandatory true;
                                    description "Destination address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container point-to-point

                    container point-to-multipoint {
                        description "Enter the point-to-multipoint context";

                        action p2mp-interface-name {
                            description "Reset information for the P2MP interface";

                            input {

                                leaf p2mp-interface-name {
                                    type string;
                                    mandatory true;
                                    description "P2MP interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action p2mp-interface-name

                    } // container point-to-multipoint

                    container mpls-tp {
                        description "Enter the mpls-tp context";

                        action lsp-id {
                            description "Reset information for the LSP ID";

                            input {

                                leaf lsp-name {
                                    type types-sros:string-not-all-spaces {
                                        length "1..256";
                                    }
                                    description "LSP name";
                                }

                                leaf path {
                                    type enumeration {
                                        enum working                        { value 0; }
                                        enum protecting                     { value 1; }
                                    }
                                    mandatory true;
                                    description "Path status";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action lsp-id

                    } // container mpls-tp

                    container lsp-ldp {
                        description "Enter the lsp-ldp context";

                        container head {
                            description "Enter the head context";

                            action session-key {
                                description "Reset information for the session key";

                                input {

                                    leaf src-ip {
                                        type types-sros:ip-address;
                                        mandatory true;
                                        description "Source address";
                                    }

                                    leaf prefix {
                                        type types-sros:ip-prefix;
                                        mandatory true;
                                        description "Prefix";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                        } // container head

                        container tail {
                            description "Enter the tail context";

                            action session-key {
                                description "Reset information for the session key";

                                input {

                                    leaf dst-ip {
                                        type types-sros:ip-address;
                                        mandatory true;
                                        description "Destination address";
                                    }

                                    leaf prefix {
                                        type types-sros:ip-prefix;
                                        mandatory true;
                                        description "Prefix";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                        } // container tail

                    } // container lsp-ldp

                    container lsp-rsvp {
                        description "Enter the lsp-rsvp context";

                        container head {
                            description "Enter the head context";

                            action session-key {
                                description "Reset information for the session key";

                                input {

                                    leaf src-ip {
                                        type types-sros:ip-address;
                                        mandatory true;
                                        description "Source address";
                                    }

                                    leaf dst-ip {
                                        type types-sros:ip-address;
                                        mandatory true;
                                        description "Destination address";
                                    }

                                    leaf tunnel-id {
                                        type uint32;
                                        mandatory true;
                                        description "Tunnel ID";
                                    }

                                    leaf lsp-id {
                                        type uint32;
                                        mandatory true;
                                        description "LSP ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                            action rsvp-session-name {
                                description "Reset information for the RSVP session name";

                                input {

                                    leaf rsvp-session-name {
                                        type types-sros:string-not-all-spaces {
                                            length "1..256";
                                        }
                                        mandatory true;
                                        description "RSVP session name";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action rsvp-session-name

                        } // container head

                        container tail {
                            description "Enter the tail context";

                            action session-key {
                                description "Reset information for the session key";

                                input {

                                    leaf src-ip {
                                        type types-sros:ip-address;
                                        mandatory true;
                                        description "Source address";
                                    }

                                    leaf dst-ip {
                                        type types-sros:ip-address;
                                        mandatory true;
                                        description "Destination address";
                                    }

                                    leaf tunnel-id {
                                        type uint32;
                                        mandatory true;
                                        description "Tunnel ID";
                                    }

                                    leaf lsp-id {
                                        type uint32;
                                        mandatory true;
                                        description "LSP ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                            action rsvp-session-name {
                                description "Reset information for the RSVP session name";

                                input {

                                    leaf rsvp-session-name {
                                        type types-sros:string-not-all-spaces {
                                            length "1..256";
                                        }
                                        mandatory true;
                                        description "RSVP session name";
                                    }

                                    leaf sender-ip {
                                        type types-sros:ip-address;
                                        mandatory true;
                                        description "RSVP session sender IP address";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action rsvp-session-name

                        } // container tail

                    } // container lsp-rsvp

                    container seamless-lsp-path {
                        description "Enter the seamless-lsp-path context";

                        action all {
                            description "Reset all sessions";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action session-key {
                            description "Reset information for the session key";

                            input {

                                leaf lsp-index {
                                    type uint32;
                                    mandatory true;
                                    description "LSP index";
                                }

                                leaf path-lspid {
                                    type uint32;
                                    mandatory true;
                                    description "LSP path ID";
                                }

                                leaf prefix {
                                    type types-sros:ip-prefix;
                                    mandatory true;
                                    description "Prefix";
                                }

                                leaf src-ip {
                                    type types-sros:ip-address;
                                    mandatory true;
                                    description "Source address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container seamless-lsp-path

                    container seamless-sr-policy {
                        description "Enter the seamless-sr-policy context";

                        action all {
                            description "Reset all sessions";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action session-key {
                            description "Reset information for the session key";

                            input {

                                leaf lsp-index {
                                    type uint32;
                                    mandatory true;
                                    description "LSP index";
                                }

                                leaf path-lspid {
                                    type uint32;
                                    mandatory true;
                                    description "LSP path ID";
                                }

                                leaf prefix {
                                    type types-sros:ip-prefix;
                                    mandatory true;
                                    description "Prefix";
                                }

                                leaf src-ip {
                                    type types-sros:ip-address;
                                    mandatory true;
                                    description "Source address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container seamless-sr-policy

                } // container session

                container statistics {
                    description "Enter the statistics context";

                    container point-to-point {
                        description "Enter the point-to-point context";

                        action session-key {
                            description "Reset information for the session key";

                            input {

                                leaf src {
                                    type types-sros:ip-address;
                                    mandatory true;
                                    description "Source address";
                                }

                                leaf dst {
                                    type types-sros:ip-address;
                                    mandatory true;
                                    description "Destination address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container point-to-point

                    container point-to-multipoint {
                        description "Enter the point-to-multipoint context";

                        action p2mp-interface-name {
                            description "Reset information for the P2MP interface";

                            input {

                                leaf p2mp-interface-name {
                                    type string;
                                    mandatory true;
                                    description "P2MP interface name";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action p2mp-interface-name

                    } // container point-to-multipoint

                    container mpls-tp {
                        description "Enter the mpls-tp context";

                        action lsp-id {
                            description "Reset information for the LSP ID";

                            input {

                                leaf lsp-name {
                                    type types-sros:string-not-all-spaces {
                                        length "1..256";
                                    }
                                    description "LSP name";
                                }

                                leaf path {
                                    type enumeration {
                                        enum working                        { value 0; }
                                        enum protecting                     { value 1; }
                                    }
                                    mandatory true;
                                    description "Path status";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action lsp-id

                    } // container mpls-tp

                    container lsp-ldp {
                        description "Enter the lsp-ldp context";

                        container head {
                            description "Enter the head context";

                            action session-key {
                                description "Reset information for the session key";

                                input {

                                    leaf src-ip {
                                        type types-sros:ip-address;
                                        mandatory true;
                                        description "Source address";
                                    }

                                    leaf prefix {
                                        type types-sros:ip-prefix;
                                        mandatory true;
                                        description "Prefix";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                        } // container head

                        container tail {
                            description "Enter the tail context";

                            action session-key {
                                description "Reset information for the session key";

                                input {

                                    leaf dst-ip {
                                        type types-sros:ip-address;
                                        mandatory true;
                                        description "Destination address";
                                    }

                                    leaf prefix {
                                        type types-sros:ip-prefix;
                                        mandatory true;
                                        description "Prefix";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                        } // container tail

                    } // container lsp-ldp

                    container lsp-rsvp {
                        description "Enter the lsp-rsvp context";

                        container head {
                            description "Enter the head context";

                            action session-key {
                                description "Reset information for the session key";

                                input {

                                    leaf src-ip {
                                        type types-sros:ip-address;
                                        mandatory true;
                                        description "Source address";
                                    }

                                    leaf dst-ip {
                                        type types-sros:ip-address;
                                        mandatory true;
                                        description "Destination address";
                                    }

                                    leaf tunnel-id {
                                        type uint32;
                                        mandatory true;
                                        description "Tunnel ID";
                                    }

                                    leaf lsp-id {
                                        type uint32;
                                        mandatory true;
                                        description "LSP ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                            action rsvp-session-name {
                                description "Reset information for the RSVP session name";

                                input {

                                    leaf rsvp-session-name {
                                        type types-sros:string-not-all-spaces {
                                            length "1..256";
                                        }
                                        mandatory true;
                                        description "RSVP session name";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action rsvp-session-name

                        } // container head

                        container tail {
                            description "Enter the tail context";

                            action session-key {
                                description "Reset information for the session key";

                                input {

                                    leaf src-ip {
                                        type types-sros:ip-address;
                                        mandatory true;
                                        description "Source address";
                                    }

                                    leaf dst-ip {
                                        type types-sros:ip-address;
                                        mandatory true;
                                        description "Destination address";
                                    }

                                    leaf tunnel-id {
                                        type uint32;
                                        mandatory true;
                                        description "Tunnel ID";
                                    }

                                    leaf lsp-id {
                                        type uint32;
                                        mandatory true;
                                        description "LSP ID";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action session-key

                            action rsvp-session-name {
                                description "Reset information for the RSVP session name";

                                input {

                                    leaf rsvp-session-name {
                                        type types-sros:string-not-all-spaces {
                                            length "1..256";
                                        }
                                        mandatory true;
                                        description "RSVP session name";
                                    }

                                    leaf sender-ip {
                                        type types-sros:ip-address;
                                        mandatory true;
                                        description "RSVP session sender IP address";
                                    }

                                }
                                output {

                                    leaf operation-id {
                                        type types-operation:operation-id;
                                        description "ID assigned to the operation.";
                                    }

                                    leaf start-time {
                                        type types-operation:operation-timestamp;
                                        description "Time when the operation started its execution.";
                                    }

                                    leaf results-path {
                                        type types-operation:operation-path;
                                        description "Path to the results of the operation formatted as xpath.";
                                    }

                                    leaf status {
                                        type types-operation:operation-status;
                                        description "Status of the operation";
                                    }

                                    leaf-list error-message {
                                        type types-operation:operation-message;
                                        description "Error messages reported during execution of the operation.";
                                    }

                                    leaf-list warning-message {
                                        type types-operation:operation-message;
                                        description "Warning messages reported during execution of the operation.";
                                    }

                                    leaf-list info-message {
                                        type types-operation:operation-message;
                                        description "Info messages reported during execution of the operation.";
                                    }

                                    leaf end-time {
                                        type types-operation:operation-timestamp;
                                        description "Time when the operation ended its execution.";
                                    }

                                }
                            } // action rsvp-session-name

                        } // container tail

                    } // container lsp-rsvp

                    container seamless-lsp-path {
                        description "Enter the seamless-lsp-path context";

                        action all {
                            description "Reset all sessions";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action session-key {
                            description "Reset information for the session key";

                            input {

                                leaf lsp-index {
                                    type uint32;
                                    mandatory true;
                                    description "LSP index";
                                }

                                leaf path-lspid {
                                    type uint32;
                                    mandatory true;
                                    description "LSP path ID";
                                }

                                leaf prefix {
                                    type types-sros:ip-prefix;
                                    mandatory true;
                                    description "Prefix";
                                }

                                leaf src-ip {
                                    type types-sros:ip-address;
                                    mandatory true;
                                    description "Source address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container seamless-lsp-path

                    container seamless-sr-policy {
                        description "Enter the seamless-sr-policy context";

                        action all {
                            description "Reset all sessions";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action session-key {
                            description "Reset information for the session key";

                            input {

                                leaf lsp-index {
                                    type uint32;
                                    mandatory true;
                                    description "LSP index";
                                }

                                leaf path-lspid {
                                    type uint32;
                                    mandatory true;
                                    description "LSP path ID";
                                }

                                leaf prefix {
                                    type types-sros:ip-prefix;
                                    mandatory true;
                                    description "Prefix";
                                }

                                leaf src-ip {
                                    type types-sros:ip-address;
                                    mandatory true;
                                    description "Source address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action session-key

                    } // container seamless-sr-policy

                } // container statistics

            } // container bfd

            container segment-routing {
                description "Enter the segment-routing context";

                container sr-policies {
                    description "Enter the sr-policies context";

                    action sr-policies-ingress-statistics {
                        description "Reset ingress traffic statistics";

                        input {

                            leaf color {
                                type leafref {
                                    path "/state:state/state:router[state:router-name=current()/../../../../router-instance]/state:segment-routing/state:sr-policies/state:sr-policy-ingress-statistics/state:color";
                                    require-instance "false";
                                }
                                mandatory true;
                                description "Color for the SR policy";
                            }

                            leaf endpoint {
                                type leafref {
                                    path "/state:state/state:router[state:router-name=current()/../../../../router-instance]/state:segment-routing/state:sr-policies/state:sr-policy-ingress-statistics[state:color=current()/../color]/state:endpoint";
                                    require-instance "false";
                                }
                                mandatory true;
                                description "Endpoint of the SR policy";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action sr-policies-ingress-statistics

                    action sr-policies-egress-statistics {
                        description "Reset egress traffic statistics";

                        input {

                            leaf color {
                                type leafref {
                                    path "/state:state/state:router[state:router-name=current()/../../../../router-instance]/state:segment-routing/state:sr-policies/state:sr-policy-egress-statistics/state:color";
                                    require-instance "false";
                                }
                                mandatory true;
                                description "Color for the SR policy";
                            }

                            leaf endpoint {
                                type leafref {
                                    path "/state:state/state:router[state:router-name=current()/../../../../router-instance]/state:segment-routing/state:sr-policies/state:sr-policy-egress-statistics[state:color=current()/../color]/state:endpoint";
                                    require-instance "false";
                                }
                                mandatory true;
                                description "Endpoint address of the SR policy";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action sr-policies-egress-statistics

                } // container sr-policies

            } // container segment-routing

            container igmp {
                description "Enter the igmp context";

                container database {
                    description "Enter the database context";

                    action all {
                        description "Reset database for all interfaces, groups, and hosts";

                        input {

                            leaf group {
                                type types-sros:ipv4-multicast-address;
                                description "Group address";
                            }

                            leaf source {
                                type types-sros:ipv4-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset the database for all group interfaces";

                        input {

                            leaf group {
                                type types-sros:ipv4-multicast-address;
                                description "Group address";
                            }

                            leaf source {
                                type types-sros:ipv4-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset the database for all hosts";

                        input {

                            leaf group {
                                type types-sros:ipv4-multicast-address;
                                description "Group address";
                            }

                            leaf source {
                                type types-sros:ipv4-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset the database on an interface";

                        input {

                            leaf group {
                                type types-sros:ipv4-multicast-address;
                                description "Group address";
                            }

                            leaf source {
                                type types-sros:ipv4-unicast-address;
                                description "Source address";
                            }

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset the database on a group interface";

                        input {

                            leaf group {
                                type types-sros:ipv4-multicast-address;
                                description "Group address";
                            }

                            leaf source {
                                type types-sros:ipv4-unicast-address;
                                description "Source address";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset the database on a forwarding group interface";

                        input {

                            leaf group {
                                type types-sros:ipv4-multicast-address;
                                description "Group address";
                            }

                            leaf source {
                                type types-sros:ipv4-unicast-address;
                                description "Source address";
                            }

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset the database on a host";

                        input {

                            leaf group {
                                type types-sros:ipv4-multicast-address;
                                description "Group address";
                            }

                            leaf source {
                                type types-sros:ipv4-unicast-address;
                                description "Source address";
                            }

                            leaf host-ip-address {
                                type types-sros:ipv4-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container database

                container mcast-reporting-statistics {
                    description "Enter the mcast-reporting-statistics context";

                    action all-hosts {
                        description "Reset multicast reporting statistics for all hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action host {
                        description "Reset multicast reporting statistics for a host";

                        input {

                            leaf host-ip-address {
                                type types-sros:ipv4-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container mcast-reporting-statistics

                container statistics {
                    description "Enter the statistics context";

                    action all {
                        description "Reset statistics for all interfaces, groups, and hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset statistics for all group interfaces";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset statistics for all hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset statistics on an interface";

                        input {

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset statistics on a group interface";

                        input {

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset statistics on a group interface";

                        input {

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset statistics on a host";

                        input {

                            leaf host-ip-address {
                                type types-sros:ipv4-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container statistics

                container version {
                    description "Enter the version context";

                    action all {
                        description "Reset the version for all interfaces, groups, and hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset the version for all group interfaces";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset the version for all hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset the version on an interface";

                        input {

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset the version on a group interface";

                        input {

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset the version on a group interface";

                        input {

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset the version on a host";

                        input {

                            leaf host-ip-address {
                                type types-sros:ipv4-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container version

            } // container igmp

            container mld {
                description "Enter the mld context";

                container database {
                    description "Enter the database context";

                    action all {
                        description "Reset database for all interfaces, groups, and hosts";

                        input {

                            leaf group {
                                type types-sros:ipv6-multicast-address;
                                description "Group address";
                            }

                            leaf source {
                                type types-sros:ipv6-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset the database for all group interfaces";

                        input {

                            leaf group {
                                type types-sros:ipv6-multicast-address;
                                description "Group address";
                            }

                            leaf source {
                                type types-sros:ipv6-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset the database for all hosts";

                        input {

                            leaf group {
                                type types-sros:ipv6-multicast-address;
                                description "Group address";
                            }

                            leaf source {
                                type types-sros:ipv6-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset the database on an interface";

                        input {

                            leaf group {
                                type types-sros:ipv6-multicast-address;
                                description "Group address";
                            }

                            leaf source {
                                type types-sros:ipv6-unicast-address;
                                description "Source address";
                            }

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset the database on a group interface";

                        input {

                            leaf group {
                                type types-sros:ipv6-multicast-address;
                                description "Group address";
                            }

                            leaf source {
                                type types-sros:ipv6-unicast-address;
                                description "Source address";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset the database on a group interface";

                        input {

                            leaf group {
                                type types-sros:ipv6-multicast-address;
                                description "Group address";
                            }

                            leaf source {
                                type types-sros:ipv6-unicast-address;
                                description "Source address";
                            }

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset the database on a host";

                        input {

                            leaf group {
                                type types-sros:ipv6-multicast-address;
                                description "Group address";
                            }

                            leaf source {
                                type types-sros:ipv6-unicast-address;
                                description "Source address";
                            }

                            leaf host-ip-address {
                                type types-sros:ipv6-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container database

                container statistics {
                    description "Enter the statistics context";

                    action all {
                        description "Reset statistics for all interfaces, groups, and hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset the statistics for all group interfaces";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset the statistics for all hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset the statistics on an interface";

                        input {

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset the statistics on a group interface";

                        input {

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset the statistics on a group interface";

                        input {

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset the statistics on a host";

                        input {

                            leaf host-ip-address {
                                type types-sros:ipv6-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container statistics

                container version {
                    description "Enter the version context";

                    action all {
                        description "Reset the version for all interfaces, groups, and hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action all-group-interfaces {
                        description "Reset the version for all group interfaces";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-group-interfaces

                    action all-hosts {
                        description "Reset the version for all hosts";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all-hosts

                    action interface {
                        description "Reset the version on an interface";

                        input {

                            leaf interface-name {
                                type types-sros:interface-name;
                                mandatory true;
                                description "Interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                    action group-interface {
                        description "Reset the version on a group interface";

                        input {

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action group-interface

                    action forwarding-group-interface {
                        description "Reset the version on a group interface";

                        input {

                            leaf forwarding-service {
                                type types-services:service-name;
                                mandatory true;
                                description "Forwarding service for a subscriber interface";
                            }

                            leaf group-interface-name {
                                type types-sros:interface-name;
                                mandatory true;
                                description "Group interface name";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action forwarding-group-interface

                    action host {
                        description "Reset the version on a host";

                        input {

                            leaf host-ip-address {
                                type types-sros:ipv6-address;
                                mandatory true;
                                description "Host address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action host

                } // container version

            } // container mld

            container pim {
                description "Enter the pim context";

                container statistics {
                    description "Enter the statistics context";

                    action all {
                        description "Reset the statistics for all interfaces";

                        input {

                            choice af {
                                case ipv4 {

                                    leaf ipv4 {
                                        type empty;
                                        description "IPv4 address";
                                    }

                                }
                                case ipv6 {

                                    leaf ipv6 {
                                        type empty;
                                        description "IPv6 address";
                                    }

                                }
                            }
                            leaf group {
                                type types-sros:ip-multicast-address;
                                description "Group address";
                            }

                            leaf source {
                                type types-sros:ip-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action interface {
                        description "Reset the statistics for an interface";

                        input {

                            leaf interface-name {
                                type types-sros:interface-name;
                                mandatory true;
                                description "Interface name";
                            }

                            choice af {
                                case ipv4 {

                                    leaf ipv4 {
                                        type empty;
                                        description "IPv4 address";
                                    }

                                }
                                case ipv6 {

                                    leaf ipv6 {
                                        type empty;
                                        description "IPv6 address";
                                    }

                                }
                            }
                            leaf group {
                                type types-sros:ip-multicast-address;
                                description "Group address";
                            }

                            leaf source {
                                type types-sros:ip-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                } // container statistics

                container database {
                    description "Enter the database context";

                    action all {
                        description "Reset the database for all interfaces";

                        input {

                            choice af {
                                case ipv4 {

                                    leaf ipv4 {
                                        type empty;
                                        description "IPv4 address";
                                    }

                                }
                                case ipv6 {

                                    leaf ipv6 {
                                        type empty;
                                        description "IPv6 address";
                                    }

                                }
                            }
                            leaf group {
                                type types-sros:ip-multicast-address;
                                description "Group address";
                            }

                            leaf source {
                                type types-sros:ip-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action interface {
                        description "Reset the database for an interface";

                        input {

                            leaf interface-name {
                                type types-sros:interface-name;
                                mandatory true;
                                description "Interface name";
                            }

                            choice af {
                                case ipv4 {

                                    leaf ipv4 {
                                        type empty;
                                        description "IPv4 address";
                                    }

                                }
                                case ipv6 {

                                    leaf ipv6 {
                                        type empty;
                                        description "IPv6 address";
                                    }

                                }
                            }
                            leaf group {
                                type types-sros:ip-multicast-address;
                                description "Group address";
                            }

                            leaf source {
                                type types-sros:ip-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                } // container database

                container neighbor {
                    description "Enter the neighbor context";

                    action all {
                        description "Reset the neighbors on all interfaces";

                        input {

                            choice af {
                                case ipv4 {

                                    leaf ipv4 {
                                        type empty;
                                        description "IPv4 address";
                                    }

                                }
                                case ipv6 {

                                    leaf ipv6 {
                                        type empty;
                                        description "IPv6 address";
                                    }

                                }
                            }
                            leaf address {
                                type types-sros:ip-unicast-address;
                                description "Neighbor address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action interface {
                        description "Reset the neighbors on an interface";

                        input {

                            leaf interface-name {
                                type types-sros:interface-name;
                                mandatory true;
                                description "Interface name";
                            }

                            choice af {
                                case ipv4 {

                                    leaf ipv4 {
                                        type empty;
                                        description "IPv4 address";
                                    }

                                }
                                case ipv6 {

                                    leaf ipv6 {
                                        type empty;
                                        description "IPv6 address";
                                    }

                                }
                            }
                            leaf address {
                                type types-sros:ip-unicast-address;
                                description "Neighbor address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action interface

                } // container neighbor

                container s-pmsi {
                    description "Enter the s-pmsi context";

                    action all {
                        description "Reset all";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action vprn {
                        description "Reset the VPRN";

                        input {

                            leaf group {
                                type types-sros:ip-multicast-address;
                                mandatory true;
                                description "Group address";
                            }

                            leaf source {
                                type types-sros:ip-unicast-address;
                                mandatory true;
                                description "Source address";
                            }

                            leaf md-group {
                                type types-sros:ipv4-multicast-address;
                                description "MD group address";
                            }

                            leaf md-source {
                                type types-sros:ipv4-unicast-address;
                                description "MD source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action vprn

                    action md {
                        description "Reset the MD";

                        input {

                            leaf group {
                                type types-sros:ipv4-multicast-address;
                                description "Group address";
                            }

                            leaf source {
                                type types-sros:ipv4-unicast-address;
                                description "Source address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action md

                } // container s-pmsi

            } // container pim

            container msdp {
                description "Enter the msdp context";

                action statistics {
                    description "Reset the statistics";

                    input {

                        leaf peer-address {
                            type types-sros:ipv4-unicast-address;
                            description "Peer address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action cache {
                    description "Reset the MSDP cache";

                    input {

                        leaf peer-address {
                            type types-sros:ipv4-unicast-address;
                            description "Peer address";
                        }

                        leaf group-address {
                            type types-sros:ipv4-multicast-address;
                            description "Group address";
                        }

                        leaf source-address {
                            type types-sros:ipv4-unicast-address;
                            description "Source address";
                        }

                        leaf origin-rp-address {
                            type types-sros:ipv4-unicast-address;
                            description "Origin RP address";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action cache

            } // container msdp

            container bier {
                description "Enter the bier context";

                action statistics {
                    description "Reset statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                container database {
                    description "Enter the database context";

                    action sub-domain {
                        description "Reset the sub-domain";

                        input {

                            leaf sub-domain-id {
                                type types-inet:as-number {
                                    range "0..255";
                                }
                                mandatory true;
                                description "Sub-domain ID";
                            }

                            leaf bsl {
                                type uint16;
                                description "Sub-domain BSL";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action sub-domain

                } // container database

            } // container bier

            container bgp {
                description "Enter the bgp context";

                list group {
                    key "group-name";
                    description "Enter the group list instance";

                    leaf group-name {
                        type leafref {
                            path "/state:state/state:router[state:router-name=current()/../../../router-instance]/state:bgp/state:group/state:group-name";
                            require-instance "false";
                        }
                        description "Group name";
                    }

                    action damping {
                        description "Reset the route damping information for received routes";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action damping

                    action flap-statistics {
                        description "Reset counter to zero for selected subset of RIB-INs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action flap-statistics

                } // list group

                list neighbor {
                    key "neighbor-id";
                    description "Enter the neighbor list instance";

                    leaf neighbor-id {
                        type union {
                            type union {
                                type types-sros:ipv4-address-with-zone;
                                type types-sros:ipv6-address-with-zone;
                            }
                            type enumeration {
                                enum external {
                                    value 1;
                                    description "Reset all eBGP neighbors";
                                }
                                enum all {
                                    value 2;
                                    description "Reset all BGP neighbors";
                                }
                            }
                        }
                        description "Neighbor ID";
                    }

                    action soft {
                        description "Reevaluate routes against configured export policies";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft

                    action soft-inbound {
                        description "Reevaluate routes against configured import policies";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft-inbound

                    action hard {
                        description "Reset BGP neighbors with TCP connection teardown";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action hard

                    action soft-route-refresh {
                        description "Reset a session by sending messages to the peer";

                        input {

                            leaf family {
                                type types-bgp:ip-family-identifier;
                                description "Address family";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft-route-refresh

                    action statistics {
                        description "Reset BGP neighbor statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action statistics

                    action end-of-rib {
                        description "Reset the Routing Information Base (RIB)";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action end-of-rib

                    action damping {
                        description "Reset the route damping information for received routes";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action damping

                    action flap-statistics {
                        description "Reset counter to zero for selected subset of RIB-INs";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action flap-statistics

                } // list neighbor

                list prefix {
                    key "ip-prefix";
                    description "Enter the prefix list instance";

                    leaf ip-prefix {
                        type types-sros:ip-prefix;
                        description "IP prefix";
                    }

                    action damping {
                        description "Reset RFD route history block for a subset of RIB-INs";

                        input {

                            leaf neighbor {
                                type leafref {
                                    path "/state:state/state:router/state:bgp/state:neighbor/state:ip-address";
                                }
                                description "IP address of the BGP neighbor";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action damping

                    action flap-statistics {
                        description "Resets the route flap statistics";

                        input {

                            leaf neighbor {
                                type leafref {
                                    path "/state:state/state:router/state:bgp/state:neighbor/state:ip-address";
                                }
                                description "IP address of the BGP neighbor";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action flap-statistics

                    action traffic-statistics {
                        description "Reset BGP-LU traffic statistics counters to zero";

                        input {

                            leaf direction {
                                type enumeration {
                                    enum ingress                        { value 1; }
                                    enum egress                         { value 2; }
                                }
                                description "Specifies the direction of the data-path";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action traffic-statistics

                } // list prefix

                list neighbor-as {
                    key "as-number";
                    description "Enter the neighbor-as list instance";

                    leaf as-number {
                        type uint32 {
                            range "1..4294967295";
                        }
                        description "AS number";
                    }

                    action soft {
                        description "Reevaluate routes against configured export policies";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft

                    action soft-inbound {
                        description "Reevaluate routes against configured import policies";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft-inbound

                    action hard {
                        description "Reset BGP neighbors with TCP connection teardown";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action hard

                    action soft-route-refresh {
                        description "Reset a session by sending messages to the peer";

                        input {

                            leaf family {
                                type types-bgp:ip-family-identifier;
                                description "Address family";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action soft-route-refresh

                    action statistics {
                        description "Reset BGP neighbor statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action statistics

                    action end-of-rib {
                        description "Reset the Routing Information Base (RIB)";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action end-of-rib

                } // list neighbor-as

                list family {
                    key "family-type";
                    description "Enter the family list instance";

                    leaf family-type {
                        type enumeration {
                            enum label-ipv4                     { value 17; }
                            enum label-ipv6                     { value 18; }
                        }
                        description "Address family for BGP reset actions";
                    }

                    action traffic-statistics {
                        description "Reset BGP-LU traffic statistics counters to zero";

                        input {

                            leaf direction {
                                type enumeration {
                                    enum ingress                        { value 1; }
                                    enum egress                         { value 2; }
                                }
                                description "Specifies the direction of the data-path";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action traffic-statistics

                } // list family

                action traffic-statistics {
                    description "Reset BGP-LU traffic statistics counters to zero";

                    input {

                        leaf direction {
                            type enumeration {
                                enum ingress                        { value 1; }
                                enum egress                         { value 2; }
                            }
                            description "Specifies the direction of the data-path";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action traffic-statistics

                action protocol {
                    description "Resets the BGP instance, causing all sessions to restart (return to IDLE)";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action protocol

            } // container bgp

            container ldp {
                description "Enter the ldp context";

                action fec-egress-statistics {
                    description "Reset LDP FEC egress statistics";

                    input {

                        leaf ip-prefix {
                            type types-sros:ip-prefix;
                            mandatory true;
                            description "Prefix FEC";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action fec-egress-statistics

                action instance {
                    description "Reset LDP instance";

                    input {

                        leaf address-family {
                            type enumeration {
                                enum ipv4                           { value 1; }
                                enum ipv6                           { value 2; }
                            }
                            description "Address family type";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action instance

                action interface {
                    description "Reset an LDP interface or its statistics";

                    input {

                        leaf interface-name {
                            type leafref {
                                path "/state:state/state:router[state:router-name=current()/../../../router-instance]/state:ldp/state:interface-parameters/state:interface/state:ip-int-name";
                            }
                            mandatory true;
                            description "LDP interface name";
                        }

                        leaf statistics {
                            type empty;
                            description "Reset LDP interface statistics";
                        }

                        choice address-family {
                            case ipv4 {

                                leaf ipv4 {
                                    type empty;
                                    description "Reset an IPv4 LDP sub-interface or its statistics";
                                }

                            }
                            case ipv6 {

                                leaf ipv6 {
                                    type empty;
                                    description "Reset an IPv6 LDP sub-interface or its statistics";
                                }

                            }
                        }
                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action interface

                action peer {
                    description "Reset statistics for LDP targeted peer";

                    input {

                        leaf ip-address {
                            type types-sros:ip-address;
                            mandatory true;
                            description "Peer address";
                        }

                        leaf statistics {
                            type empty;
                            description "Reset LDP targeted peer statistics";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action peer

                action resource-failures {
                    description "Reset resource overload status of LDP instance";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action resource-failures

                action session {
                    description "Reset overload or statistics for LDP session";

                    input {

                        leaf peer-lsr-id {
                            type leafref {
                                path "/state:state/state:router[state:router-name=current()/../../../router-instance]/state:ldp/state:session/state:peer-lsr-id";
                            }
                            mandatory true;
                            description "Peer LSR ID";
                        }

                        choice statistics-or-overload {
                            case statistics {

                                leaf statistics {
                                    type empty;
                                    mandatory true;
                                    description "Reset LDP session statistics";
                                }

                            }
                            case overload {

                                leaf overload {
                                    type empty;
                                    mandatory true;
                                    description "Reset resource overload status";
                                }

                                leaf fec-type {
                                    type enumeration {
                                        enum p2mp                           { value 1; }
                                        enum prefixes                       { value 2; }
                                        enum svc-fec128                     { value 3; }
                                        enum svc-fec129                     { value 4; }
                                    }
                                    description "Overload FEC type";
                                }

                                leaf sub-type {
                                    type enumeration {
                                        enum ipv4                           { value 1; }
                                        enum ipv6                           { value 2; }
                                    }
                                    description "Overload FEC subtype for P2MP or prefixes";
                                }

                            }
                        }
                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action session

                action statistics {
                    description "Reset LDP statistics";

                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action statistics

                action targeted-auto-rx {
                    description "Reset LDP auto-rx";

                    input {

                        leaf hold-time {
                            type uint32 {
                                range "1..65535";
                            }
                            units "seconds";
                            mandatory true;
                            description "Hold-time where auto-rx targeted peers do not generate";
                        }

                    }
                    output {

                        leaf operation-id {
                            type types-operation:operation-id;
                            description "ID assigned to the operation.";
                        }

                        leaf start-time {
                            type types-operation:operation-timestamp;
                            description "Time when the operation started its execution.";
                        }

                        leaf results-path {
                            type types-operation:operation-path;
                            description "Path to the results of the operation formatted as xpath.";
                        }

                        leaf status {
                            type types-operation:operation-status;
                            description "Status of the operation";
                        }

                        leaf-list error-message {
                            type types-operation:operation-message;
                            description "Error messages reported during execution of the operation.";
                        }

                        leaf-list warning-message {
                            type types-operation:operation-message;
                            description "Warning messages reported during execution of the operation.";
                        }

                        leaf-list info-message {
                            type types-operation:operation-message;
                            description "Info messages reported during execution of the operation.";
                        }

                        leaf end-time {
                            type types-operation:operation-timestamp;
                            description "Time when the operation ended its execution.";
                        }

                    }
                } // action targeted-auto-rx

            } // container ldp

        } // list router

        list card {
            key "slot-number";
            description "Enter the card list instance";

            leaf slot-number {
                type leafref {
                    path "/state:state/state:card/state:slot-number";
                }
                description "Slot number";
            }

            action reinitialize {
                description "Reset the specified card";

                input {

                    leaf soft {
                        type empty;
                        description "Perform a soft reset on the card";
                    }

                    leaf hard-reset-unsupported-mdas {
                        type empty;
                        description "Perform a hard reset on MDAs incapable of soft reset";
                    }

                }
                output {

                    leaf operation-id {
                        type types-operation:operation-id;
                        description "ID assigned to the operation.";
                    }

                    leaf start-time {
                        type types-operation:operation-timestamp;
                        description "Time when the operation started its execution.";
                    }

                    leaf results-path {
                        type types-operation:operation-path;
                        description "Path to the results of the operation formatted as xpath.";
                    }

                    leaf status {
                        type types-operation:operation-status;
                        description "Status of the operation";
                    }

                    leaf-list error-message {
                        type types-operation:operation-message;
                        description "Error messages reported during execution of the operation.";
                    }

                    leaf-list warning-message {
                        type types-operation:operation-message;
                        description "Warning messages reported during execution of the operation.";
                    }

                    leaf-list info-message {
                        type types-operation:operation-message;
                        description "Info messages reported during execution of the operation.";
                    }

                    leaf end-time {
                        type types-operation:operation-timestamp;
                        description "Time when the operation ended its execution.";
                    }

                }
            } // action reinitialize

            list fp {
                key "fp-number";
                description "Enter the fp list instance";

                leaf fp-number {
                    type leafref {
                        path "/state:state/state:card[state:slot-number=current()/../../slot-number]/state:fp/state:fp-number";
                    }
                    description "FP number";
                }

                container forward-engine-drop-reason {
                    description "Enter the forward-engine-drop-reason context";

                    action statistics {
                        description "Reset forwarding engine drop reason statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action statistics

                } // container forward-engine-drop-reason

                container distributed-cpu-protection {
                    description "Enter the distributed-cpu-protection context";

                    action information {
                        description "Reset distributed CPU protection information";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action information

                } // container distributed-cpu-protection

                container ingress {
                    description "Enter the ingress context";

                    action per-egress-fp-statistics {
                        description "Reset per egress FP statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action per-egress-fp-statistics

                    container queue-group {
                        description "Enter the queue-group context";

                        action statistics {
                            description "Reset the queue group statistics";

                            input {

                                leaf mode {
                                    type enumeration {
                                        enum access                         { value 0; }
                                        enum network                        { value 1; }
                                    }
                                    mandatory true;
                                    description "Queue group statistics mode";
                                }

                                leaf queue-group-name {
                                    type string;
                                    mandatory true;
                                    description "Queue group name";
                                }

                                leaf instance {
                                    type uint16;
                                    mandatory true;
                                    description "Queue group instance ID";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action statistics

                    } // container queue-group

                } // container ingress

            } // list fp

        } // list card

        container mda {
            description "Enter the mda context";

            list card-slot {
                key "slot-number";
                description "Enter the card-slot list instance";

                leaf slot-number {
                    type leafref {
                        path "/state:state/state:card/state:slot-number";
                    }
                    description "Slot number";
                }

                list mda-slot {
                    key "mda";
                    description "Enter the mda-slot list instance";

                    leaf mda {
                        type leafref {
                            path "/state:state/state:card[state:slot-number=current()/../../slot-number]/state:mda/state:mda-slot";
                        }
                        description "Card MDA slot";
                    }

                    action reinitialize {
                        description "Reset the specified MDA";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action reinitialize

                    action ipsec-statistics {
                        description "Reset MDA IPsec statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action ipsec-statistics

                } // list mda-slot

                list xiom-slot {
                    key "xiom";
                    description "Enter the xiom-slot list instance";

                    leaf xiom {
                        type leafref {
                            path "/state:state/state:card[state:slot-number=current()/../../slot-number]/state:xiom/state:xiom-slot";
                        }
                        description "XIOM slot";
                    }

                    list mda-slot {
                        key "mda";
                        description "Enter the mda-slot list instance";

                        leaf mda {
                            type leafref {
                                path "/state:state/state:card[state:slot-number=current()/../../../slot-number]/state:xiom[state:xiom-slot=current()/../../xiom]/state:mda/state:mda-slot";
                            }
                            description "XIOM MDA slot";
                        }

                        action reinitialize {
                            description "Reset the specified MDA";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action reinitialize

                        action ipsec-statistics {
                            description "Reset mda ipsec statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action ipsec-statistics

                    } // list mda-slot

                } // list xiom-slot

            } // list card-slot

        } // container mda

        container xiom {
            description "Enter the xiom context";

            list card-slot {
                key "slot-number";
                description "Enter the card-slot list instance";

                leaf slot-number {
                    type leafref {
                        path "/state:state/state:card/state:slot-number";
                    }
                    description "Slot number";
                }

                list xiom-slot {
                    key "xiom";
                    description "Enter the xiom-slot list instance";

                    leaf xiom {
                        type leafref {
                            path "/state:state/state:card[state:slot-number=current()/../../slot-number]/state:xiom/state:xiom-slot";
                        }
                        description "XIOM slot";
                    }

                    action reinitialize {
                        description "Reset the specified xiom";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action reinitialize

                } // list xiom-slot

            } // list card-slot

        } // container xiom

        container service {
            description "Enter the service context";

            list vpls {
                key "service-name";
                description "Enter the vpls list instance";

                leaf service-name {
                    type leafref {
                        path "/state:state/state:service/state:vpls/state:service-name";
                    }
                    description "VPLS service name";
                }

                container fdb {
                    description "Enter the fdb context";

                    action all {
                        description "Reset all FDB items";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action mac {
                        description "Reset operation on the MAC";

                        input {

                            leaf mac-address {
                                type types-sros:mac-unicast-address-no-zero;
                                mandatory true;
                                description "MAC address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mac

                    action spoke-sdp {
                        description "Reset operation on the spoke SDP";

                        input {

                            leaf sdp-bind-id {
                                type leafref {
                                    path "/state:state/state:service/state:vpls[state:service-name=current()/../../../service-name]/state:spoke-sdp/state:sdp-bind-id";
                                }
                                mandatory true;
                                description "Specifies the spoke-sdp";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action spoke-sdp

                    action mesh-sdp {
                        description "Reset operation on the mesh-sdp";

                        input {

                            leaf sdp-bind-id {
                                type leafref {
                                    path "/state:state/state:service/state:vpls[state:service-name=current()/../../../service-name]/state:mesh-sdp/state:sdp-bind-id";
                                }
                                mandatory true;
                                description "SDP bind ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mesh-sdp

                    action sap {
                        description "Reset operation on the SAP";

                        input {

                            leaf sap-id {
                                type leafref {
                                    path "/state:state/state:service/state:vpls[state:service-name=current()/../../../service-name]/state:sap/state:sap-id";
                                }
                                mandatory true;
                                description "SAP ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action sap

                    action vxlan {
                        description "Reset operation on the specified VXLAN instance";

                        input {

                            leaf vxlan-instance {
                                type leafref {
                                    path "/state:state/state:service/state:vpls[state:service-name=current()/../../../service-name]/state:vxlan/state:instance/state:vxlan-instance";
                                }
                                mandatory true;
                                description "VXLAN instance";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action vxlan

                } // container fdb

                container proxy-arp {
                    description "Enter the proxy-arp context";

                    action duplicate {
                        description "Reset operation on the IP address";

                        input {

                            leaf ip-address {
                                type types-sros:ipv4-address;
                                description "IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action duplicate

                    action dynamic {
                        description "Reset operation on the IP address";

                        input {

                            leaf ip-address {
                                type types-sros:ipv4-address;
                                description "IP address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action dynamic

                } // container proxy-arp

                container proxy-nd {
                    description "Enter the proxy-nd context";

                    action duplicate {
                        description "Reset operation on the specified ip-address";

                        input {

                            leaf ipv6-address {
                                type types-sros:ipv6-address;
                                description "IPv6 address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action duplicate

                    action dynamic {
                        description "Reset operation on the IP address";

                        input {

                            leaf ipv6-address {
                                type types-sros:ipv6-address;
                                description "IPv6 address";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action dynamic

                } // container proxy-nd

                container evpn {
                    description "Enter the evpn context";

                    container mac-duplication {
                        description "Enter the mac-duplication context";

                        action duplicate-mac {
                            description "Reset operations on the duplicate MAC";

                            input {

                                leaf mac-address {
                                    type leafref {
                                        path "/state:state/state:service/state:vpls[state:service-name=current()/../../../../service-name]/state:bgp-evpn/state:mac-duplication/state:duplicate-macs/state:address/state:mac";
                                    }
                                    mandatory true;
                                    description "MAC address";
                                }

                            }
                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action duplicate-mac

                        action all {
                            description "Reset all FDB items";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                    } // container mac-duplication

                } // container evpn

            } // list vpls

            container statistics {
                description "Enter the statistics context";

                list name {
                    key "service-name";
                    description "Enter the name list instance";

                    leaf service-name {
                        type types-services:service-name;
                        description "Service name";
                    }

                    action counters {
                        description "Reset counters";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action counters

                    action l2pt {
                        description "Reset L2PT statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action l2pt

                    action mrp {
                        description "Reset MRP statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mrp

                    action pip {
                        description "Reset PIP statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action pip

                    action stp {
                        description "Reset STP statistics";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stp

                    list spoke-sdp {
                        key "sdp-bind-id";
                        description "Enter the spoke-sdp list instance";

                        leaf sdp-bind-id {
                            type types-services:sdp-bind-id;
                            description "Enter spoke-sdp context";
                        }

                        action all {
                            description "Reset all";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action counters {
                            description "Reset counters";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action counters

                        action l2pt {
                            description "Reset L2PT statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action l2pt

                        action mrp {
                            description "Reset MRP statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action mrp

                        action stp {
                            description "Reset STP statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action stp

                    } // list spoke-sdp

                    list mesh-sdp {
                        key "sdp-bind-id";
                        description "Enter the mesh-sdp list instance";

                        leaf sdp-bind-id {
                            type types-services:sdp-bind-id;
                            description "Enter spoke-sdp context";
                        }

                        action all {
                            description "Reset all";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action all

                        action counters {
                            description "Reset counters";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action counters

                        action mrp {
                            description "Reset MRP statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action mrp

                        action stp {
                            description "Reset STP statistics";

                            output {

                                leaf operation-id {
                                    type types-operation:operation-id;
                                    description "ID assigned to the operation.";
                                }

                                leaf start-time {
                                    type types-operation:operation-timestamp;
                                    description "Time when the operation started its execution.";
                                }

                                leaf results-path {
                                    type types-operation:operation-path;
                                    description "Path to the results of the operation formatted as xpath.";
                                }

                                leaf status {
                                    type types-operation:operation-status;
                                    description "Status of the operation";
                                }

                                leaf-list error-message {
                                    type types-operation:operation-message;
                                    description "Error messages reported during execution of the operation.";
                                }

                                leaf-list warning-message {
                                    type types-operation:operation-message;
                                    description "Warning messages reported during execution of the operation.";
                                }

                                leaf-list info-message {
                                    type types-operation:operation-message;
                                    description "Info messages reported during execution of the operation.";
                                }

                                leaf end-time {
                                    type types-operation:operation-timestamp;
                                    description "Time when the operation ended its execution.";
                                }

                            }
                        } // action stp

                    } // list mesh-sdp

                } // list name

                list sap {
                    key "sap-id";
                    description "Enter the sap list instance";

                    leaf sap-id {
                        type types-sros:sap;
                        description "Enter sap context";
                    }

                    action all {
                        description "Reset all";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action all

                    action cem {
                        description "Reset CEM";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action cem

                    action counters {
                        description "Reset counters";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action counters

                    action stp {
                        description "Reset STP";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action stp

                    action l2pt {
                        description "Reset L2PT";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action l2pt

                    action mrp {
                        description "Reset MRP";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action mrp

                } // list sap

                list sdp {
                    key "sdp-id";
                    description "Enter the sdp list instance";

                    leaf sdp-id {
                        type leafref {
                            path "/state:state/state:service/state:sdp/state:sdp-id";
                        }
                        description "Enter sdp context";
                    }

                    action keep-alive {
                        description "Reset keep-alive";

                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action keep-alive

                    action pw-port {
                        description "Reset the PW port";

                        input {

                            leaf pw-port-id {
                                type leafref {
                                    path "/state:state/state:pw-port/state:pw-port-id";
                                }
                                mandatory true;
                                description "PW port ID";
                            }

                        }
                        output {

                            leaf operation-id {
                                type types-operation:operation-id;
                                description "ID assigned to the operation.";
                            }

                            leaf start-time {
                                type types-operation:operation-timestamp;
                                description "Time when the operation started its execution.";
                            }

                            leaf results-path {
                                type types-operation:operation-path;
                                description "Path to the results of the operation formatted as xpath.";
                            }

                            leaf status {
                                type types-operation:operation-status;
                                description "Status of the operation";
                            }

                            leaf-list error-message {
                                type types-operation:operation-message;
                                description "Error messages reported during execution of the operation.";
                            }

                            leaf-list warning-message {
                                type types-operation:operation-message;
                                description "Warning messages reported during execution of the operation.";
                            }

                            leaf-list info-message {
                                type types-operation:operation-message;
                                description "Info messages reported during execution of the operation.";
                            }

                            leaf end-time {
                                type types-operation:operation-timestamp;
                                description "Time when the operation ended its execution.";
                            }

                        }
                    } // action pw-port

                } // list sdp

            } // container statistics

        } // container service

    } // container reset

}
