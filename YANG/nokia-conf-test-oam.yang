submodule nokia-conf-test-oam {

    yang-version "1.1";

    belongs-to nokia-conf { prefix "conf"; }

    import nokia-sros-yang-extensions     { prefix "sros-ext"; }
    import nokia-types-oam                { prefix "types-oam"; }
    import nokia-types-qos                { prefix "types-qos"; }
    import nokia-types-sros               { prefix "types-sros"; }

    include nokia-conf-groups;
    include nokia-conf-testoam-service-activation-testhead;


    sros-ext:sros-major-release "rel21";

    organization "Nokia";

    contact
        "Nokia SR OS Support
         Web: <http://www.nokia.com>";

    description
        "Nokia YANG Data model to configure OAM test parameters configuration on SR OS based routers.

         Copyright 2016 Nokia. All rights reserved. Reproduction of this document
         is authorized on the condition that the foregoing copyright notice is included.

         This nokia-conf-test-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-07-12";

    grouping conf-test-oam {
        container test-oam {
            description "Enter the test-oam context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container link-measurement {
                description "Enter the link-measurement context";

                list measurement-template {
                    key "template-name";
                    description "Enter the measurement-template list instance";

                    leaf template-name {
                        type types-sros:named-item-64;
                        description "Measurement template name";
                    }

                    leaf admin-state {
                        type types-sros:admin-state;
                        default "disable";
                        description "Administrative state of the measurement template";
                    }

                    leaf description {
                        type types-sros:description;
                        description "Text description";
                    }

                    leaf unidirectional-measurement {
                        type enumeration {
                            enum "derived"                      { value 1; }
                            enum "actual"                       { value 2; }
                        }
                        default "derived";
                        description "Method used to compute the unidirectional delay value";
                    }

                    leaf delay {
                        type enumeration {
                            enum "min"                          { value 1; }
                            enum "max"                          { value 2; }
                            enum "avg"                          { value 3; }
                        }
                        default "min";
                        description "Delay measurement statistic type";
                    }

                    leaf interval {
                        type uint32 {
                            range "1..10";
                        }
                        units "seconds";
                        default "1";
                        description "Interval between test packet transmissions";
                    }

                    leaf last-reported-delay-hold {
                        type uint32 {
                            range "0|1..86400";
                        }
                        units "seconds";
                        default "86400";
                        description "Time to wait to flush the last reported delay";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container twamp-light {
                        description "Enter the twamp-light context";

                        leaf allow-egress-remark-dscp {
                            type boolean;
                            default "false";
                            description "Allow overwrite of DSCP value by the egress QoS policy";
                        }

                        leaf allow-ipv6-udp-checksum-zero {
                            type boolean;
                            default "false";
                            description "Process IPv6 packets with UDP check sum zero";
                        }

                        leaf dscp {
                            type types-qos:dscp-name;
                            default "nc1";
                            description "DSCP copied to TWAMP Light echo request packet header";
                        }

                        leaf dest-udp-port {
                            type types-sros:tcp-udp-port-non-zero;
                            default "862";
                            description "Destination UDP port used by link measurement tests";
                        }

                        leaf fc {
                            type types-sros:fc-name;
                            default "h1";
                            description "Forwarding class name for the TWAMP Light packets";
                        }

                        leaf profile {
                            type types-qos:profile-in-out;
                            default "in";
                            description "QoS profile for packet treatment in local node";
                        }

                        leaf timestamp-format {
                            type enumeration {
                                enum "ntp"                          { value 1; }
                                enum "ptp"                          { value 2; }
                            }
                            default "ntp";
                            description "Format of the timestamp used in TWAMP Light PDU";
                        }

                        leaf ttl {
                            type uint32 {
                                range "1..255";
                            }
                            default "1";
                            description "Time to live value used in the TWAMP Light test packet";
                        }

                    } // container twamp-light

                    container aggregate-sample-window {
                        description "Enter the aggregate-sample-window context";

                        leaf multiplier {
                            type uint32 {
                                range "1..12";
                            }
                            default "12";
                            description "Number of sample windows in the aggregate sample window";
                        }

                        leaf window-integrity {
                            type uint32 {
                                range "1..100";
                            }
                            units "percent";
                            description "Sample percentage required for window integrity report";
                        }

                        container threshold {
                            description "Enter the threshold context";

                            leaf relative {
                                type uint32 {
                                    range "1..100";
                                }
                                units "percent";
                                description "Relative delta for measurement reporting";
                            }

                            leaf absolute {
                                type uint32 {
                                    range "1..100000";
                                }
                                units "microseconds";
                                description "Absolute delta for delay measurement reporting";
                            }

                        } // container threshold

                    } // container aggregate-sample-window

                    container sample-window {
                        description "Enter the sample-window context";

                        leaf multiplier {
                            type uint32 {
                                range "1..900";
                            }
                            default "10";
                            description "Multiplier of interval used for sample window length";
                        }

                        leaf window-integrity {
                            type uint32 {
                                range "1..100";
                            }
                            units "percent";
                            description "Sample percentage required for window integrity report";
                        }

                        container threshold {
                            description "Enter the threshold context";

                            leaf relative {
                                type uint32 {
                                    range "1..500";
                                }
                                units "percent";
                                description "Relative delta for delay measurement reporting";
                            }

                            leaf absolute {
                                type uint32 {
                                    range "1..100000";
                                }
                                units "microseconds";
                                description "Absolute delta for delay measurement reporting";
                            }

                        } // container threshold

                    } // container sample-window

                } // list measurement-template

            } // container link-measurement

            container mpls-dm {
                description "Enter the mpls-dm context";

                leaf admin-state {
                    type types-sros:admin-state;
                    default "disable";
                    description "Administrative state of MPLS DM packet processing";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // container mpls-dm

            container twamp {
                description "Enter the twamp context";

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container server {
                    description "Enter the server context";

                    leaf admin-state {
                        type types-sros:admin-state;
                        default "disable";
                        description "Administrative state of the TWAMP server";
                    }

                    leaf inactivity-timeout {
                        type uint32 {
                            range "60..3600";
                        }
                        units "seconds";
                        sros-ext:auto-restart-to-modify;
                        default "900";
                        description "System wide inactivity timeout for each TWAMP server control connection";
                    }

                    leaf max-connections {
                        type types-oam:twamp-server-connection-count;
                        sros-ext:auto-restart-to-modify;
                        default "32";
                        description "System wide maximum number of concurrent TWAMP server control connections";
                    }

                    leaf max-sessions {
                        type types-oam:twamp-server-session-count;
                        sros-ext:auto-restart-to-modify;
                        default "32";
                        description "System wide maximum number of concurrent TWAMP server test sessions";
                    }

                    leaf ref-inactivity-timeout {
                        type uint32 {
                            range "60..3600";
                        }
                        units "seconds";
                        sros-ext:auto-restart-to-modify;
                        default "900";
                        description "System wide reflector inactivity timeout for TWAMP";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list prefix {
                        key "ip-prefix";
                        max-elements 100;
                        description "Enter the prefix list instance";

                        leaf ip-prefix {
                            type types-sros:ip-unicast-prefix;
                            description "Prefix to match against TWAMP client address";
                        }

                        leaf description {
                            type types-sros:description;
                            description "Text description";
                        }

                        leaf max-connections {
                            type types-oam:twamp-server-connection-count;
                            default "32";
                            description "Maximum number of control connections for TWAMP prefix";
                        }

                        leaf max-sessions {
                            type types-oam:twamp-server-session-count;
                            default "32";
                            description "Maximum concurrent TWAMP test sessions based on prefix";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list prefix

                } // container server

                container twamp-light {
                    description "Enter the twamp-light context";

                    leaf inactivity-timeout {
                        type uint32 {
                            range "10..100";
                        }
                        units "seconds";
                        default "100";
                        description "Time to maintain stale state on the session reflector";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // container twamp-light

            } // container twamp

            container icmp {
                description "Enter the icmp context";

                list ping-template {
                    key "name";
                    description "Enter the ping-template list instance";

                    leaf name {
                        type types-sros:named-item-64;
                        description "Ping template name";
                    }

                    leaf description {
                        type types-sros:description;
                        description "Text description";
                    }

                    leaf dscp {
                        type types-qos:dscp-name;
                        default "nc1";
                        description "DSCP value used in the outgoing ping packet";
                    }

                    leaf dot1p {
                        type types-qos:dot1p-priority;
                        default "7";
                        description "Dot1p in Ethernet header of outgoing ping packets";
                    }

                    leaf interval {
                        type uint32 {
                            range "1..60";
                        }
                        units "seconds";
                        default "60";
                        description "Packet transmit interval";
                    }

                    leaf timeout {
                        type uint32 {
                            range "1..60";
                        }
                        units "seconds";
                        default "5";
                        description "Wait time before ICMP echo request is declared lost";
                    }

                    leaf failure-threshold {
                        type uint32 {
                            range "2..10";
                        }
                        default "3";
                        description "Failure threshold to declare inter-connectivity down";
                    }

                    leaf reactivation-interval {
                        type uint32 {
                            range "1..60";
                        }
                        units "seconds";
                        default "1";
                        description "Ping reactivation interval";
                    }

                    leaf reactivation-failure-threshold {
                        type uint32 {
                            range "1..10";
                        }
                        default "4";
                        description "Threshold of consecutive failures at reactivation";
                    }

                    leaf reactivation-timeout {
                        type uint32 {
                            range "1..60";
                        }
                        units "seconds";
                        default "1";
                        description "Reactivation wait time before packet is declared lost";
                    }

                    leaf reactivation-threshold {
                        type uint32 {
                            range "1..10";
                        }
                        default "3";
                        description "Success threshold to declare inter-connectivity up";
                    }

                    leaf size {
                        type uint32 {
                            range "12..9786";
                        }
                        units "octets";
                        default "56";
                        description "Data field size of the outgoing ICMP echo packet";
                    }

                    leaf ttl {
                        type uint32 {
                            range "1..255";
                        }
                        default "1";
                        description "TTL value for the outgoing ping packet";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list ping-template

            } // container icmp

            uses conf-testoam-service-activation-testhead;
        } // container test-oam

    } // grouping conf-test-oam

}
