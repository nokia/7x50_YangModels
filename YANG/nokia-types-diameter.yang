module nokia-types-diameter {

    yang-version "1.1";

    namespace "urn:nokia.com:sros:ns:yang:sr:types-diameter";

    prefix "types-diam";

    import nokia-sros-yang-extensions     { prefix "sros-ext"; }
    import nokia-types-sros               { prefix "types-sros"; }

    sros-ext:sros-major-release "rel26";
    organization "Nokia";
    contact
        "Nokia SR OS Support
         Web: <http://www.nokia.com>";
    description
        "Common diameter data types used in the SR OS management system.

         Copyright 2016 Nokia. All rights reserved. Reproduction of this document
         is authorized on the condition that the foregoing copyright notice is included.

         This nokia-types-diameter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    typedef diam-vendor-support {
        type enumeration {
            enum vodafone                       { value 1; }
            enum three-gpp                      { value 2; }
        }
        default "vodafone";
        description
            "This gives the vaule for certain vendor specific options both
             on application as on peer level.";
    }

    typedef diam-proxy-mcs-state {
        type enumeration {
            enum init                           { value 1; }
            enum active                         { value 2; }
            enum standby                        { value 3; }
            enum active-wait                    { value 4; }
            enum standby-wait                   { value 5; }
            enum proxy-switchover-req           { value 6; }
        }
        description "mcs state of a diameter-peer-poliy in proxy role";
    }

    typedef diam-fqdn {
        type types-sros:string-not-all-spaces {
            length "1..80";
            pattern "[A-Za-z0-9\\-\\.]+" {
                error-message "'diam-fqdn' must be letters, digits, hyphen or dot (e.g. host.example.com)";
            }
        }
        description "A valid Diameter identity";
    }

    typedef diam-peer-state {
        type enumeration {
            enum closed                         { value 0; }
            enum wait-connection-ack            { value 1; }
            enum wait-i-cea                     { value 2; }
            enum i-open                         { value 3; }
            enum closing                        { value 4; }
            enum r-open                         { value 5; }
            enum wait-r-cer                     { value 6; }
        }
        description "The peer's state machine";
    }

    typedef diam-node-peer-mc-state {
        type enumeration {
            enum unavailable                    { value 0; }
            enum init                           { value 1; }
            enum wait-local                     { value 2; }
            enum wait-remote                    { value 3; }
            enum active                         { value 4; }
        }
        description "The state of the multi-chassis redundancy Diameter peer";
    }

}
