submodule nokia-state-aa-group {

    yang-version "1.1";

    belongs-to nokia-state { prefix "state"; }

    import ietf-yang-types                { prefix "yang"; }
    import nokia-sros-yang-extensions     { prefix "sros-ext"; }
    import nokia-types-application-assurance { prefix "types-aa"; }
    import nokia-types-esa                { prefix "types-esa"; }
    import nokia-types-isa                { prefix "types-isa"; }
    import nokia-types-qos                { prefix "types-qos"; }
    import nokia-types-services           { prefix "types-services"; }
    import nokia-types-sros               { prefix "types-sros"; }

    include nokia-state-log;


    sros-ext:sros-major-release "rel21";

    organization "Nokia";

    contact
        "Nokia SR OS Support
         Web: <http://www.nokia.com>";

    description
        "Nokia YANG Data model with operational state for application assurance group on SR OS based routers.

         Copyright 2016 Nokia. All rights reserved. Reproduction of this document
         is authorized on the condition that the foregoing copyright notice is included.

         This nokia-state-aa-group YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2022-03-02";

    grouping state-aa-group {
        list group {
            key "aa-group-id";
            description "Enter the group list instance";

            leaf aa-group-id {
                type uint32 {
                    range "1..255";
                }
                description "AA group ID";
            }

            container aa-interface {
                description "Enter the aa-interface context";

                list sap {
                    key "sap-id";
                    description "Enter the sap list instance";

                    leaf sap-id {
                        type types-sros:sap;
                        description "The VLAN ID on which the ISA-AA is expected to be emitting traffic.";
                    }

                    leaf oper-state {
                        type types-sros:oper-state;
                        description
                            "The operational state of the AA interface.
                             When the value is 'down' the AA interface is not active.";
                    }

                    leaf isa-address {
                        type types-sros:ip-prefix-with-host-bits;
                        description "The IP address of the ISA's AA interface.";
                    }

                } // list sap

            } // container aa-interface

            list certificate-profile {
                key "cert-prof-name";
                description "Enter the certificate-profile list instance";

                leaf cert-prof-name {
                    type types-sros:named-item;
                    description "AA group certificate profile name";
                }

                leaf oper-state {
                    type types-sros:oper-state;
                    description "The operational status of the certificate profile.";
                }

                leaf oper-flags {
                    type bits {
                        bit profile-admin-down             { position 0; }
                        bit invalid-cert-file              { position 1; }
                        bit invalid-cert-file-public-key   { position 2; }
                        bit invalid-public-key-modulus     { position 3; }
                        bit invalid-public-key-exponent    { position 4; }
                        bit unsupported-cert-file-algorithm { position 5; }
                    }
                    description "The operational condition of the certificate profile.";
                }

                leaf reference-count {
                    type uint32;
                    description "The number of clients configured with this profile.";
                }

            } // list certificate-profile

            container cflowd {
                description "Enter the cflowd context";

                list collector {
                    key "ip-address port";
                    description "Enter the collector list instance";

                    leaf ip-address {
                        type types-sros:ip-unicast-address;
                        description "IP address of the remote cflowd collector host";
                    }

                    leaf port {
                        type types-sros:tcp-udp-port-non-zero;
                        description "Cflowd collector host port number";
                    }

                    leaf oper-state {
                        type types-sros:oper-state;
                        description
                            "The operational state for the collector.
                             When 'down' no application assurance Cflowd records
                             are sent to the collector.";
                    }

                    container statistics {
                        description "Enter the statistics context";

                        leaf records-sent {
                            type yang:counter64;
                            description "The total number of flow records sent to the remote Cflowd collector.";
                        }

                    } // container statistics

                } // list collector

                container direct-export {
                    description "Enter the direct-export context";

                    list collector {
                        key "collector-id";
                        description "Enter the collector list instance";

                        leaf collector-id {
                            type uint32 {
                                range "1..65535";
                            }
                            description "Cflowd direct export collector ID";
                        }

                        list address {
                            key "ip-address port";
                            description "Enter the address list instance";

                            leaf ip-address {
                                type types-sros:ip-unicast-address;
                                description "IP address of the remote cflowd collector host";
                            }

                            leaf port {
                                type types-sros:tcp-udp-port-non-zero;
                                description "Cflowd collector host port number";
                            }

                            leaf oper-state {
                                type types-sros:oper-state;
                                description
                                    "The operational state for the Cflowd direct export collector address.
                                     When 'down' no application assurance Cflowd records are sent to the collector.";
                            }

                            list esa {
                                key "esa-id vm";
                                description "Enter the esa list instance";

                                leaf esa-id {
                                    type types-esa:esa-id;
                                    description "ESA ID";
                                }

                                leaf vm {
                                    type types-esa:vm-id;
                                    description "VM ID within the ESA";
                                }

                                leaf oper-state {
                                    type types-sros:oper-state;
                                    description "The operational status of the of the cflowd direct export collector.";
                                }

                                leaf records-sent {
                                    type yang:counter64;
                                    description "The total number of flow records sent to the remote Cflowd direct export collector.";
                                }

                            } // list esa

                            list isa {
                                key "mda-id";
                                description "Enter the isa list instance";

                                leaf mda-id {
                                    type types-isa:slot-mda;
                                    description "MDA/ISA ID";
                                }

                                leaf oper-state {
                                    type types-sros:oper-state;
                                    description "The operational status of the of the cflowd direct export collector.";
                                }

                                leaf records-sent {
                                    type yang:counter64;
                                    description "The total number of flow records sent to the remote Cflowd direct export collector.";
                                }

                            } // list isa

                            container summary {
                                description "Enter the summary context";

                                leaf oper-state {
                                    type types-sros:oper-state;
                                    description "The operational status of the of the cflowd direct export collector.";
                                }

                                leaf records-sent {
                                    type yang:counter64;
                                    description "The total number of flow records sent to the remote Cflowd direct export collector.";
                                }

                            } // container summary

                        } // list address

                    } // list collector

                } // container direct-export

            } // container cflowd

            list dns-ip-cache {
                key "dns-ip-cache-name";
                description "Enter the dns-ip-cache list instance";

                leaf dns-ip-cache-name {
                    type types-sros:named-item;
                    description "DNS IP cache name within the AA group";
                }

                list esa {
                    key "esa-id vm";
                    description "Enter the esa list instance";

                    leaf esa-id {
                        type types-esa:esa-id;
                        description "ESA ID";
                    }

                    leaf vm {
                        type types-esa:vm-id;
                        description "VM ID within the ESA";
                    }

                    container dns {
                        description "Enter the dns context";

                        container statistics {
                            description "Enter the statistics context";

                            leaf total-responses {
                                type yang:counter64;
                                description
                                    "The number of DNS responses that have been compared to the DNS domain expressions
                                     associated with this cache.";
                            }

                            leaf domain-name-match {
                                type yang:counter64;
                                description
                                    "The number of DNS responses for domains that matched a DNS domain expression associated
                                     with this cache.";
                            }

                            leaf domain-name-and-server-match {
                                type yang:counter64;
                                description
                                    "The number of DNS responses whose domain matched a DNS domain expression and
                                     server IP address matched a trusted DNS server address associated with this cache.
                                     In the absence of a configured trusted DNS server address, all DNS servers are trusted.";
                            }

                        } // container statistics

                    } // container dns

                    container cache {
                        description "Enter the cache context";

                        leaf threshold-alarm-clear {
                            type boolean;
                            description
                                "Indicates the state of the threshold alarm for this cache. A value of 'true' indicates the
                                 alarm is clear, and a value of 'false' indicates the alarm is set.";
                        }

                        container statistics {
                            description "Enter the statistics context";

                            leaf total-addresses-added {
                                type yang:counter64;
                                description "The total number of addresses that have been added to this cache.";
                            }

                            leaf total-addresses-removed {
                                type yang:counter64;
                                description "The total number of addresses that have been removed from this cache.";
                            }

                            leaf cache-full-error {
                                type yang:counter64;
                                description "The number of times an entry could not be added because the cache was full.";
                            }

                            leaf static-address-match {
                                type yang:counter64;
                                description "The number of times an IP address lookup in the cache matched a statically configured address.";
                            }

                            leaf cached-address-match {
                                type yang:counter64;
                                description "The number of times an IP address lookup in the cache matched a dynamically learned address.";
                            }

                            leaf address-miss {
                                type yang:counter64;
                                description "The number of times an IP address lookup in this cache was unsuccessful.";
                            }

                        } // container statistics

                    } // container cache

                } // list esa

                list isa {
                    key "mda-id";
                    description "Enter the isa list instance";

                    leaf mda-id {
                        type types-isa:slot-mda;
                        description "MDA/ISA ID";
                    }

                    container dns {
                        description "Enter the dns context";

                        container statistics {
                            description "Enter the statistics context";

                            leaf total-responses {
                                type yang:counter64;
                                description
                                    "The number of DNS responses that have been compared to the DNS domain expressions
                                     associated with this cache.";
                            }

                            leaf domain-name-match {
                                type yang:counter64;
                                description
                                    "The number of DNS responses for domains that matched a DNS domain expression associated
                                     with this cache.";
                            }

                            leaf domain-name-and-server-match {
                                type yang:counter64;
                                description
                                    "The number of DNS responses whose domain matched a DNS domain expression and
                                     server IP address matched a trusted DNS server address associated with this cache.
                                     In the absence of a configured trusted DNS server address, all DNS servers are trusted.";
                            }

                        } // container statistics

                    } // container dns

                    container cache {
                        description "Enter the cache context";

                        leaf threshold-alarm-clear {
                            type boolean;
                            description
                                "Indicates the state of the threshold alarm for this cache. A value of 'true' indicates the
                                 alarm is clear, and a value of 'false' indicates the alarm is set.";
                        }

                        container statistics {
                            description "Enter the statistics context";

                            leaf total-addresses-added {
                                type yang:counter64;
                                description "The total number of addresses that have been added to this cache.";
                            }

                            leaf total-addresses-removed {
                                type yang:counter64;
                                description "The total number of addresses that have been removed from this cache.";
                            }

                            leaf cache-full-error {
                                type yang:counter64;
                                description "The number of times an entry could not be added because the cache was full.";
                            }

                            leaf static-address-match {
                                type yang:counter64;
                                description "The number of times an IP address lookup in the cache matched a statically configured address.";
                            }

                            leaf cached-address-match {
                                type yang:counter64;
                                description "The number of times an IP address lookup in the cache matched a dynamically learned address.";
                            }

                            leaf address-miss {
                                type yang:counter64;
                                description "The number of times an IP address lookup in this cache was unsuccessful.";
                            }

                        } // container statistics

                    } // container cache

                } // list isa

                container summary {
                    description "Enter the summary context";

                    container dns {
                        description "Enter the dns context";

                        container statistics {
                            description "Enter the statistics context";

                            leaf total-responses {
                                type yang:counter64;
                                description
                                    "The number of DNS responses that have been compared to the DNS domain expressions
                                     associated with this cache.";
                            }

                            leaf domain-name-match {
                                type yang:counter64;
                                description
                                    "The number of DNS responses for domains that matched a DNS domain expression associated
                                     with this cache.";
                            }

                            leaf domain-name-and-server-match {
                                type yang:counter64;
                                description
                                    "The number of DNS responses whose domain matched a DNS domain expression and
                                     server IP address matched a trusted DNS server address associated with this cache.
                                     In the absence of a configured trusted DNS server address, all DNS servers are trusted.";
                            }

                        } // container statistics

                    } // container dns

                    container cache {
                        description "Enter the cache context";

                        leaf threshold-alarm-clear {
                            type boolean;
                            description
                                "Indicates the state of the threshold alarm for this cache. A value of 'true' indicates the
                                 alarm is clear, and a value of 'false' indicates the alarm is set.";
                        }

                        container statistics {
                            description "Enter the statistics context";

                            leaf total-addresses-added {
                                type yang:counter64;
                                description "The total number of addresses that have been added to this cache.";
                            }

                            leaf total-addresses-removed {
                                type yang:counter64;
                                description "The total number of addresses that have been removed from this cache.";
                            }

                            leaf cache-full-error {
                                type yang:counter64;
                                description "The number of times an entry could not be added because the cache was full.";
                            }

                            leaf static-address-match {
                                type yang:counter64;
                                description "The number of times an IP address lookup in the cache matched a statically configured address.";
                            }

                            leaf cached-address-match {
                                type yang:counter64;
                                description "The number of times an IP address lookup in the cache matched a dynamically learned address.";
                            }

                            leaf address-miss {
                                type yang:counter64;
                                description "The number of times an IP address lookup in this cache was unsuccessful.";
                            }

                        } // container statistics

                    } // container cache

                } // container summary

            } // list dns-ip-cache

            container status {
                description "Enter the status context";

                container cflowd {
                    description "Enter the cflowd context";

                    list export-type {
                        key "flow-export-type";
                        description "Enter the export-type list instance";

                        leaf flow-export-type {
                            type types-aa:cflowd-export-type;
                            description "Cflowd flow export type for the partition";
                        }

                        list esa {
                            key "esa-id vm";
                            description "Enter the esa list instance";

                            leaf esa-id {
                                type types-esa:esa-id;
                                description "ESA ID";
                            }

                            leaf vm {
                                type types-esa:vm-id;
                                description "VM ID within the ESA";
                            }

                            container statistics {
                                description "Enter the statistics context";

                                leaf active-flows {
                                    type yang:gauge32;
                                    units "flows";
                                    description "The number of active flows currently marked for export using Cflowd in the ISA-AA MDA(s).";
                                }

                                leaf records-export-rate {
                                    type yang:gauge32;
                                    units "records per second";
                                    description "The number of flow records per second being exported using Cflowd from the ISA-AA MDA(s).";
                                }

                                leaf records-reported {
                                    type yang:counter64;
                                    description "The total number of flow records reported from the ISA-AA MDA(s).";
                                }

                                leaf records-dropped {
                                    type yang:counter64;
                                    description "The total number of flow records dropped in the ISA-AA MDA(s).";
                                }

                                leaf packets-sent {
                                    type yang:counter64;
                                    units "packets";
                                    description "The total number of Cflowd packets sent from the ISA-AA MDA(s).";
                                }

                                leaf packets-sent-rate {
                                    type yang:gauge32;
                                    units "packets";
                                    description
                                        "The number of Cflowd packets per second being exported from the ISA-AA MDA(s).
                                         The calculation is based on the number of Cflowd packets generated within the last 10 seconds.";
                                }

                                leaf perf-resource-not-allocated {
                                    type yang:counter64;
                                    units "flows";
                                    description "The total number of flows that were selected for export but failed to obtain Cflowd resources in the ISA-AA MDA(s).";
                                }

                                leaf rtp-unsupported-ssrc-streams {
                                    type yang:counter64;
                                    description
                                        "The number of synchronization source (SSRC) records which had to be aborted (due to reasons such as
                                         unknown codec type, non media stream, codec switch, etc).";
                                }

                            } // container statistics

                        } // list esa

                        list isa {
                            key "mda-id";
                            description "Enter the isa list instance";

                            leaf mda-id {
                                type types-isa:slot-mda;
                                description "MDA/ISA ID";
                            }

                            container statistics {
                                description "Enter the statistics context";

                                leaf active-flows {
                                    type yang:gauge32;
                                    units "flows";
                                    description "The number of active flows currently marked for export using Cflowd in the ISA-AA MDA(s).";
                                }

                                leaf records-export-rate {
                                    type yang:gauge32;
                                    units "records per second";
                                    description "The number of flow records per second being exported using Cflowd from the ISA-AA MDA(s).";
                                }

                                leaf records-reported {
                                    type yang:counter64;
                                    description "The total number of flow records reported from the ISA-AA MDA(s).";
                                }

                                leaf records-dropped {
                                    type yang:counter64;
                                    description "The total number of flow records dropped in the ISA-AA MDA(s).";
                                }

                                leaf packets-sent {
                                    type yang:counter64;
                                    units "packets";
                                    description "The total number of Cflowd packets sent from the ISA-AA MDA(s).";
                                }

                                leaf packets-sent-rate {
                                    type yang:gauge32;
                                    units "packets";
                                    description
                                        "The number of Cflowd packets per second being exported from the ISA-AA MDA(s).
                                         The calculation is based on the number of Cflowd packets generated within the last 10 seconds.";
                                }

                                leaf perf-resource-not-allocated {
                                    type yang:counter64;
                                    units "flows";
                                    description "The total number of flows that were selected for export but failed to obtain Cflowd resources in the ISA-AA MDA(s).";
                                }

                                leaf rtp-unsupported-ssrc-streams {
                                    type yang:counter64;
                                    description
                                        "The number of synchronization source (SSRC) records which had to be aborted (due to reasons such as
                                         unknown codec type, non media stream, codec switch, etc).";
                                }

                            } // container statistics

                        } // list isa

                        container summary {
                            description "Enter the summary context";

                            container statistics {
                                description "Enter the statistics context";

                                leaf active-flows {
                                    type yang:gauge32;
                                    units "flows";
                                    description "The number of active flows currently marked for export using Cflowd in the ISA-AA MDA(s).";
                                }

                                leaf records-export-rate {
                                    type yang:gauge32;
                                    units "records per second";
                                    description "The number of flow records per second being exported using Cflowd from the ISA-AA MDA(s).";
                                }

                                leaf records-reported {
                                    type yang:counter64;
                                    description "The total number of flow records reported from the ISA-AA MDA(s).";
                                }

                                leaf records-dropped {
                                    type yang:counter64;
                                    description "The total number of flow records dropped in the ISA-AA MDA(s).";
                                }

                                leaf packets-sent {
                                    type yang:counter64;
                                    units "packets";
                                    description "The total number of Cflowd packets sent from the ISA-AA MDA(s).";
                                }

                                leaf packets-sent-rate {
                                    type yang:gauge32;
                                    units "packets";
                                    description
                                        "The number of Cflowd packets per second being exported from the ISA-AA MDA(s).
                                         The calculation is based on the number of Cflowd packets generated within the last 10 seconds.";
                                }

                                leaf perf-resource-not-allocated {
                                    type yang:counter64;
                                    units "flows";
                                    description "The total number of flows that were selected for export but failed to obtain Cflowd resources in the ISA-AA MDA(s).";
                                }

                                leaf rtp-unsupported-ssrc-streams {
                                    type yang:counter64;
                                    description
                                        "The number of synchronization source (SSRC) records which had to be aborted (due to reasons such as
                                         unknown codec type, non media stream, codec switch, etc).";
                                }

                            } // container statistics

                        } // container summary

                    } // list export-type

                } // container cflowd

                list esa {
                    key "esa-id vm";
                    description "Enter the esa list instance";

                    leaf esa-id {
                        type types-esa:esa-id;
                        description "ESA ID";
                    }

                    leaf vm {
                        type types-esa:vm-id;
                        description "VM ID within the ESA";
                    }

                    leaf max-flow-resources {
                        type yang:gauge32;
                        units "flows";
                        description "The maximum number of flow resources on the ISA-AA MDA(s).";
                    }

                    container statistics {
                        description "Enter the statistics context";

                        leaf flows {
                            type yang:counter64;
                            units "flows";
                            description "The total number of flows created on the ISA-AA MDA(s).";
                        }

                        leaf aa-subscribers-created {
                            type yang:counter64;
                            description "The number of subscribers created.";
                        }

                        leaf aa-subscribers-deleted {
                            type yang:counter64;
                            description "The number of subscribers deleted.";
                        }

                        leaf aa-subscribers-modified {
                            type yang:counter64;
                            description "The number of subscribers modified.";
                        }

                        leaf aa-subscribers-quarantined {
                            type yang:counter64;
                            description "The number of subscribers quarantined.";
                        }

                        leaf seen-ip-requests-sent {
                            type yang:counter64;
                            description
                                "The number of requests sent from the ISA-AA MDA to initiate dynamic transit subscriber creation when traffic
                                 is detected on a parent SAP or Spoke SDP.";
                        }

                        leaf seen-ip-requests-dropped {
                            type yang:counter64;
                            description "The number of Seen IP requests dropped by the ISA-AA MDA due to congestion control mechanisms.";
                        }

                        container diverted-discards {
                            description "Enter the diverted-discards context";

                            container congestion {
                                description "Enter the congestion context";

                                leaf octets {
                                    type yang:counter64;
                                    units "bytes";
                                    description "Number of bytes discarded by the IOMs prior to the ISA-AA MDA(s) due to egress IOM congestion.";
                                }

                                leaf packets {
                                    type yang:counter64;
                                    units "packets";
                                    description "Number of packets discarded by the IOMs prior to the ISA-AA MDA(s) due to egress IOM congestion.";
                                }

                            } // container congestion

                            container errors {
                                description "Enter the errors context";

                                leaf packets {
                                    type yang:counter64;
                                    units "packets";
                                    description "Number of packets discarded by the egress P-chip due to errors in the packets.";
                                }

                            } // container errors

                        } // container diverted-discards

                        container returned-discards {
                            description "Enter the returned-discards context";

                            container congestion {
                                description "Enter the congestion context";

                                leaf octets {
                                    type yang:counter64;
                                    units "bytes";
                                    description "Number of bytes discarded by the IOMs after the ISA-AA MDA(s) due to ingress IOM congestion.";
                                }

                                leaf packets {
                                    type yang:counter64;
                                    units "packets";
                                    description "Number of packets discarded by the IOMs after the ISA-AA MDA(s) due to ingress IOM congestion.";
                                }

                            } // container congestion

                            container errors {
                                description "Enter the errors context";

                                leaf packets {
                                    type yang:counter64;
                                    units "packets";
                                    description "Number of packets discarded due to an error detected by the P-chip while attempting to return the packet to the normal forwarding path.";
                                }

                            } // container errors

                        } // container returned-discards

                        container congestion-discards {
                            description "Enter the congestion-discards context";

                            leaf octets {
                                type yang:counter64;
                                units "bytes";
                                description "Number of bytes discarded by the IOMs after the ISA-AA MDA(s) due IOM congestion.";
                            }

                            leaf packets {
                                type yang:counter64;
                                units "packets";
                                description "Number of packets discarded by the IOMs after the ISA-AA MDA(s) due to IOM congestion.";
                            }

                        } // container congestion-discards

                        container active-flows {
                            description "Enter the active-flows context";

                            leaf current {
                                type yang:gauge32;
                                units "flows";
                                description "The number of active flows currently being tracked by the ISA-AA MDA(s).";
                            }

                            leaf average {
                                type yang:gauge32;
                                units "flows";
                                description "The average number of active flows being tracked by the ISA-AA MDA(s) within the last 60 minutes.";
                            }

                            leaf peak {
                                type yang:gauge32;
                                units "flows";
                                description "The peak number of active flows being tracked by the ISA-AA MDA(s) since system startup.";
                            }

                        } // container active-flows

                        container aa-subscribers-downloaded {
                            description "Enter the aa-subscribers-downloaded context";

                            leaf current {
                                type yang:gauge32;
                                description
                                    "The number of subscribers defined in TIMETRA-SUBSCRIBER-MGMT-MIB::tmnxSubInfoAppProfile
                                     in the tmnxSubscriberInfoTable with tmnxBsxAppProfDivert set to 'true'.";
                            }

                            leaf average {
                                type yang:gauge32;
                                description
                                    "The average number of subscribers defined in TIMETRA-SUBSCRIBER-MGMT-MIB::tmnxSubInfoAppProfile
                                     in the tmnxSubscriberInfoTable with tmnxBsxAppProfDivert set to 'true' within the last 60 minutes.";
                            }

                            leaf peak {
                                type yang:gauge32;
                                description
                                    "The peak number of subscribers defined in TIMETRA-SUBSCRIBER-MGMT-MIB::tmnxSubInfoAppProfile
                                     in the tmnxSubscriberInfoTable with tmnxBsxAppProfDivert set to 'true' since system startup.";
                            }

                        } // container aa-subscribers-downloaded

                        container active-subscribers {
                            description "Enter the active-subscribers context";

                            leaf current {
                                type yang:gauge32;
                                description "The number of subscribers currently with flow records in the ISA-AA MDA(s).";
                            }

                            leaf average {
                                type yang:gauge32;
                                description "The average number of subscribers with flow records in the ISA-AA MDA(s) within the last 60 minutes.";
                            }

                            leaf peak {
                                type yang:gauge32;
                                description "The peak number of subscribers with flow records in the ISA-AA MDA(s) since system startup.";
                            }

                        } // container active-subscribers

                        container diverted-traffic {
                            description "Enter the diverted-traffic context";

                            leaf octets {
                                type yang:counter64;
                                units "bytes";
                                description "Number of bytes diverted from ingress IOMs towards the ISA-AA MDA(s).";
                            }

                            leaf packets {
                                type yang:counter64;
                                units "packets";
                                description "Number of packets diverted from ingress IOMs towards the ISA-AA MDA(s).";
                            }

                        } // container diverted-traffic

                        container entered-aa {
                            description "Enter the entered-aa context";

                            leaf octets {
                                type yang:counter64;
                                units "bytes";
                                description "Number of bytes sent from an IOM which enter the ISA-AA MDA(s).";
                            }

                            leaf packets {
                                type yang:counter64;
                                units "packets";
                                description "Number of packets sent from an IOM which enter the ISA-AA MDA(s).";
                            }

                        } // container entered-aa

                        container inspected {
                            description "Enter the inspected context";

                            leaf octets {
                                type yang:counter64;
                                units "bytes";
                                description "Number of bytes sent for protocol determination in the ISA-AA MDA(s).";
                            }

                            leaf packets {
                                type yang:counter64;
                                units "packets";
                                description "Number of packets sent for protocol determination in the ISA-AA MDA(s).";
                            }

                        } // container inspected

                        container exited-aa {
                            description "Enter the exited-aa context";

                            leaf octets {
                                type yang:counter64;
                                units "bytes";
                                description "Number of bytes which exit the ISA-AA MDA(s) and are sent to the local IOM.";
                            }

                            leaf packets {
                                type yang:counter64;
                                units "packets";
                                description "Number of packets which exit the ISA-AA MDA(s) and are sent to the local IOM.";
                            }

                        } // container exited-aa

                        container buffered-in-aa {
                            description "Enter the buffered-in-aa context";

                            leaf octets {
                                type yang:counter64;
                                units "bytes";
                                description "Number of bytes buffered by the ISA-AA MDA(s).";
                            }

                            leaf packets {
                                type yang:counter64;
                                units "packets";
                                description "Number of packets buffered by the ISA-AA MDA(s).";
                            }

                        } // container buffered-in-aa

                        container discarded-in-aa {
                            description "Enter the discarded-in-aa context";

                            container policy {
                                description "Enter the policy context";

                                leaf octets {
                                    type yang:counter64;
                                    units "bytes";
                                    description "Number of bytes discarded by the ISA-AA MDA(s) due to policy.";
                                }

                                leaf packets {
                                    type yang:counter64;
                                    units "packets";
                                    description "Number of packets discarded by the ISA-AA MDA(s) due to policy.";
                                }

                            } // container policy

                            container congestion {
                                description "Enter the congestion context";

                                leaf octets {
                                    type yang:counter64;
                                    units "bytes";
                                    description "Number of bytes discarded by the ISA-AA MDA(s) due to congestion.";
                                }

                                leaf packets {
                                    type yang:counter64;
                                    units "packets";
                                    description "Number of packets discarded by the ISA-AA MDA(s) due to congestion.";
                                }

                            } // container congestion

                            container errors {
                                description "Enter the errors context";

                                leaf octets {
                                    type yang:counter64;
                                    units "bytes";
                                    description "Number of bytes discarded due to unrecoverable errors.";
                                }

                                leaf packets {
                                    type yang:counter64;
                                    units "packets";
                                    description "Number of packets discarded due to unrecoverable errors.";
                                }

                            } // container errors

                            container tcp-optimization {
                                description "Enter the tcp-optimization context";

                            } // container tcp-optimization

                        } // container discarded-in-aa

                        container modified-in-aa {
                            description "Enter the modified-in-aa context";

                            container packet-size-increased {
                                description "Enter the packet-size-increased context";

                                leaf octets {
                                    type yang:counter64;
                                    units "bytes";
                                    description "Number of additional octets the ISA-AA MDA injected into the packets.";
                                }

                                leaf packets {
                                    type yang:counter64;
                                    units "packets";
                                    description "Number of packets that the ISA-AA MDA has increased in size.";
                                }

                            } // container packet-size-increased

                            container packet-size-decreased {
                                description "Enter the packet-size-decreased context";

                                leaf octets {
                                    type yang:counter64;
                                    units "bytes";
                                    description "Number of octets the ISA-AA MDA has removed from packets.";
                                }

                                leaf packets {
                                    type yang:counter64;
                                    units "packets";
                                    description "Number of packets that the ISA-AA MDA has decreased in size.";
                                }

                            } // container packet-size-decreased

                        } // container modified-in-aa

                        container errors {
                            description "Enter the errors context";

                            container policy-bypass {
                                description "Enter the policy-bypass context";

                                leaf octets {
                                    type yang:counter64;
                                    units "bytes";
                                    description
                                        "Number of octets which pass untouched that did not have statistics or policy applied.
                                         These bytes are counted as policy bypass errors.";
                                }

                                leaf packets {
                                    type yang:counter64;
                                    units "packets";
                                    description
                                        "Number of packets which passed untouched that did not have statistics or policy applied.
                                         These packets are counted as policy bypass errors.";
                                }

                            } // container policy-bypass

                            container cut-through {
                                description "Enter the cut-through context";

                                leaf octets {
                                    type yang:counter64;
                                    units "bytes";
                                    description
                                        "Number of octets which passed untouched, but have policy applied.
                                         These octets are counted as cut-through errors.";
                                }

                                leaf packets {
                                    type yang:counter64;
                                    units "packets";
                                    description
                                        "Number of packets which passed untouched, but have policy applied.
                                         These packets are counted as cut-through errors.";
                                }

                                container flow-resource {
                                    description "Enter the flow-resource context";

                                    leaf octets {
                                        type yang:counter64;
                                        units "bytes";
                                        description "Number of octets that the ISA-AA MDA(s) have cut-through due to flow resource exhaustion.";
                                    }

                                    leaf packets {
                                        type yang:counter64;
                                        units "packets";
                                        description "Number of packets that the ISA-AA MDA(s) have cut-through due to flow resource exhaustion.";
                                    }

                                } // container flow-resource

                                container overload {
                                    description "Enter the overload context";

                                    leaf octets {
                                        type yang:counter64;
                                        units "bytes";
                                        description "Number of octets that the ISA-AA MDA has cut-through due to the overload cut-through configuration as indicated by the object tmnxBsxIsaAaGrpOverloadCutThru.";
                                    }

                                    leaf packets {
                                        type yang:counter64;
                                        units "packets";
                                        description "Number of octets that the ISA-AA MDA has cut-through due to the overload cut-through configuration as indicated by the object tmnxBsxIsaAaGrpOverloadCutThru.";
                                    }

                                } // container overload

                            } // container cut-through

                        } // container errors

                        container generated-in-aa {
                            description "Enter the generated-in-aa context";

                            container http-redirect {
                                description "Enter the http-redirect context";

                                leaf octets {
                                    type yang:counter64;
                                    units "bytes";
                                    description "Number of octets that the ISA-AA MDA has created to redirect HTTP and HTTPS.";
                                }

                                leaf packets {
                                    type yang:counter64;
                                    units "packets";
                                    description "Number of packets that the ISA-AA MDA has created to redirect HTTP and HTTPS.";
                                }

                            } // container http-redirect

                        } // container generated-in-aa

                        container returned-traffic {
                            description "Enter the returned-traffic context";

                            leaf octets {
                                type yang:counter64;
                                units "bytes";
                                description "Number of bytes returned to the normal forwarding path that are sent to egress IOMs from the ISA-AA MDA(s).";
                            }

                            leaf packets {
                                type yang:counter64;
                                units "packets";
                                description "Number of packets returned to the normal forwarding path that are sent to egress IOMs from the ISA-AA MDA(s).";
                            }

                        } // container returned-traffic

                        container flow-resources {
                            description "Enter the flow-resources context";

                            leaf current {
                                type yang:gauge32;
                                description "The number of flow resources currently in-use on the ISA-AA MDA(s).";
                            }

                            leaf average {
                                type yang:gauge32;
                                units "flows";
                                description "The average number of flow resources in use on the ISA-AA MDA(s) within the last 60 minutes.";
                            }

                            leaf peak {
                                type yang:gauge32;
                                units "flows";
                                description "The peak number of flow resources in use on the ISA-AA MDA(s) since system startup.";
                            }

                            leaf current-percent {
                                type uint32 {
                                    range "0..10000";
                                }
                                units "centipercent";
                                description "The current percentage of total flow resources in-use on the ISA-AA MDA.";
                            }

                            leaf average-percent {
                                type uint32 {
                                    range "0..10000";
                                }
                                units "centipercent";
                                description "The average percentage of total flow resources in-use on the ISA-AA MDA.";
                            }

                            leaf peak-percent {
                                type uint32 {
                                    range "0..10000";
                                }
                                units "centipercent";
                                description "The peak percentage of total flow resources in-use on the ISA-AA MDA.";
                            }

                        } // container flow-resources

                        container flow-setup-rate {
                            description "Enter the flow-setup-rate context";

                            leaf current {
                                type yang:gauge32;
                                units "flows per second";
                                description "The number of flow setups per second over the most recent 10 second period.";
                            }

                            leaf average {
                                type yang:gauge32;
                                units "flows per second";
                                description "The average number of flow setups per second being tracked by the ISA-AA MDA(s) within the last 60 minutes.";
                            }

                            leaf peak {
                                type yang:gauge32;
                                units "flows per second";
                                description "The peak number of flow setups per second being tracked by the ISA-AA MDA(s) since system startup.";
                            }

                        } // container flow-setup-rate

                        container traffic-rate {
                            description "Enter the traffic-rate context";

                            leaf current {
                                type yang:gauge32;
                                units "megabps";
                                description "The traffic rate in megabits(s) per second (mbps) incoming to the ISA-AA MDA(s).";
                            }

                            leaf average {
                                type yang:gauge32;
                                units "megabps";
                                description "The average traffic rate in megabits(s) per second (mbps) incoming to the ISA-AA MDA(s) within the last 60 minutes.";
                            }

                            leaf peak {
                                type yang:gauge32;
                                units "megabps";
                                description "The peak traffic rate in megabits(s) per second (mbps) incoming to the ISA-AA MDA(s) since system startup.";
                            }

                        } // container traffic-rate

                        container packet-rate {
                            description "Enter the packet-rate context";

                            leaf current {
                                type yang:gauge32;
                                units "packets per second";
                                description "The current number of packets per second incoming to the ISA-AA MDA(s).";
                            }

                            leaf average {
                                type yang:gauge32;
                                units "packets per second";
                                description "The average number of packets per second incoming to the ISA-AA MDA(s) within the last 60 minutes.";
                            }

                            leaf peak {
                                type yang:gauge32;
                                units "packets per second";
                                description "The peak number of packets per second incoming to the ISA-AA MDA(s) since system startup.";
                            }

                        } // container packet-rate

                        container datapath-cpu-usage {
                            description "Enter the datapath-cpu-usage context";

                            leaf current {
                                type uint32 {
                                    range "0..10000";
                                }
                                units "centipercent";
                                description "The percent utilization of the datapath CPU on the ISA-AA MDA(s).";
                            }

                            leaf average {
                                type uint32 {
                                    range "0..10000";
                                }
                                units "centipercent";
                                description "The average percent utilization of the datapath CPU on the ISA-AA MDA(s) within the last 60 minutes.";
                            }

                            leaf peak {
                                type uint32 {
                                    range "0..10000";
                                }
                                units "centipercent";
                                description "The peak percent utilization of the datapath CPU on the ISA-AA MDA(s) since system startup.";
                            }

                        } // container datapath-cpu-usage

                        container management-cpu-usage {
                            description "Enter the management-cpu-usage context";

                            leaf current {
                                type uint32 {
                                    range "0..10000";
                                }
                                units "centipercent";
                                description "The percent utilization of the management CPU on the ISA-AA MDA(s).";
                            }

                            leaf average {
                                type uint32 {
                                    range "0..10000";
                                }
                                units "centipercent";
                                description "The average percent utilization of the management CPU on the ISA-AA MDA(s) within the last 60 minutes.";
                            }

                            leaf peak {
                                type uint32 {
                                    range "0..10000";
                                }
                                units "centipercent";
                                description "The peak percent utilization of the management CPU on the ISA-AA MDA(s) since system startup.";
                            }

                        } // container management-cpu-usage

                    } // container statistics

                    container tca {
                        description "Enter the tca context";

                        container flow-resources {
                            description "Enter the flow-resources context";

                            leaf state {
                                type types-aa:tca-state;
                                description "The state of the flow resource TCA (tmnxBsxIsaAaGrpFlowFull).";
                            }

                            container statistics {
                                description "Enter the statistics context";

                                leaf count {
                                    type yang:counter64;
                                    description "The number of times the flow resource TCA (tmnxBsxIsaAaGrpFlowFull) was raised since system startup.";
                                }

                                leaf duration {
                                    type yang:counter64;
                                    units "seconds";
                                    description "The amount of time the flow resource TCA (tmnxBsxIsaAaGrpFlowFull) was in the raised state since system startup.";
                                }

                            } // container statistics

                        } // container flow-resources

                        container flow-setup-rate {
                            description "Enter the flow-setup-rate context";

                            leaf state {
                                type types-aa:tca-state;
                                description "The state of the flow setup rate TCA (tmnxBsxIsaAaGrpFlowSetup).";
                            }

                            container statistics {
                                description "Enter the statistics context";

                                leaf count {
                                    type yang:counter64;
                                    description "The number of times the flow setup rate TCA (tmnxBsxIsaAaGrpFlowSetup) was raised since system startup.";
                                }

                                leaf duration {
                                    type yang:counter64;
                                    units "seconds";
                                    description "The amount of time the flow setup rate TCA (tmnxBsxIsaAaGrpFlowSetup) was in the raised state since system startup.";
                                }

                            } // container statistics

                        } // container flow-setup-rate

                        container traffic-rate {
                            description "Enter the traffic-rate context";

                            leaf state {
                                type types-aa:tca-state;
                                description "The state of the bit rate TCA (tmnxBsxIsaAaGrpBitRate).";
                            }

                            container statistics {
                                description "Enter the statistics context";

                                leaf count {
                                    type yang:counter64;
                                    description "The number of times the bit rate TCA (tmnxBsxIsaAaGrpBitRate) was raised since system startup.";
                                }

                                leaf duration {
                                    type yang:counter64;
                                    units "seconds";
                                    description "The amount time the bit rate TCA (tmnxBsxIsaAaGrpBitRate) was in the raised state since system startup.";
                                }

                            } // container statistics

                        } // container traffic-rate

                        container packet-rate {
                            description "Enter the packet-rate context";

                            leaf state {
                                type types-aa:tca-state;
                                description "The state of the packet rate TCA (tmnxBsxIsaAaGrpPacketRate).";
                            }

                            container statistics {
                                description "Enter the statistics context";

                                leaf count {
                                    type yang:counter64;
                                    description "The number of times the packet rate TCA (tmnxBsxIsaAaGrpPacketRate) was raised since system startup.";
                                }

                                leaf duration {
                                    type yang:counter64;
                                    units "seconds";
                                    description "The amount of time the packet rate TCA (tmnxBsxIsaAaGrpPacketRate) was in the raised state since system startup.";
                                }

                            } // container statistics

                        } // container packet-rate

                        container datapath-cpu-usage {
                            description "Enter the datapath-cpu-usage context";

                            leaf state {
                                type types-aa:tca-state;
                                description "The state of the datapath CPU TCA (tmnxBsxDatapathCpuUsage).";
                            }

                            container statistics {
                                description "Enter the statistics context";

                                leaf count {
                                    type yang:counter64;
                                    description "The number of times the datapath CPU TCA (tmnxBsxDatapathCpuUsage) was raised since system startup.";
                                }

                                leaf duration {
                                    type yang:counter64;
                                    units "seconds";
                                    description "The amount of time the datapath CPU TCA (tmnxBsxDatapathCpuUsage) was in the raised state since system startup.";
                                }

                            } // container statistics

                        } // container datapath-cpu-usage

                        container isa-overload {
                            description "Enter the isa-overload context";

                            leaf state {
                                type types-aa:tca-state;
                                description "The state of the overload cut-through TCA (tmnxBsxIsaAaGrpOvrldCutthru).";
                            }

                            container statistics {
                                description "Enter the statistics context";

                                leaf count {
                                    type yang:counter64;
                                    description "The number of times the overload cut-through TCA (tmnxBsxIsaAaGrpOvrldCutthru) was raised since system startup.";
                                }

                                leaf duration {
                                    type yang:counter64;
                                    units "seconds";
                                    description "The amount of time the overload cut-through TCA (tmnxBsxIsaAaGrpOvrldCutthru) was in the raised state since system startup.";
                                }

                            } // container statistics

                        } // container isa-overload

                    } // container tca

                    container sub-to-net {
                        description "Enter the sub-to-net context";

                        container overload-cut-through-tca {
                            description "Enter the overload-cut-through-tca context";

                            leaf state {
                                type types-aa:tca-state;
                                description "The state of the subscriber to network weighted average shared buffer TCA (tmnxBsxIsaAaGrpFmSbWaSBufOvld).";
                            }

                            leaf current-wa-buffer-depth {
                                type uint32 {
                                    range "0..10000";
                                }
                                units "centipercent";
                                description "The percent utilization of the subscriber to network weighted average shared buffer on the ISA-AA MDA(s).";
                            }

                            container statistics {
                                description "Enter the statistics context";

                                leaf count {
                                    type yang:counter64;
                                    description "The number of times the subscriber to network weighted average shared buffer TCA (tmnxBsxIsaAaGrpFmSbWaSBufOvld) was raised since system startup.";
                                }

                                leaf duration {
                                    type yang:counter64;
                                    units "seconds";
                                    description "The amount of time the subscriber to network weighted average shared buffer TCA (tmnxBsxIsaAaGrpFmSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the subscriber-to-network direction.";
                                }

                                leaf packets {
                                    type yang:counter64;
                                    units "packets";
                                    description "Number of packets diverted from ingress IOMs towards the ISA-AA MDA(s) in the subscriber-to-network direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the subscriber-to-network direction.";
                                    }

                                    leaf packets {
                                        type yang:counter64;
                                        units "packets";
                                        description "Number of packets discarded by the IOMs prior to the ISA-AA MDA(s) due to egress IOM congestion in the subscriber-to-network direction.";
                                    }

                                } // container congestion

                                container errors {
                                    description "Enter the errors context";

                                    leaf packets {
                                        type yang:counter64;
                                        units "packets";
                                        description "Number of packets discarded by the egress P-chip due to errors in the packets in the subscriber-to-network direction.";
                                    }

                                } // container errors

                            } // container diverted-discards

                            container entered-aa {
                                description "Enter the entered-aa context";

                                leaf octets {
                                    type yang:counter64;
                                    units "bytes";
                                    description "Number of bytes sent from an IOM which enter the ISA-AA MDA(s) in the subscriber-to-network direction.";
                                }

                                leaf packets {
                                    type yang:counter64;
                                    units "packets";
                                    description "Number of packets sent from an IOM which enter the ISA-AA MDA(s) in the subscriber-to-network direction.";
                                }

                            } // container entered-aa

                            container buffered-in-aa {
                                description "Enter the buffered-in-aa context";

                                leaf octets {
                                    type yang:counter64;
                                    units "bytes";
                                    description "Number of bytes buffered by the ISA-AA MDA(s) in the subscriber-to-network direction.";
                                }

                                leaf packets {
                                    type yang:counter64;
                                    units "packets";
                                    description "Number of packets buffered by the ISA-AA MDA(s) in the subscriber-to-network direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the subscriber-to-network direction.";
                                    }

                                    leaf packets {
                                        type yang:counter64;
                                        units "packets";
                                        description "Number of packets discarded by the ISA-AA MDA(s) due to policy in the subscriber-to-network direction.";
                                    }

                                } // container policy

                                container congestion {
                                    description "Enter the congestion context";

                                    leaf octets {
                                        type yang:counter64;
                                        units "bytes";
                                        description "Number of bytes discarded by the ISA-AA MDA(s) due to congestion in the subscriber-to-network direction.";
                                    }

                                    leaf packets {
                                        type yang:counter64;
                                        units "packets";
                                        description "Number of packets discarded by the ISA-AA MDA(s) due to congestion in the subscriber-to-network direction.";
                                    }

                                } // container congestion

                                container errors {
                                    description "Enter the errors context";

                                    leaf octets {
                                        type yang:counter64;
                                        units "bytes";
                                        description "Number of bytes discarded due to unrecoverable errors in the subscriber-to-network direction.";
                                    }

                                    leaf packets {
                                        type yang:counter64;
                                        units "packets";
                                        description "Number of packets discarded due to unrecoverable errors in the subscriber-to-network direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the subscriber-to-network direction.";
                                    }

                                    leaf packets {
                                        type yang:counter64;
                                        units "packets";
                                        description "Number of packets that the ISA-AA MDA has increased in size in the subscriber-to-network direction.";
                                    }

                                } // container packet-size-increased

                                container packet-size-decreased {
                                    description "Enter the packet-size-decreased context";

                                    leaf octets {
                                        type yang:counter64;
                                        units "bytes";
                                        description "Number of octets the ISA-AA MDA has removed from packets in the subscriber-to-network direction.";
                                    }

                                    leaf packets {
                                        type yang:counter64;
                                        units "packets";
                                        description "Number of packets that the ISA-AA MDA has decreased in size in the subscriber-to-network direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which pass untouched that did not have statistics or policy applied.
                                             These bytes are counted as policy bypass errors in the subscriber-to-network direction.";
                                    }

                                    leaf packets {
                                        type yang:counter64;
                                        units "packets";
                                        description
                                            "Number of packets which passed untouched that did not have statistics or policy applied.
                                             These packets are counted as policy bypass errors in the subscriber-to-network direction.";
                                    }

                                } // container policy-bypass

                                container cut-through {
                                    description "Enter the cut-through context";

                                    leaf octets {
                                        type yang:counter64;
                                        units "bytes";
                                        description
                                            "Number of octets which passed untouched, but have policy applied in the subscriber-to-network direction.
                                             These octets are counted as cut-through errors.";
                                    }

                                    leaf packets {
                                        type yang:counter64;
                                        units "packets";
                                        description
                                            "Number of packets which passed untouched, but have policy applied in the subscriber-to-network direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the subscriber-to-network direction.";
                                    }

                                    leaf packets {
                                        type yang:counter64;
                                        units "packets";
                                        description "Number of packets that the ISA-AA MDA has created to redirect HTTP and HTTPS in the subscriber-to-network direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the subscriber-to-network direction.";
                                }

                                leaf packets {
                                    type yang:counter64;
                                    units "packets";
                                    description "Number of packets which exit the ISA-AA MDA(s) and are sent to the local IOM in the subscriber-to-network direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the subscriber-to-network direction.";
                                    }

                                    leaf packets {
                                        type yang:counter64;
                                        units "packets";
                                        description "Number of packets discarded by the IOMs after the ISA-AA MDA(s) due to ingress IOM congestion in the subscriber-to-network direction.";
                                    }

                                } // container congestion

                                container errors {
                                    description "Enter the errors context";

                                    leaf packets {
                                        type yang:counter64;
                                        units "packets";
                                        description
                                            "Number of packets discarded due to an error detected by the P-chip while attempting to return
                                             the packet to the normal forwarding path in the subscriber-to-network direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the subscriber-to-network direction.";
                                }

                                leaf packets {
                                    type yang:counter64;
                                    units "packets";
                                    description "Number of packets returned to the normal forwarding path that are sent to egress IOMs from the ISA-AA MDA(s) in the subscriber-to-network direction.";
                                }

                            } // container returned-traffic

                        } // container statistics

                    } // container sub-to-net

                    container net-to-sub {
                        description "Enter the net-to-sub context";

                        container overload-cut-through-tca {
                            description "Enter the overload-cut-through-tca context";

                            leaf current-wa-buffer-depth {
                                type uint32 {
                                    range "0..10000";
                                }
                                units "centipercent";
                                description "The percent utilization of the network to subscriber weighted average shared buffer on the ISA-AA MDA(s).";
                            }

                            leaf state {
                                type types-aa:tca-state;
                                description "The state of the network to subscriber weighted average shared buffer TCA (tmnxBsxIsaAaGrpToSbWaSBufOvld).";
                            }

                            container statistics {
                                description "Enter the statistics context";

                                leaf count {
                                    type yang:counter64;
                                    description "The number of times the network to subscriber weighted average shared buffer TCA (tmnxBsxIsaAaGrpToSbWaSBufOvld) was raised since system startup.";
                                }

                                leaf duration {
                                    type yang:counter64;
                                    units "seconds";
                                    description "The amount of time the network to subscriber weighted average shared buffer TCA (tmnxBsxIsaAaGrpToSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the network-to-subscriber direction.";
                                }

                                leaf packets {
                                    type yang:counter64;
                                    units "packets";
                                    description "Number of packets diverted from ingress IOMs towards the ISA-AA MDA(s) in the network-to-subscriber direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the network-to-subscriber direction.";
                                    }

                                    leaf packets {
                                        type yang:counter64;
                                        units "packets";
                                        description "Number of packets discarded by the IOMs prior to the ISA-AA MDA(s) due to egress IOM congestion in the network-to-subscriber direction.";
                                    }

                                } // container congestion

                                container errors {
                                    description "Enter the errors context";

                                    leaf packets {
                                        type yang:counter64;
                                        units "packets";
                                        description "Number of packets discarded by the egress P-chip due to errors in the packets in the network-to-subscriber direction";
                                    }

                                } // container errors

                            } // container diverted-discards

                            container entered-aa {
                                description "Enter the entered-aa context";

                                leaf octets {
                                    type yang:counter64;
                                    units "bytes";
                                    description "Number of bytes sent from an IOM which enter the ISA-AA MDA(s) in the network-to-subscriber direction.";
                                }

                                leaf packets {
                                    type yang:counter64;
                                    units "packets";
                                    description "Number of packets sent from an IOM which enter the ISA-AA MDA(s) in the network-to-subscriber direction.";
                                }

                            } // container entered-aa

                            container buffered-in-aa {
                                description "Enter the buffered-in-aa context";

                                leaf octets {
                                    type yang:counter64;
                                    units "bytes";
                                    description "Number of bytes buffered by the ISA-AA MDA(s) in the network-to-subscriber direction.";
                                }

                                leaf packets {
                                    type yang:counter64;
                                    units "packets";
                                    description "Number of packets buffered by the ISA-AA MDA(s) in the network-to-subscriber direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the network-to-subscriber direction.";
                                    }

                                    leaf packets {
                                        type yang:counter64;
                                        units "packets";
                                        description "Number of packets discarded by the ISA-AA MDA(s) due to policy in the network-to-subscriber direction.";
                                    }

                                } // container policy

                                container congestion {
                                    description "Enter the congestion context";

                                    leaf octets {
                                        type yang:counter64;
                                        units "bytes";
                                        description "Number of bytes discarded by the ISA-AA MDA(s) due to congestion in the network-to-subscriber direction.";
                                    }

                                    leaf packets {
                                        type yang:counter64;
                                        units "packets";
                                        description "Number of packets discarded by the ISA-AA MDA(s) due to congestion in the network-to-subscriber direction.";
                                    }

                                } // container congestion

                                container errors {
                                    description "Enter the errors context";

                                    leaf octets {
                                        type yang:counter64;
                                        units "bytes";
                                        description "Number of bytes discarded due to unrecoverable errors in the network-to-subscriber direction.";
                                    }

                                    leaf packets {
                                        type yang:counter64;
                                        units "packets";
                                        description "Number of packets discarded due to unrecoverable errors in the network-to-subscriber direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the network-to-subscriber direction.";
                                    }

                                    leaf packets {
                                        type yang:counter64;
                                        units "packets";
                                        description "Number of packets that the ISA-AA MDA has increased in size in the network-to-subscriber direction.";
                                    }

                                } // container packet-size-increased

                                container packet-size-decreased {
                                    description "Enter the packet-size-decreased context";

                                    leaf octets {
                                        type yang:counter64;
                                        units "bytes";
                                        description "Number of octets the ISA-AA MDA has removed from packets in the network-to-subscriber direction.";
                                    }

                                    leaf packets {
                                        type yang:counter64;
                                        units "packets";
                                        description "Number of packets that the ISA-AA MDA has decreased in size in the network-to-subscriber direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which passed untouched that did not have statistics or policy applied.
                                             These octets are counted as policy bypass errors in the network-to-subscriber direction.";
                                    }

                                    leaf packets {
                                        type yang:counter64;
                                        units "packets";
                                        description
                                            "Number of packets which passed untouched that did not have statistics or policy applied.
                                             These packets are counted as policy bypass errors in the network-to-subscriber direction.";
                                    }

                                } // container policy-bypass

                                container cut-through {
                                    description "Enter the cut-through context";

                                    leaf octets {
                                        type yang:counter64;
                                        units "bytes";
                                        description
                                            "Number of octets which passed untouched, but have policy applied in the network-to-subscriber direction.
                                             These octets are counted as cut-through errors.";
                                    }

                                    leaf packets {
                                        type yang:counter64;
                                        units "packets";
                                        description
                                            "Number of packets which passed untouched, but have policy applied in the network-to-subscriber direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the network-to-subscriber direction.";
                                    }

                                    leaf packets {
                                        type yang:counter64;
                                        units "packets";
                                        description "Number of packets that the ISA-AA MDA has created to redirect HTTP and HTTPS in the network-to-subscriber direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the network-to-subscriber direction.";
                                }

                                leaf packets {
                                    type yang:counter64;
                                    units "packets";
                                    description "Number of packets which exit the ISA-AA MDA(s) and are sent to the local IOM in the network-to-subscriber direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the network-to-subscriber direction.";
                                    }

                                    leaf packets {
                                        type yang:counter64;
                                        units "packets";
                                        description "Number of packets discarded by the IOMs after the ISA-AA MDA(s) due to ingress IOM congestion in the network-to-subscriber direction.";
                                    }

                                } // container congestion

                                container errors {
                                    description "Enter the errors context";

                                    leaf packets {
                                        type yang:counter64;
                                        units "packets";
                                        description
                                            "Number of packets discarded due to an error detected by the P-chip while attempting to return
                                             the packet to the normal forwarding path in the network-to-subscriber direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the network-to-subscriber direction.";
                                }

                                leaf packets {
                                    type yang:counter64;
                                    units "packets";
                                    description "Number of packets returned to the normal forwarding path that are sent to egress IOMs from the ISA-AA MDA(s) in the network-to-subscriber direction.";
                                }

                            } // container returned-traffic

                        } // container statistics

                    } // container net-to-sub

                    container qos {
                        description "Enter the qos context";

                        container ingress {
                            description "Enter the ingress context";

                            list direction {
                                key "direction queue-id";
                                description "Enter the direction list instance";

                                leaf direction {
                                    type types-aa:queue-traffic-direction;
                                    description "The traffic direction (net-to-sub or sub-to-net).";
                                }

                                leaf queue-id {
                                    type types-qos:ingress-queue-id;
                                    description "The ingress queue identifier.";
                                }

                                container statistics {
                                    description "Enter the statistics context";

                                    container in-profile-forwarded {
                                        description "Enter the in-profile-forwarded context";

                                        leaf octets {
                                            type yang:counter64;
                                            units "bytes";
                                            description "Number of in profile bytes diverted towards egress IOMs from the ISA-AA MDA within this group for the particular queue.";
                                        }

                                        leaf packets {
                                            type yang:counter64;
                                            units "packets";
                                            description "Number of in profile packets diverted towards egress IOMs from the ISA-AA MDA within this group for the particular queue.";
                                        }

                                    } // container in-profile-forwarded

                                    container in-profile-dropped {
                                        description "Enter the in-profile-dropped context";

                                        leaf octets {
                                            type yang:counter64;
                                            units "bytes";
                                            description "Number of in profile bytes discarded towards egress IOMs from the ISA-AA MDA within this group for the particular queue.";
                                        }

                                        leaf packets {
                                            type yang:counter64;
                                            units "packets";
                                            description "Number of in profile packets discarded towards egress IOMs from the ISA-AA MDA within this group for the particular queue.";
                                        }

                                    } // container in-profile-dropped

                                    container out-profile-forwarded {
                                        description "Enter the out-profile-forwarded context";

                                        leaf octets {
                                            type yang:counter64;
                                            units "bytes";
                                            description "Number of out of profile bytes diverted towards egress IOMs from the ISA-AA MDA within this group for the particular queue.";
                                        }

                                        leaf packets {
                                            type yang:counter64;
                                            units "packets";
                                            description "Number of out of profile packets diverted towards egress IOMs from the ISA-AA MDA within this group for the particular queue.";
                                        }

                                    } // container out-profile-forwarded

                                    container out-profile-dropped {
                                        description "Enter the out-profile-dropped context";

                                        leaf octets {
                                            type yang:counter64;
                                            units "bytes";
                                            description "Number of out of profile bytes discarded towards egress IOMs from the ISA-AA MDA within this group for the particular queue.";
                                        }

                                        leaf packets {
                                            type yang:counter64;
                                            units "packets";
                                            description "Number of out of profile packets discarded towards egress IOMs from the ISA-AA MDA within this group for the particular queue.";
                                        }

                                    } // container out-profile-dropped

                                } // container statistics

                            } // list direction

                        } // container ingress

                        container egress {
                            description "Enter the egress context";

                            list direction {
                                key "direction queue-id";
                                description "Enter the direction list instance";

                                leaf direction {
                                    type types-aa:queue-traffic-direction;
                                    description "The traffic direction (net-to-sub or sub-to-net).";
                                }

                                leaf queue-id {
                                    type types-qos:egress-queue-id;
                                    description "The ingress queue identifier.";
                                }

                                container statistics {
                                    description "Enter the statistics context";

                                    container in-profile-forwarded {
                                        description "Enter the in-profile-forwarded context";

                                        leaf octets {
                                            type yang:counter64;
                                            units "bytes";
                                            description "Number of in profile bytes diverted from ingress IOMs towards the ISA-AA MDA within this group for the particular queue.";
                                        }

                                        leaf packets {
                                            type yang:counter64;
                                            units "packets";
                                            description "Number of in profile packets diverted from ingress IOMs towards the ISA-AA MDA within this group for the particular queue.";
                                        }

                                    } // container in-profile-forwarded

                                    container in-profile-dropped {
                                        description "Enter the in-profile-dropped context";

                                        leaf octets {
                                            type yang:counter64;
                                            units "bytes";
                                            description "Number of in profile bytes discarded from ingress IOMs towards the ISA-AA MDA within this group for the particular queue.";
                                        }

                                        leaf packets {
                                            type yang:counter64;
                                            units "packets";
                                            description "Number of in profile packets discarded from ingress IOMs towards the ISA-AA MDA within this group for the particular queue.";
                                        }

                                    } // container in-profile-dropped

                                    container out-profile-forwarded {
                                        description "Enter the out-profile-forwarded context";

                                        leaf octets {
                                            type yang:counter64;
                                            units "bytes";
                                            description "Number of out of profile bytes diverted from ingress IOMs towards the ISA-AA MDA within this group for the particular queue.";
                                        }

                                        leaf packets {
                                            type yang:counter64;
                                            units "packets";
                                            description "Number of out of profile packets diverted from ingress IOMs towards the ISA-AA MDA within this group for the particular queue.";
                                        }

                                    } // container out-profile-forwarded

                                    container out-profile-dropped {
                                        description "Enter the out-profile-dropped context";

                                        leaf octets {
                                            type yang:counter64;
                                            units "bytes";
                                            description "Number of out of profile bytes discarded from ingress IOMs towards the ISA-AA MDA within this group for the particular queue.";
                                        }

                                        leaf packets {
                                            type yang:counter64;
                                            units "packets";
                                            description "Number of out of profile packets discarded from ingress IOMs towards the ISA-AA MDA within this group for the particular queue.";
                                        }

                                    } // container out-profile-dropped

                                } // container statistics

                            } // list direction

                        } // container egress

                    } // container qos

                } // list esa

                list isa {
                    key "mda-id";
                    description "Enter the isa list instance";

                    leaf mda-id {
                        type types-isa:slot-mda;
                        description "MDA/ISA ID";
                    }

                    leaf max-flow-resources {
                        type yang:gauge32;
                        units "flows";
                        description "The maximum number of flow resources on the ISA-AA MDA(s).";
                    }

                    container statistics {
                        description "Enter the statistics context";

                        leaf flows {
                            type yang:counter64;
                            units "flows";
                            description "The total number of flows created on the ISA-AA MDA(s).";
                        }

                        leaf aa-subscribers-created {
                            type yang:counter64;
                            description "The number of subscribers created.";
                        }

                        leaf aa-subscribers-deleted {
                            type yang:counter64;
                            description "The number of subscribers deleted.";
                        }

                        leaf aa-subscribers-modified {
                            type yang:counter64;
                            description "The number of subscribers modified.";
                        }

                        leaf aa-subscribers-quarantined {
                            type yang:counter64;
                            description "The number of subscribers quarantined.";
                        }

                        leaf seen-ip-requests-sent {
                            type yang:counter64;
                            description
                                "The number of requests sent from the ISA-AA MDA to initiate dynamic transit subscriber creation when traffic
                                 is detected on a parent SAP or Spoke SDP.";
                        }

                        leaf seen-ip-requests-dropped {
                            type yang:counter64;
                            description "The number of Seen IP requests dropped by the ISA-AA MDA due to congestion control mechanisms.";
                        }

                        container diverted-discards {
                            description "Enter the diverted-discards context";

                            container congestion {
                                description "Enter the congestion context";

                                leaf octets {
                                    type yang:counter64;
                                    units "bytes";
                                    description "Number of bytes discarded by the IOMs prior to the ISA-AA MDA(s) due to egress IOM congestion.";
                                }

                                leaf packets {
                                    type yang:counter64;
                                    units "packets";
                                    description "Number of packets discarded by the IOMs prior to the ISA-AA MDA(s) due to egress IOM congestion.";
                                }

                            } // container congestion

                            container errors {
                                description "Enter the errors context";

                                leaf packets {
                                    type yang:counter64;
                                    units "packets";
                                    description "Number of packets discarded by the egress P-chip due to errors in the packets.";
                                }

                            } // container errors

                        } // container diverted-discards

                        container returned-discards {
                            description "Enter the returned-discards context";

                            container congestion {
                                description "Enter the congestion context";

                                leaf octets {
                                    type yang:counter64;
                                    units "bytes";
                                    description "Number of bytes discarded by the IOMs after the ISA-AA MDA(s) due to ingress IOM congestion.";
                                }

                                leaf packets {
                                    type yang:counter64;
                                    units "packets";
                                    description "Number of packets discarded by the IOMs after the ISA-AA MDA(s) due to ingress IOM congestion.";
                                }

                            } // container congestion

                            container errors {
                                description "Enter the errors context";

                                leaf packets {
                                    type yang:counter64;
                                    units "packets";
                                    description "Number of packets discarded due to an error detected by the P-chip while attempting to return the packet to the normal forwarding path.";
                                }

                            } // container errors

                        } // container returned-discards

                        container congestion-discards {
                            description "Enter the congestion-discards context";

                            leaf octets {
                                type yang:counter64;
                                units "bytes";
                                description "Number of bytes discarded by the IOMs after the ISA-AA MDA(s) due IOM congestion.";
                            }

                            leaf packets {
                                type yang:counter64;
                                units "packets";
                                description "Number of packets discarded by the IOMs after the ISA-AA MDA(s) due to IOM congestion.";
                            }

                        } // container congestion-discards

                        container active-flows {
                            description "Enter the active-flows context";

                            leaf current {
                                type yang:gauge32;
                                units "flows";
                                description "The number of active flows currently being tracked by the ISA-AA MDA(s).";
                            }

                            leaf average {
                                type yang:gauge32;
                                units "flows";
                                description "The average number of active flows being tracked by the ISA-AA MDA(s) within the last 60 minutes.";
                            }

                            leaf peak {
                                type yang:gauge32;
                                units "flows";
                                description "The peak number of active flows being tracked by the ISA-AA MDA(s) since system startup.";
                            }

                        } // container active-flows

                        container aa-subscribers-downloaded {
                            description "Enter the aa-subscribers-downloaded context";

                            leaf current {
                                type yang:gauge32;
                                description
                                    "The number of subscribers defined in TIMETRA-SUBSCRIBER-MGMT-MIB::tmnxSubInfoAppProfile
                                     in the tmnxSubscriberInfoTable with tmnxBsxAppProfDivert set to 'true'.";
                            }

                            leaf average {
                                type yang:gauge32;
                                description
                                    "The average number of subscribers defined in TIMETRA-SUBSCRIBER-MGMT-MIB::tmnxSubInfoAppProfile
                                     in the tmnxSubscriberInfoTable with tmnxBsxAppProfDivert set to 'true' within the last 60 minutes.";
                            }

                            leaf peak {
                                type yang:gauge32;
                                description
                                    "The peak number of subscribers defined in TIMETRA-SUBSCRIBER-MGMT-MIB::tmnxSubInfoAppProfile
                                     in the tmnxSubscriberInfoTable with tmnxBsxAppProfDivert set to 'true' since system startup.";
                            }

                        } // container aa-subscribers-downloaded

                        container active-subscribers {
                            description "Enter the active-subscribers context";

                            leaf current {
                                type yang:gauge32;
                                description "The number of subscribers currently with flow records in the ISA-AA MDA(s).";
                            }

                            leaf average {
                                type yang:gauge32;
                                description "The average number of subscribers with flow records in the ISA-AA MDA(s) within the last 60 minutes.";
                            }

                            leaf peak {
                                type yang:gauge32;
                                description "The peak number of subscribers with flow records in the ISA-AA MDA(s) since system startup.";
                            }

                        } // container active-subscribers

                        container diverted-traffic {
                            description "Enter the diverted-traffic context";

                            leaf octets {
                                type yang:counter64;
                                units "bytes";
                                description "Number of bytes diverted from ingress IOMs towards the ISA-AA MDA(s).";
                            }

                            leaf packets {
                                type yang:counter64;
                                units "packets";
                                description "Number of packets diverted from ingress IOMs towards the ISA-AA MDA(s).";
                            }

                        } // container diverted-traffic

                        container entered-aa {
                            description "Enter the entered-aa context";

                            leaf octets {
                                type yang:counter64;
                                units "bytes";
                                description "Number of bytes sent from an IOM which enter the ISA-AA MDA(s).";
                            }

                            leaf packets {
                                type yang:counter64;
                                units "packets";
                                description "Number of packets sent from an IOM which enter the ISA-AA MDA(s).";
                            }

                        } // container entered-aa

                        container inspected {
                            description "Enter the inspected context";

                            leaf octets {
                                type yang:counter64;
                                units "bytes";
                                description "Number of bytes sent for protocol determination in the ISA-AA MDA(s).";
                            }

                            leaf packets {
                                type yang:counter64;
                                units "packets";
                                description "Number of packets sent for protocol determination in the ISA-AA MDA(s).";
                            }

                        } // container inspected

                        container exited-aa {
                            description "Enter the exited-aa context";

                            leaf octets {
                                type yang:counter64;
                                units "bytes";
                                description "Number of bytes which exit the ISA-AA MDA(s) and are sent to the local IOM.";
                            }

                            leaf packets {
                                type yang:counter64;
                                units "packets";
                                description "Number of packets which exit the ISA-AA MDA(s) and are sent to the local IOM.";
                            }

                        } // container exited-aa

                        container buffered-in-aa {
                            description "Enter the buffered-in-aa context";

                            leaf octets {
                                type yang:counter64;
                                units "bytes";
                                description "Number of bytes buffered by the ISA-AA MDA(s).";
                            }

                            leaf packets {
                                type yang:counter64;
                                units "packets";
                                description "Number of packets buffered by the ISA-AA MDA(s).";
                            }

                        } // container buffered-in-aa

                        container discarded-in-aa {
                            description "Enter the discarded-in-aa context";

                            container policy {
                                description "Enter the policy context";

                                leaf octets {
                                    type yang:counter64;
                                    units "bytes";
                                    description "Number of bytes discarded by the ISA-AA MDA(s) due to policy.";
                                }

                                leaf packets {
                                    type yang:counter64;
                                    units "packets";
                                    description "Number of packets discarded by the ISA-AA MDA(s) due to policy.";
                                }

                            } // container policy

                            container congestion {
                                description "Enter the congestion context";

                                leaf octets {
                                    type yang:counter64;
                                    units "bytes";
                                    description "Number of bytes discarded by the ISA-AA MDA(s) due to congestion.";
                                }

                                leaf packets {
                                    type yang:counter64;
                                    units "packets";
                                    description "Number of packets discarded by the ISA-AA MDA(s) due to congestion.";
                                }

                            } // container congestion

                            container errors {
                                description "Enter the errors context";

                                leaf octets {
                                    type yang:counter64;
                                    units "bytes";
                                    description "Number of bytes discarded due to unrecoverable errors.";
                                }

                                leaf packets {
                                    type yang:counter64;
                                    units "packets";
                                    description "Number of packets discarded due to unrecoverable errors.";
                                }

                            } // container errors

                            container tcp-optimization {
                                description "Enter the tcp-optimization context";

                            } // container tcp-optimization

                        } // container discarded-in-aa

                        container modified-in-aa {
                            description "Enter the modified-in-aa context";

                            container packet-size-increased {
                                description "Enter the packet-size-increased context";

                                leaf octets {
                                    type yang:counter64;
                                    units "bytes";
                                    description "Number of additional octets the ISA-AA MDA injected into the packets.";
                                }

                                leaf packets {
                                    type yang:counter64;
                                    units "packets";
                                    description "Number of packets that the ISA-AA MDA has increased in size.";
                                }

                            } // container packet-size-increased

                            container packet-size-decreased {
                                description "Enter the packet-size-decreased context";

                                leaf octets {
                                    type yang:counter64;
                                    units "bytes";
                                    description "Number of octets the ISA-AA MDA has removed from packets.";
                                }

                                leaf packets {
                                    type yang:counter64;
                                    units "packets";
                                    description "Number of packets that the ISA-AA MDA has decreased in size.";
                                }

                            } // container packet-size-decreased

                        } // container modified-in-aa

                        container errors {
                            description "Enter the errors context";

                            container policy-bypass {
                                description "Enter the policy-bypass context";

                                leaf octets {
                                    type yang:counter64;
                                    units "bytes";
                                    description
                                        "Number of octets which pass untouched that did not have statistics or policy applied.
                                         These bytes are counted as policy bypass errors.";
                                }

                                leaf packets {
                                    type yang:counter64;
                                    units "packets";
                                    description
                                        "Number of packets which passed untouched that did not have statistics or policy applied.
                                         These packets are counted as policy bypass errors.";
                                }

                            } // container policy-bypass

                            container cut-through {
                                description "Enter the cut-through context";

                                leaf octets {
                                    type yang:counter64;
                                    units "bytes";
                                    description
                                        "Number of octets which passed untouched, but have policy applied.
                                         These octets are counted as cut-through errors.";
                                }

                                leaf packets {
                                    type yang:counter64;
                                    units "packets";
                                    description
                                        "Number of packets which passed untouched, but have policy applied.
                                         These packets are counted as cut-through errors.";
                                }

                                container flow-resource {
                                    description "Enter the flow-resource context";

                                    leaf octets {
                                        type yang:counter64;
                                        units "bytes";
                                        description "Number of octets that the ISA-AA MDA(s) have cut-through due to flow resource exhaustion.";
                                    }

                                    leaf packets {
                                        type yang:counter64;
                                        units "packets";
                                        description "Number of packets that the ISA-AA MDA(s) have cut-through due to flow resource exhaustion.";
                                    }

                                } // container flow-resource

                                container overload {
                                    description "Enter the overload context";

                                    leaf octets {
                                        type yang:counter64;
                                        units "bytes";
                                        description "Number of octets that the ISA-AA MDA has cut-through due to the overload cut-through configuration as indicated by the object tmnxBsxIsaAaGrpOverloadCutThru.";
                                    }

                                    leaf packets {
                                        type yang:counter64;
                                        units "packets";
                                        description "Number of octets that the ISA-AA MDA has cut-through due to the overload cut-through configuration as indicated by the object tmnxBsxIsaAaGrpOverloadCutThru.";
                                    }

                                } // container overload

                            } // container cut-through

                        } // container errors

                        container generated-in-aa {
                            description "Enter the generated-in-aa context";

                            container http-redirect {
                                description "Enter the http-redirect context";

                                leaf octets {
                                    type yang:counter64;
                                    units "bytes";
                                    description "Number of octets that the ISA-AA MDA has created to redirect HTTP and HTTPS.";
                                }

                                leaf packets {
                                    type yang:counter64;
                                    units "packets";
                                    description "Number of packets that the ISA-AA MDA has created to redirect HTTP and HTTPS.";
                                }

                            } // container http-redirect

                        } // container generated-in-aa

                        container returned-traffic {
                            description "Enter the returned-traffic context";

                            leaf octets {
                                type yang:counter64;
                                units "bytes";
                                description "Number of bytes returned to the normal forwarding path that are sent to egress IOMs from the ISA-AA MDA(s).";
                            }

                            leaf packets {
                                type yang:counter64;
                                units "packets";
                                description "Number of packets returned to the normal forwarding path that are sent to egress IOMs from the ISA-AA MDA(s).";
                            }

                        } // container returned-traffic

                        container flow-resources {
                            description "Enter the flow-resources context";

                            leaf current {
                                type yang:gauge32;
                                description "The number of flow resources currently in-use on the ISA-AA MDA(s).";
                            }

                            leaf average {
                                type yang:gauge32;
                                units "flows";
                                description "The average number of flow resources in use on the ISA-AA MDA(s) within the last 60 minutes.";
                            }

                            leaf peak {
                                type yang:gauge32;
                                units "flows";
                                description "The peak number of flow resources in use on the ISA-AA MDA(s) since system startup.";
                            }

                            leaf current-percent {
                                type uint32 {
                                    range "0..10000";
                                }
                                units "centipercent";
                                description "The current percentage of total flow resources in-use on the ISA-AA MDA.";
                            }

                            leaf average-percent {
                                type uint32 {
                                    range "0..10000";
                                }
                                units "centipercent";
                                description "The average percentage of total flow resources in-use on the ISA-AA MDA.";
                            }

                            leaf peak-percent {
                                type uint32 {
                                    range "0..10000";
                                }
                                units "centipercent";
                                description "The peak percentage of total flow resources in-use on the ISA-AA MDA.";
                            }

                        } // container flow-resources

                        container flow-setup-rate {
                            description "Enter the flow-setup-rate context";

                            leaf current {
                                type yang:gauge32;
                                units "flows per second";
                                description "The number of flow setups per second over the most recent 10 second period.";
                            }

                            leaf average {
                                type yang:gauge32;
                                units "flows per second";
                                description "The average number of flow setups per second being tracked by the ISA-AA MDA(s) within the last 60 minutes.";
                            }

                            leaf peak {
                                type yang:gauge32;
                                units "flows per second";
                                description "The peak number of flow setups per second being tracked by the ISA-AA MDA(s) since system startup.";
                            }

                        } // container flow-setup-rate

                        container traffic-rate {
                            description "Enter the traffic-rate context";

                            leaf current {
                                type yang:gauge32;
                                units "megabps";
                                description "The traffic rate in megabits(s) per second (mbps) incoming to the ISA-AA MDA(s).";
                            }

                            leaf average {
                                type yang:gauge32;
                                units "megabps";
                                description "The average traffic rate in megabits(s) per second (mbps) incoming to the ISA-AA MDA(s) within the last 60 minutes.";
                            }

                            leaf peak {
                                type yang:gauge32;
                                units "megabps";
                                description "The peak traffic rate in megabits(s) per second (mbps) incoming to the ISA-AA MDA(s) since system startup.";
                            }

                        } // container traffic-rate

                        container packet-rate {
                            description "Enter the packet-rate context";

                            leaf current {
                                type yang:gauge32;
                                units "packets per second";
                                description "The current number of packets per second incoming to the ISA-AA MDA(s).";
                            }

                            leaf average {
                                type yang:gauge32;
                                units "packets per second";
                                description "The average number of packets per second incoming to the ISA-AA MDA(s) within the last 60 minutes.";
                            }

                            leaf peak {
                                type yang:gauge32;
                                units "packets per second";
                                description "The peak number of packets per second incoming to the ISA-AA MDA(s) since system startup.";
                            }

                        } // container packet-rate

                        container datapath-cpu-usage {
                            description "Enter the datapath-cpu-usage context";

                            leaf current {
                                type uint32 {
                                    range "0..10000";
                                }
                                units "centipercent";
                                description "The percent utilization of the datapath CPU on the ISA-AA MDA(s).";
                            }

                            leaf average {
                                type uint32 {
                                    range "0..10000";
                                }
                                units "centipercent";
                                description "The average percent utilization of the datapath CPU on the ISA-AA MDA(s) within the last 60 minutes.";
                            }

                            leaf peak {
                                type uint32 {
                                    range "0..10000";
                                }
                                units "centipercent";
                                description "The peak percent utilization of the datapath CPU on the ISA-AA MDA(s) since system startup.";
                            }

                        } // container datapath-cpu-usage

                        container management-cpu-usage {
                            description "Enter the management-cpu-usage context";

                            leaf current {
                                type uint32 {
                                    range "0..10000";
                                }
                                units "centipercent";
                                description "The percent utilization of the management CPU on the ISA-AA MDA(s).";
                            }

                            leaf average {
                                type uint32 {
                                    range "0..10000";
                                }
                                units "centipercent";
                                description "The average percent utilization of the management CPU on the ISA-AA MDA(s) within the last 60 minutes.";
                            }

                            leaf peak {
                                type uint32 {
                                    range "0..10000";
                                }
                                units "centipercent";
                                description "The peak percent utilization of the management CPU on the ISA-AA MDA(s) since system startup.";
                            }

                        } // container management-cpu-usage

                    } // container statistics

                    container tca {
                        description "Enter the tca context";

                        container flow-resources {
                            description "Enter the flow-resources context";

                            leaf state {
                                type types-aa:tca-state;
                                description "The state of the flow resource TCA (tmnxBsxIsaAaGrpFlowFull).";
                            }

                            container statistics {
                                description "Enter the statistics context";

                                leaf count {
                                    type yang:counter64;
                                    description "The number of times the flow resource TCA (tmnxBsxIsaAaGrpFlowFull) was raised since system startup.";
                                }

                                leaf duration {
                                    type yang:counter64;
                                    units "seconds";
                                    description "The amount of time the flow resource TCA (tmnxBsxIsaAaGrpFlowFull) was in the raised state since system startup.";
                                }

                            } // container statistics

                        } // container flow-resources

                        container flow-setup-rate {
                            description "Enter the flow-setup-rate context";

                            leaf state {
                                type types-aa:tca-state;
                                description "The state of the flow setup rate TCA (tmnxBsxIsaAaGrpFlowSetup).";
                            }

                            container statistics {
                                description "Enter the statistics context";

                                leaf count {
                                    type yang:counter64;
                                    description "The number of times the flow setup rate TCA (tmnxBsxIsaAaGrpFlowSetup) was raised since system startup.";
                                }

                                leaf duration {
                                    type yang:counter64;
                                    units "seconds";
                                    description "The amount of time the flow setup rate TCA (tmnxBsxIsaAaGrpFlowSetup) was in the raised state since system startup.";
                                }

                            } // container statistics

                        } // container flow-setup-rate

                        container traffic-rate {
                            description "Enter the traffic-rate context";

                            leaf state {
                                type types-aa:tca-state;
                                description "The state of the bit rate TCA (tmnxBsxIsaAaGrpBitRate).";
                            }

                            container statistics {
                                description "Enter the statistics context";

                                leaf count {
                                    type yang:counter64;
                                    description "The number of times the bit rate TCA (tmnxBsxIsaAaGrpBitRate) was raised since system startup.";
                                }

                                leaf duration {
                                    type yang:counter64;
                                    units "seconds";
                                    description "The amount time the bit rate TCA (tmnxBsxIsaAaGrpBitRate) was in the raised state since system startup.";
                                }

                            } // container statistics

                        } // container traffic-rate

                        container packet-rate {
                            description "Enter the packet-rate context";

                            leaf state {
                                type types-aa:tca-state;
                                description "The state of the packet rate TCA (tmnxBsxIsaAaGrpPacketRate).";
                            }

                            container statistics {
                                description "Enter the statistics context";

                                leaf count {
                                    type yang:counter64;
                                    description "The number of times the packet rate TCA (tmnxBsxIsaAaGrpPacketRate) was raised since system startup.";
                                }

                                leaf duration {
                                    type yang:counter64;
                                    units "seconds";
                                    description "The amount of time the packet rate TCA (tmnxBsxIsaAaGrpPacketRate) was in the raised state since system startup.";
                                }

                            } // container statistics

                        } // container packet-rate

                        container datapath-cpu-usage {
                            description "Enter the datapath-cpu-usage context";

                            leaf state {
                                type types-aa:tca-state;
                                description "The state of the datapath CPU TCA (tmnxBsxDatapathCpuUsage).";
                            }

                            container statistics {
                                description "Enter the statistics context";

                                leaf count {
                                    type yang:counter64;
                                    description "The number of times the datapath CPU TCA (tmnxBsxDatapathCpuUsage) was raised since system startup.";
                                }

                                leaf duration {
                                    type yang:counter64;
                                    units "seconds";
                                    description "The amount of time the datapath CPU TCA (tmnxBsxDatapathCpuUsage) was in the raised state since system startup.";
                                }

                            } // container statistics

                        } // container datapath-cpu-usage

                        container isa-overload {
                            description "Enter the isa-overload context";

                            leaf state {
                                type types-aa:tca-state;
                                description "The state of the overload cut-through TCA (tmnxBsxIsaAaGrpOvrldCutthru).";
                            }

                            container statistics {
                                description "Enter the statistics context";

                                leaf count {
                                    type yang:counter64;
                                    description "The number of times the overload cut-through TCA (tmnxBsxIsaAaGrpOvrldCutthru) was raised since system startup.";
                                }

                                leaf duration {
                                    type yang:counter64;
                                    units "seconds";
                                    description "The amount of time the overload cut-through TCA (tmnxBsxIsaAaGrpOvrldCutthru) was in the raised state since system startup.";
                                }

                            } // container statistics

                        } // container isa-overload

                    } // container tca

                    container sub-to-net {
                        description "Enter the sub-to-net context";

                        container overload-cut-through-tca {
                            description "Enter the overload-cut-through-tca context";

                            leaf state {
                                type types-aa:tca-state;
                                description "The state of the subscriber to network weighted average shared buffer TCA (tmnxBsxIsaAaGrpFmSbWaSBufOvld).";
                            }

                            leaf current-wa-buffer-depth {
                                type uint32 {
                                    range "0..10000";
                                }
                                units "centipercent";
                                description "The percent utilization of the subscriber to network weighted average shared buffer on the ISA-AA MDA(s).";
                            }

                            container statistics {
                                description "Enter the statistics context";

                                leaf count {
                                    type yang:counter64;
                                    description "The number of times the subscriber to network weighted average shared buffer TCA (tmnxBsxIsaAaGrpFmSbWaSBufOvld) was raised since system startup.";
                                }

                                leaf duration {
                                    type yang:counter64;
                                    units "seconds";
                                    description "The amount of time the subscriber to network weighted average shared buffer TCA (tmnxBsxIsaAaGrpFmSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the subscriber-to-network direction.";
                                }

                                leaf packets {
                                    type yang:counter64;
                                    units "packets";
                                    description "Number of packets diverted from ingress IOMs towards the ISA-AA MDA(s) in the subscriber-to-network direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the subscriber-to-network direction.";
                                    }

                                    leaf packets {
                                        type yang:counter64;
                                        units "packets";
                                        description "Number of packets discarded by the IOMs prior to the ISA-AA MDA(s) due to egress IOM congestion in the subscriber-to-network direction.";
                                    }

                                } // container congestion

                                container errors {
                                    description "Enter the errors context";

                                    leaf packets {
                                        type yang:counter64;
                                        units "packets";
                                        description "Number of packets discarded by the egress P-chip due to errors in the packets in the subscriber-to-network direction.";
                                    }

                                } // container errors

                            } // container diverted-discards

                            container entered-aa {
                                description "Enter the entered-aa context";

                                leaf octets {
                                    type yang:counter64;
                                    units "bytes";
                                    description "Number of bytes sent from an IOM which enter the ISA-AA MDA(s) in the subscriber-to-network direction.";
                                }

                                leaf packets {
                                    type yang:counter64;
                                    units "packets";
                                    description "Number of packets sent from an IOM which enter the ISA-AA MDA(s) in the subscriber-to-network direction.";
                                }

                            } // container entered-aa

                            container buffered-in-aa {
                                description "Enter the buffered-in-aa context";

                                leaf octets {
                                    type yang:counter64;
                                    units "bytes";
                                    description "Number of bytes buffered by the ISA-AA MDA(s) in the subscriber-to-network direction.";
                                }

                                leaf packets {
                                    type yang:counter64;
                                    units "packets";
                                    description "Number of packets buffered by the ISA-AA MDA(s) in the subscriber-to-network direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the subscriber-to-network direction.";
                                    }

                                    leaf packets {
                                        type yang:counter64;
                                        units "packets";
                                        description "Number of packets discarded by the ISA-AA MDA(s) due to policy in the subscriber-to-network direction.";
                                    }

                                } // container policy

                                container congestion {
                                    description "Enter the congestion context";

                                    leaf octets {
                                        type yang:counter64;
                                        units "bytes";
                                        description "Number of bytes discarded by the ISA-AA MDA(s) due to congestion in the subscriber-to-network direction.";
                                    }

                                    leaf packets {
                                        type yang:counter64;
                                        units "packets";
                                        description "Number of packets discarded by the ISA-AA MDA(s) due to congestion in the subscriber-to-network direction.";
                                    }

                                } // container congestion

                                container errors {
                                    description "Enter the errors context";

                                    leaf octets {
                                        type yang:counter64;
                                        units "bytes";
                                        description "Number of bytes discarded due to unrecoverable errors in the subscriber-to-network direction.";
                                    }

                                    leaf packets {
                                        type yang:counter64;
                                        units "packets";
                                        description "Number of packets discarded due to unrecoverable errors in the subscriber-to-network direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the subscriber-to-network direction.";
                                    }

                                    leaf packets {
                                        type yang:counter64;
                                        units "packets";
                                        description "Number of packets that the ISA-AA MDA has increased in size in the subscriber-to-network direction.";
                                    }

                                } // container packet-size-increased

                                container packet-size-decreased {
                                    description "Enter the packet-size-decreased context";

                                    leaf octets {
                                        type yang:counter64;
                                        units "bytes";
                                        description "Number of octets the ISA-AA MDA has removed from packets in the subscriber-to-network direction.";
                                    }

                                    leaf packets {
                                        type yang:counter64;
                                        units "packets";
                                        description "Number of packets that the ISA-AA MDA has decreased in size in the subscriber-to-network direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which pass untouched that did not have statistics or policy applied.
                                             These bytes are counted as policy bypass errors in the subscriber-to-network direction.";
                                    }

                                    leaf packets {
                                        type yang:counter64;
                                        units "packets";
                                        description
                                            "Number of packets which passed untouched that did not have statistics or policy applied.
                                             These packets are counted as policy bypass errors in the subscriber-to-network direction.";
                                    }

                                } // container policy-bypass

                                container cut-through {
                                    description "Enter the cut-through context";

                                    leaf octets {
                                        type yang:counter64;
                                        units "bytes";
                                        description
                                            "Number of octets which passed untouched, but have policy applied in the subscriber-to-network direction.
                                             These octets are counted as cut-through errors.";
                                    }

                                    leaf packets {
                                        type yang:counter64;
                                        units "packets";
                                        description
                                            "Number of packets which passed untouched, but have policy applied in the subscriber-to-network direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the subscriber-to-network direction.";
                                    }

                                    leaf packets {
                                        type yang:counter64;
                                        units "packets";
                                        description "Number of packets that the ISA-AA MDA has created to redirect HTTP and HTTPS in the subscriber-to-network direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the subscriber-to-network direction.";
                                }

                                leaf packets {
                                    type yang:counter64;
                                    units "packets";
                                    description "Number of packets which exit the ISA-AA MDA(s) and are sent to the local IOM in the subscriber-to-network direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the subscriber-to-network direction.";
                                    }

                                    leaf packets {
                                        type yang:counter64;
                                        units "packets";
                                        description "Number of packets discarded by the IOMs after the ISA-AA MDA(s) due to ingress IOM congestion in the subscriber-to-network direction.";
                                    }

                                } // container congestion

                                container errors {
                                    description "Enter the errors context";

                                    leaf packets {
                                        type yang:counter64;
                                        units "packets";
                                        description
                                            "Number of packets discarded due to an error detected by the P-chip while attempting to return
                                             the packet to the normal forwarding path in the subscriber-to-network direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the subscriber-to-network direction.";
                                }

                                leaf packets {
                                    type yang:counter64;
                                    units "packets";
                                    description "Number of packets returned to the normal forwarding path that are sent to egress IOMs from the ISA-AA MDA(s) in the subscriber-to-network direction.";
                                }

                            } // container returned-traffic

                        } // container statistics

                    } // container sub-to-net

                    container net-to-sub {
                        description "Enter the net-to-sub context";

                        container overload-cut-through-tca {
                            description "Enter the overload-cut-through-tca context";

                            leaf current-wa-buffer-depth {
                                type uint32 {
                                    range "0..10000";
                                }
                                units "centipercent";
                                description "The percent utilization of the network to subscriber weighted average shared buffer on the ISA-AA MDA(s).";
                            }

                            leaf state {
                                type types-aa:tca-state;
                                description "The state of the network to subscriber weighted average shared buffer TCA (tmnxBsxIsaAaGrpToSbWaSBufOvld).";
                            }

                            container statistics {
                                description "Enter the statistics context";

                                leaf count {
                                    type yang:counter64;
                                    description "The number of times the network to subscriber weighted average shared buffer TCA (tmnxBsxIsaAaGrpToSbWaSBufOvld) was raised since system startup.";
                                }

                                leaf duration {
                                    type yang:counter64;
                                    units "seconds";
                                    description "The amount of time the network to subscriber weighted average shared buffer TCA (tmnxBsxIsaAaGrpToSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the network-to-subscriber direction.";
                                }

                                leaf packets {
                                    type yang:counter64;
                                    units "packets";
                                    description "Number of packets diverted from ingress IOMs towards the ISA-AA MDA(s) in the network-to-subscriber direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the network-to-subscriber direction.";
                                    }

                                    leaf packets {
                                        type yang:counter64;
                                        units "packets";
                                        description "Number of packets discarded by the IOMs prior to the ISA-AA MDA(s) due to egress IOM congestion in the network-to-subscriber direction.";
                                    }

                                } // container congestion

                                container errors {
                                    description "Enter the errors context";

                                    leaf packets {
                                        type yang:counter64;
                                        units "packets";
                                        description "Number of packets discarded by the egress P-chip due to errors in the packets in the network-to-subscriber direction";
                                    }

                                } // container errors

                            } // container diverted-discards

                            container entered-aa {
                                description "Enter the entered-aa context";

                                leaf octets {
                                    type yang:counter64;
                                    units "bytes";
                                    description "Number of bytes sent from an IOM which enter the ISA-AA MDA(s) in the network-to-subscriber direction.";
                                }

                                leaf packets {
                                    type yang:counter64;
                                    units "packets";
                                    description "Number of packets sent from an IOM which enter the ISA-AA MDA(s) in the network-to-subscriber direction.";
                                }

                            } // container entered-aa

                            container buffered-in-aa {
                                description "Enter the buffered-in-aa context";

                                leaf octets {
                                    type yang:counter64;
                                    units "bytes";
                                    description "Number of bytes buffered by the ISA-AA MDA(s) in the network-to-subscriber direction.";
                                }

                                leaf packets {
                                    type yang:counter64;
                                    units "packets";
                                    description "Number of packets buffered by the ISA-AA MDA(s) in the network-to-subscriber direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the network-to-subscriber direction.";
                                    }

                                    leaf packets {
                                        type yang:counter64;
                                        units "packets";
                                        description "Number of packets discarded by the ISA-AA MDA(s) due to policy in the network-to-subscriber direction.";
                                    }

                                } // container policy

                                container congestion {
                                    description "Enter the congestion context";

                                    leaf octets {
                                        type yang:counter64;
                                        units "bytes";
                                        description "Number of bytes discarded by the ISA-AA MDA(s) due to congestion in the network-to-subscriber direction.";
                                    }

                                    leaf packets {
                                        type yang:counter64;
                                        units "packets";
                                        description "Number of packets discarded by the ISA-AA MDA(s) due to congestion in the network-to-subscriber direction.";
                                    }

                                } // container congestion

                                container errors {
                                    description "Enter the errors context";

                                    leaf octets {
                                        type yang:counter64;
                                        units "bytes";
                                        description "Number of bytes discarded due to unrecoverable errors in the network-to-subscriber direction.";
                                    }

                                    leaf packets {
                                        type yang:counter64;
                                        units "packets";
                                        description "Number of packets discarded due to unrecoverable errors in the network-to-subscriber direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the network-to-subscriber direction.";
                                    }

                                    leaf packets {
                                        type yang:counter64;
                                        units "packets";
                                        description "Number of packets that the ISA-AA MDA has increased in size in the network-to-subscriber direction.";
                                    }

                                } // container packet-size-increased

                                container packet-size-decreased {
                                    description "Enter the packet-size-decreased context";

                                    leaf octets {
                                        type yang:counter64;
                                        units "bytes";
                                        description "Number of octets the ISA-AA MDA has removed from packets in the network-to-subscriber direction.";
                                    }

                                    leaf packets {
                                        type yang:counter64;
                                        units "packets";
                                        description "Number of packets that the ISA-AA MDA has decreased in size in the network-to-subscriber direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which passed untouched that did not have statistics or policy applied.
                                             These octets are counted as policy bypass errors in the network-to-subscriber direction.";
                                    }

                                    leaf packets {
                                        type yang:counter64;
                                        units "packets";
                                        description
                                            "Number of packets which passed untouched that did not have statistics or policy applied.
                                             These packets are counted as policy bypass errors in the network-to-subscriber direction.";
                                    }

                                } // container policy-bypass

                                container cut-through {
                                    description "Enter the cut-through context";

                                    leaf octets {
                                        type yang:counter64;
                                        units "bytes";
                                        description
                                            "Number of octets which passed untouched, but have policy applied in the network-to-subscriber direction.
                                             These octets are counted as cut-through errors.";
                                    }

                                    leaf packets {
                                        type yang:counter64;
                                        units "packets";
                                        description
                                            "Number of packets which passed untouched, but have policy applied in the network-to-subscriber direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the network-to-subscriber direction.";
                                    }

                                    leaf packets {
                                        type yang:counter64;
                                        units "packets";
                                        description "Number of packets that the ISA-AA MDA has created to redirect HTTP and HTTPS in the network-to-subscriber direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the network-to-subscriber direction.";
                                }

                                leaf packets {
                                    type yang:counter64;
                                    units "packets";
                                    description "Number of packets which exit the ISA-AA MDA(s) and are sent to the local IOM in the network-to-subscriber direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the network-to-subscriber direction.";
                                    }

                                    leaf packets {
                                        type yang:counter64;
                                        units "packets";
                                        description "Number of packets discarded by the IOMs after the ISA-AA MDA(s) due to ingress IOM congestion in the network-to-subscriber direction.";
                                    }

                                } // container congestion

                                container errors {
                                    description "Enter the errors context";

                                    leaf packets {
                                        type yang:counter64;
                                        units "packets";
                                        description
                                            "Number of packets discarded due to an error detected by the P-chip while attempting to return
                                             the packet to the normal forwarding path in the network-to-subscriber direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the network-to-subscriber direction.";
                                }

                                leaf packets {
                                    type yang:counter64;
                                    units "packets";
                                    description "Number of packets returned to the normal forwarding path that are sent to egress IOMs from the ISA-AA MDA(s) in the network-to-subscriber direction.";
                                }

                            } // container returned-traffic

                        } // container statistics

                    } // container net-to-sub

                    container qos {
                        description "Enter the qos context";

                        container ingress {
                            description "Enter the ingress context";

                            list direction {
                                key "direction queue-id";
                                description "Enter the direction list instance";

                                leaf direction {
                                    type types-aa:queue-traffic-direction;
                                    description "The traffic direction (net-to-sub or sub-to-net).";
                                }

                                leaf queue-id {
                                    type types-qos:ingress-queue-id;
                                    description "The ingress queue identifier.";
                                }

                                container statistics {
                                    description "Enter the statistics context";

                                    container in-profile-forwarded {
                                        description "Enter the in-profile-forwarded context";

                                        leaf octets {
                                            type yang:counter64;
                                            units "bytes";
                                            description "Number of in profile bytes diverted towards egress IOMs from the ISA-AA MDA within this group for the particular queue.";
                                        }

                                        leaf packets {
                                            type yang:counter64;
                                            units "packets";
                                            description "Number of in profile packets diverted towards egress IOMs from the ISA-AA MDA within this group for the particular queue.";
                                        }

                                    } // container in-profile-forwarded

                                    container in-profile-dropped {
                                        description "Enter the in-profile-dropped context";

                                        leaf octets {
                                            type yang:counter64;
                                            units "bytes";
                                            description "Number of in profile bytes discarded towards egress IOMs from the ISA-AA MDA within this group for the particular queue.";
                                        }

                                        leaf packets {
                                            type yang:counter64;
                                            units "packets";
                                            description "Number of in profile packets discarded towards egress IOMs from the ISA-AA MDA within this group for the particular queue.";
                                        }

                                    } // container in-profile-dropped

                                    container out-profile-forwarded {
                                        description "Enter the out-profile-forwarded context";

                                        leaf octets {
                                            type yang:counter64;
                                            units "bytes";
                                            description "Number of out of profile bytes diverted towards egress IOMs from the ISA-AA MDA within this group for the particular queue.";
                                        }

                                        leaf packets {
                                            type yang:counter64;
                                            units "packets";
                                            description "Number of out of profile packets diverted towards egress IOMs from the ISA-AA MDA within this group for the particular queue.";
                                        }

                                    } // container out-profile-forwarded

                                    container out-profile-dropped {
                                        description "Enter the out-profile-dropped context";

                                        leaf octets {
                                            type yang:counter64;
                                            units "bytes";
                                            description "Number of out of profile bytes discarded towards egress IOMs from the ISA-AA MDA within this group for the particular queue.";
                                        }

                                        leaf packets {
                                            type yang:counter64;
                                            units "packets";
                                            description "Number of out of profile packets discarded towards egress IOMs from the ISA-AA MDA within this group for the particular queue.";
                                        }

                                    } // container out-profile-dropped

                                } // container statistics

                            } // list direction

                        } // container ingress

                        container egress {
                            description "Enter the egress context";

                            list direction {
                                key "direction queue-id";
                                description "Enter the direction list instance";

                                leaf direction {
                                    type types-aa:queue-traffic-direction;
                                    description "The traffic direction (net-to-sub or sub-to-net).";
                                }

                                leaf queue-id {
                                    type types-qos:egress-queue-id;
                                    description "The ingress queue identifier.";
                                }

                                container statistics {
                                    description "Enter the statistics context";

                                    container in-profile-forwarded {
                                        description "Enter the in-profile-forwarded context";

                                        leaf octets {
                                            type yang:counter64;
                                            units "bytes";
                                            description "Number of in profile bytes diverted from ingress IOMs towards the ISA-AA MDA within this group for the particular queue.";
                                        }

                                        leaf packets {
                                            type yang:counter64;
                                            units "packets";
                                            description "Number of in profile packets diverted from ingress IOMs towards the ISA-AA MDA within this group for the particular queue.";
                                        }

                                    } // container in-profile-forwarded

                                    container in-profile-dropped {
                                        description "Enter the in-profile-dropped context";

                                        leaf octets {
                                            type yang:counter64;
                                            units "bytes";
                                            description "Number of in profile bytes discarded from ingress IOMs towards the ISA-AA MDA within this group for the particular queue.";
                                        }

                                        leaf packets {
                                            type yang:counter64;
                                            units "packets";
                                            description "Number of in profile packets discarded from ingress IOMs towards the ISA-AA MDA within this group for the particular queue.";
                                        }

                                    } // container in-profile-dropped

                                    container out-profile-forwarded {
                                        description "Enter the out-profile-forwarded context";

                                        leaf octets {
                                            type yang:counter64;
                                            units "bytes";
                                            description "Number of out of profile bytes diverted from ingress IOMs towards the ISA-AA MDA within this group for the particular queue.";
                                        }

                                        leaf packets {
                                            type yang:counter64;
                                            units "packets";
                                            description "Number of out of profile packets diverted from ingress IOMs towards the ISA-AA MDA within this group for the particular queue.";
                                        }

                                    } // container out-profile-forwarded

                                    container out-profile-dropped {
                                        description "Enter the out-profile-dropped context";

                                        leaf octets {
                                            type yang:counter64;
                                            units "bytes";
                                            description "Number of out of profile bytes discarded from ingress IOMs towards the ISA-AA MDA within this group for the particular queue.";
                                        }

                                        leaf packets {
                                            type yang:counter64;
                                            units "packets";
                                            description "Number of out of profile packets discarded from ingress IOMs towards the ISA-AA MDA within this group for the particular queue.";
                                        }

                                    } // container out-profile-dropped

                                } // container statistics

                            } // list direction

                        } // container egress

                    } // container qos

                } // list isa

                container summary {
                    description "Enter the summary context";

                    leaf max-flow-resources {
                        type yang:gauge32;
                        units "flows";
                        description "The maximum number of flow resources on the ISA-AA MDA(s).";
                    }

                    container statistics {
                        description "Enter the statistics context";

                        leaf flows {
                            type yang:counter64;
                            units "flows";
                            description "The total number of flows created on the ISA-AA MDA(s).";
                        }

                        leaf aa-subscribers-created {
                            type yang:counter64;
                            description "The number of subscribers created.";
                        }

                        leaf aa-subscribers-deleted {
                            type yang:counter64;
                            description "The number of subscribers deleted.";
                        }

                        leaf aa-subscribers-modified {
                            type yang:counter64;
                            description "The number of subscribers modified.";
                        }

                        leaf aa-subscribers-quarantined {
                            type yang:counter64;
                            description "The number of subscribers quarantined.";
                        }

                        leaf seen-ip-requests-sent {
                            type yang:counter64;
                            description
                                "The number of requests sent from the ISA-AA MDA to initiate dynamic transit subscriber creation when traffic
                                 is detected on a parent SAP or Spoke SDP.";
                        }

                        leaf seen-ip-requests-dropped {
                            type yang:counter64;
                            description "The number of Seen IP requests dropped by the ISA-AA MDA due to congestion control mechanisms.";
                        }

                        container diverted-discards {
                            description "Enter the diverted-discards context";

                            container congestion {
                                description "Enter the congestion context";

                                leaf octets {
                                    type yang:counter64;
                                    units "bytes";
                                    description "Number of bytes discarded by the IOMs prior to the ISA-AA MDA(s) due to egress IOM congestion.";
                                }

                                leaf packets {
                                    type yang:counter64;
                                    units "packets";
                                    description "Number of packets discarded by the IOMs prior to the ISA-AA MDA(s) due to egress IOM congestion.";
                                }

                            } // container congestion

                            container errors {
                                description "Enter the errors context";

                                leaf packets {
                                    type yang:counter64;
                                    units "packets";
                                    description "Number of packets discarded by the egress P-chip due to errors in the packets.";
                                }

                            } // container errors

                        } // container diverted-discards

                        container returned-discards {
                            description "Enter the returned-discards context";

                            container congestion {
                                description "Enter the congestion context";

                                leaf octets {
                                    type yang:counter64;
                                    units "bytes";
                                    description "Number of bytes discarded by the IOMs after the ISA-AA MDA(s) due to ingress IOM congestion.";
                                }

                                leaf packets {
                                    type yang:counter64;
                                    units "packets";
                                    description "Number of packets discarded by the IOMs after the ISA-AA MDA(s) due to ingress IOM congestion.";
                                }

                            } // container congestion

                            container errors {
                                description "Enter the errors context";

                                leaf packets {
                                    type yang:counter64;
                                    units "packets";
                                    description "Number of packets discarded due to an error detected by the P-chip while attempting to return the packet to the normal forwarding path.";
                                }

                            } // container errors

                        } // container returned-discards

                        container congestion-discards {
                            description "Enter the congestion-discards context";

                            leaf octets {
                                type yang:counter64;
                                units "bytes";
                                description "Number of bytes discarded by the IOMs after the ISA-AA MDA(s) due IOM congestion.";
                            }

                            leaf packets {
                                type yang:counter64;
                                units "packets";
                                description "Number of packets discarded by the IOMs after the ISA-AA MDA(s) due to IOM congestion.";
                            }

                        } // container congestion-discards

                        container active-flows {
                            description "Enter the active-flows context";

                            leaf current {
                                type yang:gauge32;
                                units "flows";
                                description "The number of active flows currently being tracked by the ISA-AA MDA(s).";
                            }

                            leaf average {
                                type yang:gauge32;
                                units "flows";
                                description "The average number of active flows being tracked by the ISA-AA MDA(s) within the last 60 minutes.";
                            }

                            leaf peak {
                                type yang:gauge32;
                                units "flows";
                                description "The peak number of active flows being tracked by the ISA-AA MDA(s) since system startup.";
                            }

                        } // container active-flows

                        container aa-subscribers-downloaded {
                            description "Enter the aa-subscribers-downloaded context";

                            leaf current {
                                type yang:gauge32;
                                description
                                    "The number of subscribers defined in TIMETRA-SUBSCRIBER-MGMT-MIB::tmnxSubInfoAppProfile
                                     in the tmnxSubscriberInfoTable with tmnxBsxAppProfDivert set to 'true'.";
                            }

                            leaf average {
                                type yang:gauge32;
                                description
                                    "The average number of subscribers defined in TIMETRA-SUBSCRIBER-MGMT-MIB::tmnxSubInfoAppProfile
                                     in the tmnxSubscriberInfoTable with tmnxBsxAppProfDivert set to 'true' within the last 60 minutes.";
                            }

                            leaf peak {
                                type yang:gauge32;
                                description
                                    "The peak number of subscribers defined in TIMETRA-SUBSCRIBER-MGMT-MIB::tmnxSubInfoAppProfile
                                     in the tmnxSubscriberInfoTable with tmnxBsxAppProfDivert set to 'true' since system startup.";
                            }

                        } // container aa-subscribers-downloaded

                        container active-subscribers {
                            description "Enter the active-subscribers context";

                            leaf current {
                                type yang:gauge32;
                                description "The number of subscribers currently with flow records in the ISA-AA MDA(s).";
                            }

                            leaf average {
                                type yang:gauge32;
                                description "The average number of subscribers with flow records in the ISA-AA MDA(s) within the last 60 minutes.";
                            }

                            leaf peak {
                                type yang:gauge32;
                                description "The peak number of subscribers with flow records in the ISA-AA MDA(s) since system startup.";
                            }

                        } // container active-subscribers

                        container diverted-traffic {
                            description "Enter the diverted-traffic context";

                            leaf octets {
                                type yang:counter64;
                                units "bytes";
                                description "Number of bytes diverted from ingress IOMs towards the ISA-AA MDA(s).";
                            }

                            leaf packets {
                                type yang:counter64;
                                units "packets";
                                description "Number of packets diverted from ingress IOMs towards the ISA-AA MDA(s).";
                            }

                        } // container diverted-traffic

                        container entered-aa {
                            description "Enter the entered-aa context";

                            leaf octets {
                                type yang:counter64;
                                units "bytes";
                                description "Number of bytes sent from an IOM which enter the ISA-AA MDA(s).";
                            }

                            leaf packets {
                                type yang:counter64;
                                units "packets";
                                description "Number of packets sent from an IOM which enter the ISA-AA MDA(s).";
                            }

                        } // container entered-aa

                        container inspected {
                            description "Enter the inspected context";

                            leaf octets {
                                type yang:counter64;
                                units "bytes";
                                description "Number of bytes sent for protocol determination in the ISA-AA MDA(s).";
                            }

                            leaf packets {
                                type yang:counter64;
                                units "packets";
                                description "Number of packets sent for protocol determination in the ISA-AA MDA(s).";
                            }

                        } // container inspected

                        container exited-aa {
                            description "Enter the exited-aa context";

                            leaf octets {
                                type yang:counter64;
                                units "bytes";
                                description "Number of bytes which exit the ISA-AA MDA(s) and are sent to the local IOM.";
                            }

                            leaf packets {
                                type yang:counter64;
                                units "packets";
                                description "Number of packets which exit the ISA-AA MDA(s) and are sent to the local IOM.";
                            }

                        } // container exited-aa

                        container buffered-in-aa {
                            description "Enter the buffered-in-aa context";

                            leaf octets {
                                type yang:counter64;
                                units "bytes";
                                description "Number of bytes buffered by the ISA-AA MDA(s).";
                            }

                            leaf packets {
                                type yang:counter64;
                                units "packets";
                                description "Number of packets buffered by the ISA-AA MDA(s).";
                            }

                        } // container buffered-in-aa

                        container discarded-in-aa {
                            description "Enter the discarded-in-aa context";

                            container policy {
                                description "Enter the policy context";

                                leaf octets {
                                    type yang:counter64;
                                    units "bytes";
                                    description "Number of bytes discarded by the ISA-AA MDA(s) due to policy.";
                                }

                                leaf packets {
                                    type yang:counter64;
                                    units "packets";
                                    description "Number of packets discarded by the ISA-AA MDA(s) due to policy.";
                                }

                            } // container policy

                            container congestion {
                                description "Enter the congestion context";

                                leaf octets {
                                    type yang:counter64;
                                    units "bytes";
                                    description "Number of bytes discarded by the ISA-AA MDA(s) due to congestion.";
                                }

                                leaf packets {
                                    type yang:counter64;
                                    units "packets";
                                    description "Number of packets discarded by the ISA-AA MDA(s) due to congestion.";
                                }

                            } // container congestion

                            container errors {
                                description "Enter the errors context";

                                leaf octets {
                                    type yang:counter64;
                                    units "bytes";
                                    description "Number of bytes discarded due to unrecoverable errors.";
                                }

                                leaf packets {
                                    type yang:counter64;
                                    units "packets";
                                    description "Number of packets discarded due to unrecoverable errors.";
                                }

                            } // container errors

                            container tcp-optimization {
                                description "Enter the tcp-optimization context";

                            } // container tcp-optimization

                        } // container discarded-in-aa

                        container modified-in-aa {
                            description "Enter the modified-in-aa context";

                            container packet-size-increased {
                                description "Enter the packet-size-increased context";

                                leaf octets {
                                    type yang:counter64;
                                    units "bytes";
                                    description "Number of additional octets the ISA-AA MDA injected into the packets.";
                                }

                                leaf packets {
                                    type yang:counter64;
                                    units "packets";
                                    description "Number of packets that the ISA-AA MDA has increased in size.";
                                }

                            } // container packet-size-increased

                            container packet-size-decreased {
                                description "Enter the packet-size-decreased context";

                                leaf octets {
                                    type yang:counter64;
                                    units "bytes";
                                    description "Number of octets the ISA-AA MDA has removed from packets.";
                                }

                                leaf packets {
                                    type yang:counter64;
                                    units "packets";
                                    description "Number of packets that the ISA-AA MDA has decreased in size.";
                                }

                            } // container packet-size-decreased

                        } // container modified-in-aa

                        container errors {
                            description "Enter the errors context";

                            container policy-bypass {
                                description "Enter the policy-bypass context";

                                leaf octets {
                                    type yang:counter64;
                                    units "bytes";
                                    description
                                        "Number of octets which pass untouched that did not have statistics or policy applied.
                                         These bytes are counted as policy bypass errors.";
                                }

                                leaf packets {
                                    type yang:counter64;
                                    units "packets";
                                    description
                                        "Number of packets which passed untouched that did not have statistics or policy applied.
                                         These packets are counted as policy bypass errors.";
                                }

                            } // container policy-bypass

                            container cut-through {
                                description "Enter the cut-through context";

                                leaf octets {
                                    type yang:counter64;
                                    units "bytes";
                                    description
                                        "Number of octets which passed untouched, but have policy applied.
                                         These octets are counted as cut-through errors.";
                                }

                                leaf packets {
                                    type yang:counter64;
                                    units "packets";
                                    description
                                        "Number of packets which passed untouched, but have policy applied.
                                         These packets are counted as cut-through errors.";
                                }

                                container flow-resource {
                                    description "Enter the flow-resource context";

                                    leaf octets {
                                        type yang:counter64;
                                        units "bytes";
                                        description "Number of octets that the ISA-AA MDA(s) have cut-through due to flow resource exhaustion.";
                                    }

                                    leaf packets {
                                        type yang:counter64;
                                        units "packets";
                                        description "Number of packets that the ISA-AA MDA(s) have cut-through due to flow resource exhaustion.";
                                    }

                                } // container flow-resource

                                container overload {
                                    description "Enter the overload context";

                                    leaf octets {
                                        type yang:counter64;
                                        units "bytes";
                                        description "Number of octets that the ISA-AA MDA has cut-through due to the overload cut-through configuration as indicated by the object tmnxBsxIsaAaGrpOverloadCutThru.";
                                    }

                                    leaf packets {
                                        type yang:counter64;
                                        units "packets";
                                        description "Number of octets that the ISA-AA MDA has cut-through due to the overload cut-through configuration as indicated by the object tmnxBsxIsaAaGrpOverloadCutThru.";
                                    }

                                } // container overload

                            } // container cut-through

                        } // container errors

                        container generated-in-aa {
                            description "Enter the generated-in-aa context";

                            container http-redirect {
                                description "Enter the http-redirect context";

                                leaf octets {
                                    type yang:counter64;
                                    units "bytes";
                                    description "Number of octets that the ISA-AA MDA has created to redirect HTTP and HTTPS.";
                                }

                                leaf packets {
                                    type yang:counter64;
                                    units "packets";
                                    description "Number of packets that the ISA-AA MDA has created to redirect HTTP and HTTPS.";
                                }

                            } // container http-redirect

                        } // container generated-in-aa

                        container returned-traffic {
                            description "Enter the returned-traffic context";

                            leaf octets {
                                type yang:counter64;
                                units "bytes";
                                description "Number of bytes returned to the normal forwarding path that are sent to egress IOMs from the ISA-AA MDA(s).";
                            }

                            leaf packets {
                                type yang:counter64;
                                units "packets";
                                description "Number of packets returned to the normal forwarding path that are sent to egress IOMs from the ISA-AA MDA(s).";
                            }

                        } // container returned-traffic

                        container flow-resources {
                            description "Enter the flow-resources context";

                            leaf current {
                                type yang:gauge32;
                                description "The number of flow resources currently in-use on the ISA-AA MDA(s).";
                            }

                            leaf average {
                                type yang:gauge32;
                                units "flows";
                                description "The average number of flow resources in use on the ISA-AA MDA(s) within the last 60 minutes.";
                            }

                            leaf peak {
                                type yang:gauge32;
                                units "flows";
                                description "The peak number of flow resources in use on the ISA-AA MDA(s) since system startup.";
                            }

                            leaf current-percent {
                                type uint32 {
                                    range "0..10000";
                                }
                                units "centipercent";
                                description "The current percentage of total flow resources in-use on the ISA-AA MDA.";
                            }

                            leaf average-percent {
                                type uint32 {
                                    range "0..10000";
                                }
                                units "centipercent";
                                description "The average percentage of total flow resources in-use on the ISA-AA MDA.";
                            }

                            leaf peak-percent {
                                type uint32 {
                                    range "0..10000";
                                }
                                units "centipercent";
                                description "The peak percentage of total flow resources in-use on the ISA-AA MDA.";
                            }

                        } // container flow-resources

                        container flow-setup-rate {
                            description "Enter the flow-setup-rate context";

                            leaf current {
                                type yang:gauge32;
                                units "flows per second";
                                description "The number of flow setups per second over the most recent 10 second period.";
                            }

                            leaf average {
                                type yang:gauge32;
                                units "flows per second";
                                description "The average number of flow setups per second being tracked by the ISA-AA MDA(s) within the last 60 minutes.";
                            }

                            leaf peak {
                                type yang:gauge32;
                                units "flows per second";
                                description "The peak number of flow setups per second being tracked by the ISA-AA MDA(s) since system startup.";
                            }

                        } // container flow-setup-rate

                        container traffic-rate {
                            description "Enter the traffic-rate context";

                            leaf current {
                                type yang:gauge32;
                                units "megabps";
                                description "The traffic rate in megabits(s) per second (mbps) incoming to the ISA-AA MDA(s).";
                            }

                            leaf average {
                                type yang:gauge32;
                                units "megabps";
                                description "The average traffic rate in megabits(s) per second (mbps) incoming to the ISA-AA MDA(s) within the last 60 minutes.";
                            }

                            leaf peak {
                                type yang:gauge32;
                                units "megabps";
                                description "The peak traffic rate in megabits(s) per second (mbps) incoming to the ISA-AA MDA(s) since system startup.";
                            }

                        } // container traffic-rate

                        container packet-rate {
                            description "Enter the packet-rate context";

                            leaf current {
                                type yang:gauge32;
                                units "packets per second";
                                description "The current number of packets per second incoming to the ISA-AA MDA(s).";
                            }

                            leaf average {
                                type yang:gauge32;
                                units "packets per second";
                                description "The average number of packets per second incoming to the ISA-AA MDA(s) within the last 60 minutes.";
                            }

                            leaf peak {
                                type yang:gauge32;
                                units "packets per second";
                                description "The peak number of packets per second incoming to the ISA-AA MDA(s) since system startup.";
                            }

                        } // container packet-rate

                        container datapath-cpu-usage {
                            description "Enter the datapath-cpu-usage context";

                            leaf current {
                                type uint32 {
                                    range "0..10000";
                                }
                                units "centipercent";
                                description "The percent utilization of the datapath CPU on the ISA-AA MDA(s).";
                            }

                            leaf average {
                                type uint32 {
                                    range "0..10000";
                                }
                                units "centipercent";
                                description "The average percent utilization of the datapath CPU on the ISA-AA MDA(s) within the last 60 minutes.";
                            }

                            leaf peak {
                                type uint32 {
                                    range "0..10000";
                                }
                                units "centipercent";
                                description "The peak percent utilization of the datapath CPU on the ISA-AA MDA(s) since system startup.";
                            }

                        } // container datapath-cpu-usage

                        container management-cpu-usage {
                            description "Enter the management-cpu-usage context";

                            leaf current {
                                type uint32 {
                                    range "0..10000";
                                }
                                units "centipercent";
                                description "The percent utilization of the management CPU on the ISA-AA MDA(s).";
                            }

                            leaf average {
                                type uint32 {
                                    range "0..10000";
                                }
                                units "centipercent";
                                description "The average percent utilization of the management CPU on the ISA-AA MDA(s) within the last 60 minutes.";
                            }

                            leaf peak {
                                type uint32 {
                                    range "0..10000";
                                }
                                units "centipercent";
                                description "The peak percent utilization of the management CPU on the ISA-AA MDA(s) since system startup.";
                            }

                        } // container management-cpu-usage

                    } // container statistics

                    container tca {
                        description "Enter the tca context";

                        container flow-resources {
                            description "Enter the flow-resources context";

                            leaf state {
                                type types-aa:tca-state;
                                description "The state of the flow resource TCA (tmnxBsxIsaAaGrpFlowFull).";
                            }

                            container statistics {
                                description "Enter the statistics context";

                                leaf count {
                                    type yang:counter64;
                                    description "The number of times the flow resource TCA (tmnxBsxIsaAaGrpFlowFull) was raised since system startup.";
                                }

                                leaf duration {
                                    type yang:counter64;
                                    units "seconds";
                                    description "The amount of time the flow resource TCA (tmnxBsxIsaAaGrpFlowFull) was in the raised state since system startup.";
                                }

                            } // container statistics

                        } // container flow-resources

                        container flow-setup-rate {
                            description "Enter the flow-setup-rate context";

                            leaf state {
                                type types-aa:tca-state;
                                description "The state of the flow setup rate TCA (tmnxBsxIsaAaGrpFlowSetup).";
                            }

                            container statistics {
                                description "Enter the statistics context";

                                leaf count {
                                    type yang:counter64;
                                    description "The number of times the flow setup rate TCA (tmnxBsxIsaAaGrpFlowSetup) was raised since system startup.";
                                }

                                leaf duration {
                                    type yang:counter64;
                                    units "seconds";
                                    description "The amount of time the flow setup rate TCA (tmnxBsxIsaAaGrpFlowSetup) was in the raised state since system startup.";
                                }

                            } // container statistics

                        } // container flow-setup-rate

                        container traffic-rate {
                            description "Enter the traffic-rate context";

                            leaf state {
                                type types-aa:tca-state;
                                description "The state of the bit rate TCA (tmnxBsxIsaAaGrpBitRate).";
                            }

                            container statistics {
                                description "Enter the statistics context";

                                leaf count {
                                    type yang:counter64;
                                    description "The number of times the bit rate TCA (tmnxBsxIsaAaGrpBitRate) was raised since system startup.";
                                }

                                leaf duration {
                                    type yang:counter64;
                                    units "seconds";
                                    description "The amount time the bit rate TCA (tmnxBsxIsaAaGrpBitRate) was in the raised state since system startup.";
                                }

                            } // container statistics

                        } // container traffic-rate

                        container packet-rate {
                            description "Enter the packet-rate context";

                            leaf state {
                                type types-aa:tca-state;
                                description "The state of the packet rate TCA (tmnxBsxIsaAaGrpPacketRate).";
                            }

                            container statistics {
                                description "Enter the statistics context";

                                leaf count {
                                    type yang:counter64;
                                    description "The number of times the packet rate TCA (tmnxBsxIsaAaGrpPacketRate) was raised since system startup.";
                                }

                                leaf duration {
                                    type yang:counter64;
                                    units "seconds";
                                    description "The amount of time the packet rate TCA (tmnxBsxIsaAaGrpPacketRate) was in the raised state since system startup.";
                                }

                            } // container statistics

                        } // container packet-rate

                        container datapath-cpu-usage {
                            description "Enter the datapath-cpu-usage context";

                            leaf state {
                                type types-aa:tca-state;
                                description "The state of the datapath CPU TCA (tmnxBsxDatapathCpuUsage).";
                            }

                            container statistics {
                                description "Enter the statistics context";

                                leaf count {
                                    type yang:counter64;
                                    description "The number of times the datapath CPU TCA (tmnxBsxDatapathCpuUsage) was raised since system startup.";
                                }

                                leaf duration {
                                    type yang:counter64;
                                    units "seconds";
                                    description "The amount of time the datapath CPU TCA (tmnxBsxDatapathCpuUsage) was in the raised state since system startup.";
                                }

                            } // container statistics

                        } // container datapath-cpu-usage

                        container isa-overload {
                            description "Enter the isa-overload context";

                            leaf state {
                                type types-aa:tca-state;
                                description "The state of the overload cut-through TCA (tmnxBsxIsaAaGrpOvrldCutthru).";
                            }

                            container statistics {
                                description "Enter the statistics context";

                                leaf count {
                                    type yang:counter64;
                                    description "The number of times the overload cut-through TCA (tmnxBsxIsaAaGrpOvrldCutthru) was raised since system startup.";
                                }

                                leaf duration {
                                    type yang:counter64;
                                    units "seconds";
                                    description "The amount of time the overload cut-through TCA (tmnxBsxIsaAaGrpOvrldCutthru) was in the raised state since system startup.";
                                }

                            } // container statistics

                        } // container isa-overload

                    } // container tca

                    container sub-to-net {
                        description "Enter the sub-to-net context";

                        container overload-cut-through-tca {
                            description "Enter the overload-cut-through-tca context";

                            leaf state {
                                type types-aa:tca-state;
                                description "The state of the subscriber to network weighted average shared buffer TCA (tmnxBsxIsaAaGrpFmSbWaSBufOvld).";
                            }

                            leaf current-wa-buffer-depth {
                                type uint32 {
                                    range "0..10000";
                                }
                                units "centipercent";
                                description "The percent utilization of the subscriber to network weighted average shared buffer on the ISA-AA MDA(s).";
                            }

                            container statistics {
                                description "Enter the statistics context";

                                leaf count {
                                    type yang:counter64;
                                    description "The number of times the subscriber to network weighted average shared buffer TCA (tmnxBsxIsaAaGrpFmSbWaSBufOvld) was raised since system startup.";
                                }

                                leaf duration {
                                    type yang:counter64;
                                    units "seconds";
                                    description "The amount of time the subscriber to network weighted average shared buffer TCA (tmnxBsxIsaAaGrpFmSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the subscriber-to-network direction.";
                                }

                                leaf packets {
                                    type yang:counter64;
                                    units "packets";
                                    description "Number of packets diverted from ingress IOMs towards the ISA-AA MDA(s) in the subscriber-to-network direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the subscriber-to-network direction.";
                                    }

                                    leaf packets {
                                        type yang:counter64;
                                        units "packets";
                                        description "Number of packets discarded by the IOMs prior to the ISA-AA MDA(s) due to egress IOM congestion in the subscriber-to-network direction.";
                                    }

                                } // container congestion

                                container errors {
                                    description "Enter the errors context";

                                    leaf packets {
                                        type yang:counter64;
                                        units "packets";
                                        description "Number of packets discarded by the egress P-chip due to errors in the packets in the subscriber-to-network direction.";
                                    }

                                } // container errors

                            } // container diverted-discards

                            container entered-aa {
                                description "Enter the entered-aa context";

                                leaf octets {
                                    type yang:counter64;
                                    units "bytes";
                                    description "Number of bytes sent from an IOM which enter the ISA-AA MDA(s) in the subscriber-to-network direction.";
                                }

                                leaf packets {
                                    type yang:counter64;
                                    units "packets";
                                    description "Number of packets sent from an IOM which enter the ISA-AA MDA(s) in the subscriber-to-network direction.";
                                }

                            } // container entered-aa

                            container buffered-in-aa {
                                description "Enter the buffered-in-aa context";

                                leaf octets {
                                    type yang:counter64;
                                    units "bytes";
                                    description "Number of bytes buffered by the ISA-AA MDA(s) in the subscriber-to-network direction.";
                                }

                                leaf packets {
                                    type yang:counter64;
                                    units "packets";
                                    description "Number of packets buffered by the ISA-AA MDA(s) in the subscriber-to-network direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the subscriber-to-network direction.";
                                    }

                                    leaf packets {
                                        type yang:counter64;
                                        units "packets";
                                        description "Number of packets discarded by the ISA-AA MDA(s) due to policy in the subscriber-to-network direction.";
                                    }

                                } // container policy

                                container congestion {
                                    description "Enter the congestion context";

                                    leaf octets {
                                        type yang:counter64;
                                        units "bytes";
                                        description "Number of bytes discarded by the ISA-AA MDA(s) due to congestion in the subscriber-to-network direction.";
                                    }

                                    leaf packets {
                                        type yang:counter64;
                                        units "packets";
                                        description "Number of packets discarded by the ISA-AA MDA(s) due to congestion in the subscriber-to-network direction.";
                                    }

                                } // container congestion

                                container errors {
                                    description "Enter the errors context";

                                    leaf octets {
                                        type yang:counter64;
                                        units "bytes";
                                        description "Number of bytes discarded due to unrecoverable errors in the subscriber-to-network direction.";
                                    }

                                    leaf packets {
                                        type yang:counter64;
                                        units "packets";
                                        description "Number of packets discarded due to unrecoverable errors in the subscriber-to-network direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the subscriber-to-network direction.";
                                    }

                                    leaf packets {
                                        type yang:counter64;
                                        units "packets";
                                        description "Number of packets that the ISA-AA MDA has increased in size in the subscriber-to-network direction.";
                                    }

                                } // container packet-size-increased

                                container packet-size-decreased {
                                    description "Enter the packet-size-decreased context";

                                    leaf octets {
                                        type yang:counter64;
                                        units "bytes";
                                        description "Number of octets the ISA-AA MDA has removed from packets in the subscriber-to-network direction.";
                                    }

                                    leaf packets {
                                        type yang:counter64;
                                        units "packets";
                                        description "Number of packets that the ISA-AA MDA has decreased in size in the subscriber-to-network direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which pass untouched that did not have statistics or policy applied.
                                             These bytes are counted as policy bypass errors in the subscriber-to-network direction.";
                                    }

                                    leaf packets {
                                        type yang:counter64;
                                        units "packets";
                                        description
                                            "Number of packets which passed untouched that did not have statistics or policy applied.
                                             These packets are counted as policy bypass errors in the subscriber-to-network direction.";
                                    }

                                } // container policy-bypass

                                container cut-through {
                                    description "Enter the cut-through context";

                                    leaf octets {
                                        type yang:counter64;
                                        units "bytes";
                                        description
                                            "Number of octets which passed untouched, but have policy applied in the subscriber-to-network direction.
                                             These octets are counted as cut-through errors.";
                                    }

                                    leaf packets {
                                        type yang:counter64;
                                        units "packets";
                                        description
                                            "Number of packets which passed untouched, but have policy applied in the subscriber-to-network direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the subscriber-to-network direction.";
                                    }

                                    leaf packets {
                                        type yang:counter64;
                                        units "packets";
                                        description "Number of packets that the ISA-AA MDA has created to redirect HTTP and HTTPS in the subscriber-to-network direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the subscriber-to-network direction.";
                                }

                                leaf packets {
                                    type yang:counter64;
                                    units "packets";
                                    description "Number of packets which exit the ISA-AA MDA(s) and are sent to the local IOM in the subscriber-to-network direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the subscriber-to-network direction.";
                                    }

                                    leaf packets {
                                        type yang:counter64;
                                        units "packets";
                                        description "Number of packets discarded by the IOMs after the ISA-AA MDA(s) due to ingress IOM congestion in the subscriber-to-network direction.";
                                    }

                                } // container congestion

                                container errors {
                                    description "Enter the errors context";

                                    leaf packets {
                                        type yang:counter64;
                                        units "packets";
                                        description
                                            "Number of packets discarded due to an error detected by the P-chip while attempting to return
                                             the packet to the normal forwarding path in the subscriber-to-network direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the subscriber-to-network direction.";
                                }

                                leaf packets {
                                    type yang:counter64;
                                    units "packets";
                                    description "Number of packets returned to the normal forwarding path that are sent to egress IOMs from the ISA-AA MDA(s) in the subscriber-to-network direction.";
                                }

                            } // container returned-traffic

                        } // container statistics

                    } // container sub-to-net

                    container net-to-sub {
                        description "Enter the net-to-sub context";

                        container overload-cut-through-tca {
                            description "Enter the overload-cut-through-tca context";

                            leaf current-wa-buffer-depth {
                                type uint32 {
                                    range "0..10000";
                                }
                                units "centipercent";
                                description "The percent utilization of the network to subscriber weighted average shared buffer on the ISA-AA MDA(s).";
                            }

                            leaf state {
                                type types-aa:tca-state;
                                description "The state of the network to subscriber weighted average shared buffer TCA (tmnxBsxIsaAaGrpToSbWaSBufOvld).";
                            }

                            container statistics {
                                description "Enter the statistics context";

                                leaf count {
                                    type yang:counter64;
                                    description "The number of times the network to subscriber weighted average shared buffer TCA (tmnxBsxIsaAaGrpToSbWaSBufOvld) was raised since system startup.";
                                }

                                leaf duration {
                                    type yang:counter64;
                                    units "seconds";
                                    description "The amount of time the network to subscriber weighted average shared buffer TCA (tmnxBsxIsaAaGrpToSbWaSBufOvld) was in the raised state since system startup.";
                                }

                            } // container statistics

                        } // container overload-cut-through-tca

                        container statistics {
                            description "Enter the statistics context";

                            container diverted-traffic {
                                description "Enter the diverted-traffic context";

                                leaf octets {
                                    type yang:counter64;
                                    units "bytes";
                                    description "Number of bytes diverted from ingress IOMs towards the ISA-AA MDA(s) in the network-to-subscriber direction.";
                                }

                                leaf packets {
                                    type yang:counter64;
                                    units "packets";
                                    description "Number of packets diverted from ingress IOMs towards the ISA-AA MDA(s) in the network-to-subscriber direction.";
                                }

                            } // container diverted-traffic

                            container diverted-discards {
                                description "Enter the diverted-discards context";

                                container congestion {
                                    description "Enter the congestion context";

                                    leaf octets {
                                        type yang:counter64;
                                        units "bytes";
                                        description "Number of bytes discarded by the IOMs prior to the ISA-AA MDA(s) due to egress IOM congestion in the network-to-subscriber direction.";
                                    }

                                    leaf packets {
                                        type yang:counter64;
                                        units "packets";
                                        description "Number of packets discarded by the IOMs prior to the ISA-AA MDA(s) due to egress IOM congestion in the network-to-subscriber direction.";
                                    }

                                } // container congestion

                                container errors {
                                    description "Enter the errors context";

                                    leaf packets {
                                        type yang:counter64;
                                        units "packets";
                                        description "Number of packets discarded by the egress P-chip due to errors in the packets in the network-to-subscriber direction";
                                    }

                                } // container errors

                            } // container diverted-discards

                            container entered-aa {
                                description "Enter the entered-aa context";

                                leaf octets {
                                    type yang:counter64;
                                    units "bytes";
                                    description "Number of bytes sent from an IOM which enter the ISA-AA MDA(s) in the network-to-subscriber direction.";
                                }

                                leaf packets {
                                    type yang:counter64;
                                    units "packets";
                                    description "Number of packets sent from an IOM which enter the ISA-AA MDA(s) in the network-to-subscriber direction.";
                                }

                            } // container entered-aa

                            container buffered-in-aa {
                                description "Enter the buffered-in-aa context";

                                leaf octets {
                                    type yang:counter64;
                                    units "bytes";
                                    description "Number of bytes buffered by the ISA-AA MDA(s) in the network-to-subscriber direction.";
                                }

                                leaf packets {
                                    type yang:counter64;
                                    units "packets";
                                    description "Number of packets buffered by the ISA-AA MDA(s) in the network-to-subscriber direction.";
                                }

                            } // container buffered-in-aa

                            container discarded-in-aa {
                                description "Enter the discarded-in-aa context";

                                container policy {
                                    description "Enter the policy context";

                                    leaf octets {
                                        type yang:counter64;
                                        units "bytes";
                                        description "Number of bytes discarded by the ISA-AA MDA(s) due to policy in the network-to-subscriber direction.";
                                    }

                                    leaf packets {
                                        type yang:counter64;
                                        units "packets";
                                        description "Number of packets discarded by the ISA-AA MDA(s) due to policy in the network-to-subscriber direction.";
                                    }

                                } // container policy

                                container congestion {
                                    description "Enter the congestion context";

                                    leaf octets {
                                        type yang:counter64;
                                        units "bytes";
                                        description "Number of bytes discarded by the ISA-AA MDA(s) due to congestion in the network-to-subscriber direction.";
                                    }

                                    leaf packets {
                                        type yang:counter64;
                                        units "packets";
                                        description "Number of packets discarded by the ISA-AA MDA(s) due to congestion in the network-to-subscriber direction.";
                                    }

                                } // container congestion

                                container errors {
                                    description "Enter the errors context";

                                    leaf octets {
                                        type yang:counter64;
                                        units "bytes";
                                        description "Number of bytes discarded due to unrecoverable errors in the network-to-subscriber direction.";
                                    }

                                    leaf packets {
                                        type yang:counter64;
                                        units "packets";
                                        description "Number of packets discarded due to unrecoverable errors in the network-to-subscriber direction.";
                                    }

                                } // container errors

                            } // container discarded-in-aa

                            container modified-in-aa {
                                description "Enter the modified-in-aa context";

                                container packet-size-increased {
                                    description "Enter the packet-size-increased context";

                                    leaf octets {
                                        type yang:counter64;
                                        units "bytes";
                                        description "Number of additional octets the ISA-AA MDA injected into the packets in the network-to-subscriber direction.";
                                    }

                                    leaf packets {
                                        type yang:counter64;
                                        units "packets";
                                        description "Number of packets that the ISA-AA MDA has increased in size in the network-to-subscriber direction.";
                                    }

                                } // container packet-size-increased

                                container packet-size-decreased {
                                    description "Enter the packet-size-decreased context";

                                    leaf octets {
                                        type yang:counter64;
                                        units "bytes";
                                        description "Number of octets the ISA-AA MDA has removed from packets in the network-to-subscriber direction.";
                                    }

                                    leaf packets {
                                        type yang:counter64;
                                        units "packets";
                                        description "Number of packets that the ISA-AA MDA has decreased in size in the network-to-subscriber direction.";
                                    }

                                } // container packet-size-decreased

                            } // container modified-in-aa

                            container errors {
                                description "Enter the errors context";

                                container policy-bypass {
                                    description "Enter the policy-bypass context";

                                    leaf octets {
                                        type yang:counter64;
                                        units "bytes";
                                        description
                                            "Number of octets which passed untouched that did not have statistics or policy applied.
                                             These octets are counted as policy bypass errors in the network-to-subscriber direction.";
                                    }

                                    leaf packets {
                                        type yang:counter64;
                                        units "packets";
                                        description
                                            "Number of packets which passed untouched that did not have statistics or policy applied.
                                             These packets are counted as policy bypass errors in the network-to-subscriber direction.";
                                    }

                                } // container policy-bypass

                                container cut-through {
                                    description "Enter the cut-through context";

                                    leaf octets {
                                        type yang:counter64;
                                        units "bytes";
                                        description
                                            "Number of octets which passed untouched, but have policy applied in the network-to-subscriber direction.
                                             These octets are counted as cut-through errors.";
                                    }

                                    leaf packets {
                                        type yang:counter64;
                                        units "packets";
                                        description
                                            "Number of packets which passed untouched, but have policy applied in the network-to-subscriber direction.
                                             These packets are counted as cut-through errors.";
                                    }

                                } // container cut-through

                            } // container errors

                            container generated-in-aa {
                                description "Enter the generated-in-aa context";

                                container http-redirect {
                                    description "Enter the http-redirect context";

                                    leaf octets {
                                        type yang:counter64;
                                        units "bytes";
                                        description "Number of octets that the ISA-AA MDA has created to redirect HTTP and HTTPS in the network-to-subscriber direction.";
                                    }

                                    leaf packets {
                                        type yang:counter64;
                                        units "packets";
                                        description "Number of packets that the ISA-AA MDA has created to redirect HTTP and HTTPS in the network-to-subscriber direction.";
                                    }

                                } // container http-redirect

                            } // container generated-in-aa

                            container exited-aa {
                                description "Enter the exited-aa context";

                                leaf octets {
                                    type yang:counter64;
                                    units "bytes";
                                    description "Number of bytes which exit the ISA-AA MDA(s) and are sent to the local IOM in the network-to-subscriber direction.";
                                }

                                leaf packets {
                                    type yang:counter64;
                                    units "packets";
                                    description "Number of packets which exit the ISA-AA MDA(s) and are sent to the local IOM in the network-to-subscriber direction.";
                                }

                            } // container exited-aa

                            container returned-discards {
                                description "Enter the returned-discards context";

                                container congestion {
                                    description "Enter the congestion context";

                                    leaf octets {
                                        type yang:counter64;
                                        units "bytes";
                                        description "Number of bytes discarded by the IOMs after the ISA-AA MDA(s) due to ingress IOM congestion in the network-to-subscriber direction.";
                                    }

                                    leaf packets {
                                        type yang:counter64;
                                        units "packets";
                                        description "Number of packets discarded by the IOMs after the ISA-AA MDA(s) due to ingress IOM congestion in the network-to-subscriber direction.";
                                    }

                                } // container congestion

                                container errors {
                                    description "Enter the errors context";

                                    leaf packets {
                                        type yang:counter64;
                                        units "packets";
                                        description
                                            "Number of packets discarded due to an error detected by the P-chip while attempting to return
                                             the packet to the normal forwarding path in the network-to-subscriber direction.";
                                    }

                                } // container errors

                            } // container returned-discards

                            container returned-traffic {
                                description "Enter the returned-traffic context";

                                leaf octets {
                                    type yang:counter64;
                                    units "bytes";
                                    description "Number of bytes returned to the normal forwarding path that are sent to egress IOMs from the ISA-AA MDA(s) in the network-to-subscriber direction.";
                                }

                                leaf packets {
                                    type yang:counter64;
                                    units "packets";
                                    description "Number of packets returned to the normal forwarding path that are sent to egress IOMs from the ISA-AA MDA(s) in the network-to-subscriber direction.";
                                }

                            } // container returned-traffic

                        } // container statistics

                    } // container net-to-sub

                } // container summary

            } // container status

            list url-list {
                key "url-list-name";
                description "Enter the url-list list instance";

                leaf url-list-name {
                    type types-sros:named-item;
                    description "URL list name";
                }

                leaf oper-state {
                    type types-sros:oper-state;
                    description
                        "The operational state of the URL list.
                         When the value is 'down' the URL list is not active.";
                }

                leaf oper-flags {
                    type types-aa:url-list-flags;
                    description "The conditions that affect the operating status of the URL list.";
                }

                leaf deployed-to-isas {
                    type boolean;
                    description
                        "Indicates whether or not the configured file has been deployed to all AA ISAs or ESA-VMs in this group.

                         A value of 'true' indicates the configured url-list file is currently deployed
                         on AA ISAs or ESA-VMs in this group.

                         A value of 'false' indicates the configured url-list file is different from the one currently
                         deployed on AA ISAs or ESA-VMs in this group. An admin/application-assurance/group/url-list upgrade
                         or url-list admin-state enable can trigger the current file to be imported and deployed.";
                }

                container file-import {
                    description "Enter the file-import context";

                    container success {
                        description "Enter the success context";

                        leaf last-time {
                            type yang:date-and-time;
                            description
                                "The most recent time of a successful file import.  When a file import is successful attempt/last-time
                                 and success/last-time will be the same and attempt/in-progress will be 'false'.";
                        }

                        leaf file-name {
                            type types-sros:display-string-or-empty {
                                length "0..180";
                            }
                            description "The filename on compact flash at the time of the most recent successful URL list file import.";
                        }

                        leaf url-entries {
                            type yang:gauge32;
                            description "The number of entries in the URL list retrieved from the specified file.";
                        }

                        leaf url-characters {
                            type yang:gauge32;
                            description "The number of characters in the URLs retrieved from the specified file.";
                        }

                        leaf url-host-expressions {
                            type yang:gauge32;
                            description "The number of host expressions in the URLs retrieved from the specified file.";
                        }

                        leaf blank-or-comment-lines {
                            type yang:gauge32;
                            description "The number of blank or comment lines that were skipped while processing the specified file.";
                        }

                    } // container success

                    container attempt {
                        description "Enter the attempt context";

                        leaf last-time {
                            type yang:date-and-time;
                            description
                                "The most recent time of an attempted file import.  When a file import is successful attempt/last-time
                                 and success/last-time will be the same and attempt/in-progress will be 'false'.";
                        }

                        leaf in-progress {
                            type boolean;
                            description "Indicates 'true' if there is a file import attempt currently in progress.";
                        }

                        leaf file-name {
                            type types-sros:display-string-or-empty {
                                length "0..180";
                            }
                            description "The filename on compact flash at the time of the most recent attempted URL list file import.";
                        }

                        leaf error-line {
                            type uint32 {
                                range "0..2147483647";
                            }
                            description
                                "The approximate line from the specified file which had an error while performing a URL list file import.
                                 A value of 0 indicates there was an error not associated with any line.";
                        }

                        leaf error-reason {
                            type types-aa:url-list-flags;
                            description "The reason for the failure of the URL list file import.";
                        }

                        leaf error-detail {
                            type types-sros:display-string;
                            description "The text reason for the failure of the URL list file import.";
                        }

                    } // container attempt

                } // container file-import

            } // list url-list

            list url-filter {
                key "url-filter-name";
                description "Enter the url-filter list instance";

                leaf url-filter-name {
                    type types-sros:named-item;
                    description "URL filter name";
                }

                list esa {
                    key "esa-id vm";
                    description "Enter the esa list instance";

                    leaf esa-id {
                        type types-esa:esa-id;
                        description "ESA ID";
                    }

                    leaf vm {
                        type types-esa:vm-id;
                        description "VM ID within the ESA";
                    }

                    leaf oper-state {
                        type types-sros:oper-state;
                        description "The operational state of the URL Filter.";
                    }

                    leaf oper-flags {
                        type bits {
                            bit admin-down                     { position 0; }
                            bit no-aa-interface                { position 1; }
                            bit aa-interface-down              { position 2; }
                            bit icap-server-down               { position 3; }
                            bit url-list-down                  { position 4; }
                            bit web-service-down               { position 5; }
                        }
                        description "The conditions that affect the operating status of the URL Filter";
                    }

                    container statistics {
                        description "Enter the statistics context";

                        leaf client-requests {
                            type yang:counter64;
                            description
                                "The number of URL requests made by clients to web servers that were
                                 analyzed by the url-filter.";
                        }

                        leaf client-request-errors {
                            type yang:counter64;
                            description "The number of times the URL request was unable to be analyzed.";
                        }

                        leaf server-response-allow {
                            type yang:counter64;
                            description
                                "The number of URL responses from web servers to clients that were
                                 allowed based on the url-filter analysis of the client-request
                                 resulting in a url-allow decision.";
                        }

                        leaf server-response-redirect {
                            type yang:counter64;
                            description
                                "The number of URL responses from web servers to clients that were
                                 redirected based on the url-filter analysis of the client-request
                                 resulting in a url-block-redirect decision and the conversation
                                 being redirectable.";
                        }

                        leaf server-response-block {
                            type yang:counter64;
                            description
                                "The number of URL responses from web servers to clients that were
                                 blocked or TCP reset based on the url-filter analysis of the client-request
                                 resulting in a url-block-redirect decision and the conversation
                                 not being redirectable.";
                        }

                        leaf server-response-default {
                            type yang:counter64;
                            description
                                "The number of URL responses from web servers to clients that took
                                 a default-actions based on the url-filter analysis of the client-request
                                 resulting in a url-default-action decision.";
                        }

                        leaf url-allow {
                            type yang:counter64;
                            description
                                "The total number of URL lookup requests that resulted in an 'allow'
                                 decision by the url-filter.";
                        }

                        leaf url-block-redirect {
                            type yang:counter64;
                            description
                                "The total number of URL lookup requests that resulted in a 'redirect'
                                 or 'block' decision by the last filtering function within the url-filter.";
                        }

                        leaf url-default-action {
                            type yang:counter64;
                            description
                                "The total number of URL lookup requests that resulted in a 'default-action'
                                 decision by the last filtering function within the url-filter.";
                        }

                    } // container statistics

                    container local-filtering {
                        description "Enter the local-filtering context";

                        container statistics {
                            description "Enter the statistics context";

                            container allow-list {
                                description "Enter the allow-list context";

                                leaf lookup {
                                    type yang:counter64;
                                    description "The number of allow-list URL lookups.";
                                }

                                leaf match {
                                    type yang:counter64;
                                    description "The number of allow-list URL lookups that matched and were allowed.";
                                }

                            } // container allow-list

                        } // container statistics

                    } // container local-filtering

                    container icap {
                        description "Enter the icap context";

                        container statistics {
                            description "Enter the statistics context";

                            leaf late-response {
                                type yang:counter64;
                                description "The number of times the HTTP response was received prior to the ICAP response.";
                            }

                            leaf late-response-packets-discarded {
                                type yang:counter64;
                                description "The number of packets dropped while waiting for an ICAP response.";
                            }

                            leaf late-response-octets-discarded {
                                type yang:counter64;
                                description "The number of bytes dropped while waiting for an ICAP response.";
                            }

                            leaf default-action {
                                type yang:counter64;
                                description
                                    "The number of times the ICAP url-filter took the default-action due
                                     to the url filter's inability to send the request to the ICAP server
                                     or due to receiving a malformed response from it.";
                            }

                        } // container statistics

                    } // container icap

                    container web-service {
                        description "Enter the web-service context";

                        leaf cache-entries {
                            type yang:gauge32;
                            description "The current number of cache entries in use for url-filtering web-service.";
                        }

                        leaf cache-entries-maximum {
                            type uint32;
                            description
                                "The maximum number of cache entries that can be allocated per URL filter providing
                                 web-service per ISA.";
                        }

                        leaf connections-established {
                            type yang:gauge32;
                            description "The current number of TCP connections which are established with the web-service server.";
                        }

                        leaf connections-maximum {
                            type uint32;
                            description "The maximum number of TCP connections which can be established with the web-service server.";
                        }

                        leaf dns-oper-state {
                            type types-sros:oper-state;
                            description "The operational state of DNS resolution for the web-service FQDN.";
                        }

                        leaf dns-oper-flags {
                            type bits {
                                bit notApplicable                  { position 0; }
                                bit filterAdminDown                { position 1; }
                                bit noAaIf                         { position 2; }
                                bit aaIfDown                       { position 3; }
                                bit dnsDown                        { position 4; }
                                bit lookUpFailure                  { position 5; }
                                bit unreachable                    { position 6; }
                            }
                            description "The different conditions that affect the operating status of the web-service DNS resolution.";
                        }

                        leaf request-rate {
                            type yang:gauge32;
                            description "The average number of web-service requests sent per second over the last 10 second period.";
                        }

                        leaf round-trip-time {
                            type yang:gauge32;
                            units "microseconds";
                            description "The average amount of time it took to receive web-service Responses over the last 10 second period.";
                        }

                        container statistics {
                            description "Enter the statistics context";

                            leaf requests {
                                type yang:counter64;
                                description "The number of web service requests which have been sent to the web-service server.";
                            }

                            leaf request-errors {
                                type yang:counter64;
                                description "The number of web service requests that were unable to be sent to the web-service server.";
                            }

                            leaf late-response {
                                type yang:counter64;
                                description "The number of times the HTTP response was received prior to the web-service server response.";
                            }

                            leaf late-response-packets-discarded {
                                type yang:counter64;
                                description "The number of packets dropped while waiting for a web-service response.";
                            }

                            leaf late-response-octets-discarded {
                                type yang:counter64;
                                description "The number of bytes dropped while waiting for a web-service response.";
                            }

                            leaf cache-hit {
                                type yang:counter64;
                                description "The number of cache hits while performing url category classification requests.";
                            }

                            leaf cache-miss {
                                type yang:counter64;
                                description "The number of cache misses while performing url category classification requests.";
                            }

                            leaf override-hit {
                                type yang:counter64;
                                description "The number of URL lookups that matched entries in the classification override entries.";
                            }

                            leaf override-miss {
                                type yang:counter64;
                                description "The number of URL lookups that missed entries in the classification override entries.";
                            }

                            container result {
                                description "Enter the result context";

                                leaf allow {
                                    type yang:counter64;
                                    description "The number of web-service classifications which allowed the url for the subscriber's profile.";
                                }

                                leaf block {
                                    type yang:counter64;
                                    description "The number of web-service classifications which blocked the url for the subscriber's profile.";
                                }

                                leaf redirect {
                                    type yang:counter64;
                                    description "The number of web-service classifications which redirected the url for the subscriber's profile.";
                                }

                                leaf default-action {
                                    type yang:counter64;
                                    description
                                        "The number of times the web-service url-filter took the default-action due
                                         to the url filter's inability to send the request to the web-service server
                                         or due to receiving a malformed response from the web-service server.";
                                }

                            } // container result

                        } // container statistics

                    } // container web-service

                } // list esa

                list isa {
                    key "mda-id";
                    description "Enter the isa list instance";

                    leaf mda-id {
                        type types-isa:slot-mda;
                        description "MDA/ISA ID";
                    }

                    leaf oper-state {
                        type types-sros:oper-state;
                        description "The operational state of the URL Filter.";
                    }

                    leaf oper-flags {
                        type bits {
                            bit admin-down                     { position 0; }
                            bit no-aa-interface                { position 1; }
                            bit aa-interface-down              { position 2; }
                            bit icap-server-down               { position 3; }
                            bit url-list-down                  { position 4; }
                            bit web-service-down               { position 5; }
                        }
                        description "The conditions that affect the operating status of the URL Filter";
                    }

                    container statistics {
                        description "Enter the statistics context";

                        leaf client-requests {
                            type yang:counter64;
                            description
                                "The number of URL requests made by clients to web servers that were
                                 analyzed by the url-filter.";
                        }

                        leaf client-request-errors {
                            type yang:counter64;
                            description "The number of times the URL request was unable to be analyzed.";
                        }

                        leaf server-response-allow {
                            type yang:counter64;
                            description
                                "The number of URL responses from web servers to clients that were
                                 allowed based on the url-filter analysis of the client-request
                                 resulting in a url-allow decision.";
                        }

                        leaf server-response-redirect {
                            type yang:counter64;
                            description
                                "The number of URL responses from web servers to clients that were
                                 redirected based on the url-filter analysis of the client-request
                                 resulting in a url-block-redirect decision and the conversation
                                 being redirectable.";
                        }

                        leaf server-response-block {
                            type yang:counter64;
                            description
                                "The number of URL responses from web servers to clients that were
                                 blocked or TCP reset based on the url-filter analysis of the client-request
                                 resulting in a url-block-redirect decision and the conversation
                                 not being redirectable.";
                        }

                        leaf server-response-default {
                            type yang:counter64;
                            description
                                "The number of URL responses from web servers to clients that took
                                 a default-actions based on the url-filter analysis of the client-request
                                 resulting in a url-default-action decision.";
                        }

                        leaf url-allow {
                            type yang:counter64;
                            description
                                "The total number of URL lookup requests that resulted in an 'allow'
                                 decision by the url-filter.";
                        }

                        leaf url-block-redirect {
                            type yang:counter64;
                            description
                                "The total number of URL lookup requests that resulted in a 'redirect'
                                 or 'block' decision by the last filtering function within the url-filter.";
                        }

                        leaf url-default-action {
                            type yang:counter64;
                            description
                                "The total number of URL lookup requests that resulted in a 'default-action'
                                 decision by the last filtering function within the url-filter.";
                        }

                    } // container statistics

                    container local-filtering {
                        description "Enter the local-filtering context";

                        container statistics {
                            description "Enter the statistics context";

                            container allow-list {
                                description "Enter the allow-list context";

                                leaf lookup {
                                    type yang:counter64;
                                    description "The number of allow-list URL lookups.";
                                }

                                leaf match {
                                    type yang:counter64;
                                    description "The number of allow-list URL lookups that matched and were allowed.";
                                }

                            } // container allow-list

                        } // container statistics

                    } // container local-filtering

                    container icap {
                        description "Enter the icap context";

                        container statistics {
                            description "Enter the statistics context";

                            leaf late-response {
                                type yang:counter64;
                                description "The number of times the HTTP response was received prior to the ICAP response.";
                            }

                            leaf late-response-packets-discarded {
                                type yang:counter64;
                                description "The number of packets dropped while waiting for an ICAP response.";
                            }

                            leaf late-response-octets-discarded {
                                type yang:counter64;
                                description "The number of bytes dropped while waiting for an ICAP response.";
                            }

                            leaf default-action {
                                type yang:counter64;
                                description
                                    "The number of times the ICAP url-filter took the default-action due
                                     to the url filter's inability to send the request to the ICAP server
                                     or due to receiving a malformed response from it.";
                            }

                        } // container statistics

                    } // container icap

                    container web-service {
                        description "Enter the web-service context";

                        leaf cache-entries {
                            type yang:gauge32;
                            description "The current number of cache entries in use for url-filtering web-service.";
                        }

                        leaf cache-entries-maximum {
                            type uint32;
                            description
                                "The maximum number of cache entries that can be allocated per URL filter providing
                                 web-service per ISA.";
                        }

                        leaf connections-established {
                            type yang:gauge32;
                            description "The current number of TCP connections which are established with the web-service server.";
                        }

                        leaf connections-maximum {
                            type uint32;
                            description "The maximum number of TCP connections which can be established with the web-service server.";
                        }

                        leaf dns-oper-state {
                            type types-sros:oper-state;
                            description "The operational state of DNS resolution for the web-service FQDN.";
                        }

                        leaf dns-oper-flags {
                            type bits {
                                bit notApplicable                  { position 0; }
                                bit filterAdminDown                { position 1; }
                                bit noAaIf                         { position 2; }
                                bit aaIfDown                       { position 3; }
                                bit dnsDown                        { position 4; }
                                bit lookUpFailure                  { position 5; }
                                bit unreachable                    { position 6; }
                            }
                            description "The different conditions that affect the operating status of the web-service DNS resolution.";
                        }

                        leaf request-rate {
                            type yang:gauge32;
                            description "The average number of web-service requests sent per second over the last 10 second period.";
                        }

                        leaf round-trip-time {
                            type yang:gauge32;
                            units "microseconds";
                            description "The average amount of time it took to receive web-service Responses over the last 10 second period.";
                        }

                        container statistics {
                            description "Enter the statistics context";

                            leaf requests {
                                type yang:counter64;
                                description "The number of web service requests which have been sent to the web-service server.";
                            }

                            leaf request-errors {
                                type yang:counter64;
                                description "The number of web service requests that were unable to be sent to the web-service server.";
                            }

                            leaf late-response {
                                type yang:counter64;
                                description "The number of times the HTTP response was received prior to the web-service server response.";
                            }

                            leaf late-response-packets-discarded {
                                type yang:counter64;
                                description "The number of packets dropped while waiting for a web-service response.";
                            }

                            leaf late-response-octets-discarded {
                                type yang:counter64;
                                description "The number of bytes dropped while waiting for a web-service response.";
                            }

                            leaf cache-hit {
                                type yang:counter64;
                                description "The number of cache hits while performing url category classification requests.";
                            }

                            leaf cache-miss {
                                type yang:counter64;
                                description "The number of cache misses while performing url category classification requests.";
                            }

                            leaf override-hit {
                                type yang:counter64;
                                description "The number of URL lookups that matched entries in the classification override entries.";
                            }

                            leaf override-miss {
                                type yang:counter64;
                                description "The number of URL lookups that missed entries in the classification override entries.";
                            }

                            container result {
                                description "Enter the result context";

                                leaf allow {
                                    type yang:counter64;
                                    description "The number of web-service classifications which allowed the url for the subscriber's profile.";
                                }

                                leaf block {
                                    type yang:counter64;
                                    description "The number of web-service classifications which blocked the url for the subscriber's profile.";
                                }

                                leaf redirect {
                                    type yang:counter64;
                                    description "The number of web-service classifications which redirected the url for the subscriber's profile.";
                                }

                                leaf default-action {
                                    type yang:counter64;
                                    description
                                        "The number of times the web-service url-filter took the default-action due
                                         to the url filter's inability to send the request to the web-service server
                                         or due to receiving a malformed response from the web-service server.";
                                }

                            } // container result

                        } // container statistics

                    } // container web-service

                } // list isa

                container summary {
                    description "Enter the summary context";

                    leaf oper-state {
                        type types-sros:oper-state;
                        description "The operational state of the URL Filter.";
                    }

                    leaf oper-flags {
                        type bits {
                            bit admin-down                     { position 0; }
                            bit no-aa-interface                { position 1; }
                            bit aa-interface-down              { position 2; }
                            bit icap-server-down               { position 3; }
                            bit url-list-down                  { position 4; }
                            bit web-service-down               { position 5; }
                        }
                        description "The conditions that affect the operating status of the URL Filter";
                    }

                    container statistics {
                        description "Enter the statistics context";

                        leaf client-requests {
                            type yang:counter64;
                            description
                                "The number of URL requests made by clients to web servers that were
                                 analyzed by the url-filter.";
                        }

                        leaf client-request-errors {
                            type yang:counter64;
                            description "The number of times the URL request was unable to be analyzed.";
                        }

                        leaf server-response-allow {
                            type yang:counter64;
                            description
                                "The number of URL responses from web servers to clients that were
                                 allowed based on the url-filter analysis of the client-request
                                 resulting in a url-allow decision.";
                        }

                        leaf server-response-redirect {
                            type yang:counter64;
                            description
                                "The number of URL responses from web servers to clients that were
                                 redirected based on the url-filter analysis of the client-request
                                 resulting in a url-block-redirect decision and the conversation
                                 being redirectable.";
                        }

                        leaf server-response-block {
                            type yang:counter64;
                            description
                                "The number of URL responses from web servers to clients that were
                                 blocked or TCP reset based on the url-filter analysis of the client-request
                                 resulting in a url-block-redirect decision and the conversation
                                 not being redirectable.";
                        }

                        leaf server-response-default {
                            type yang:counter64;
                            description
                                "The number of URL responses from web servers to clients that took
                                 a default-actions based on the url-filter analysis of the client-request
                                 resulting in a url-default-action decision.";
                        }

                        leaf url-allow {
                            type yang:counter64;
                            description
                                "The total number of URL lookup requests that resulted in an 'allow'
                                 decision by the url-filter.";
                        }

                        leaf url-block-redirect {
                            type yang:counter64;
                            description
                                "The total number of URL lookup requests that resulted in a 'redirect'
                                 or 'block' decision by the last filtering function within the url-filter.";
                        }

                        leaf url-default-action {
                            type yang:counter64;
                            description
                                "The total number of URL lookup requests that resulted in a 'default-action'
                                 decision by the last filtering function within the url-filter.";
                        }

                    } // container statistics

                    container local-filtering {
                        description "Enter the local-filtering context";

                        container statistics {
                            description "Enter the statistics context";

                            container allow-list {
                                description "Enter the allow-list context";

                                leaf lookup {
                                    type yang:counter64;
                                    description "The number of allow-list URL lookups.";
                                }

                                leaf match {
                                    type yang:counter64;
                                    description "The number of allow-list URL lookups that matched and were allowed.";
                                }

                            } // container allow-list

                        } // container statistics

                    } // container local-filtering

                    container icap {
                        description "Enter the icap context";

                        container statistics {
                            description "Enter the statistics context";

                            leaf late-response {
                                type yang:counter64;
                                description "The number of times the HTTP response was received prior to the ICAP response.";
                            }

                            leaf late-response-packets-discarded {
                                type yang:counter64;
                                description "The number of packets dropped while waiting for an ICAP response.";
                            }

                            leaf late-response-octets-discarded {
                                type yang:counter64;
                                description "The number of bytes dropped while waiting for an ICAP response.";
                            }

                            leaf default-action {
                                type yang:counter64;
                                description
                                    "The number of times the ICAP url-filter took the default-action due
                                     to the url filter's inability to send the request to the ICAP server
                                     or due to receiving a malformed response from it.";
                            }

                        } // container statistics

                    } // container icap

                    container web-service {
                        description "Enter the web-service context";

                        leaf cache-entries {
                            type yang:gauge32;
                            description "The current number of cache entries in use for url-filtering web-service.";
                        }

                        leaf cache-entries-maximum {
                            type uint32;
                            description
                                "The maximum number of cache entries that can be allocated per URL filter providing
                                 web-service per ISA.";
                        }

                        leaf connections-established {
                            type yang:gauge32;
                            description "The current number of TCP connections which are established with the web-service server.";
                        }

                        leaf connections-maximum {
                            type uint32;
                            description "The maximum number of TCP connections which can be established with the web-service server.";
                        }

                        leaf dns-oper-state {
                            type types-sros:oper-state;
                            description "The operational state of DNS resolution for the web-service FQDN.";
                        }

                        leaf dns-oper-flags {
                            type bits {
                                bit notApplicable                  { position 0; }
                                bit filterAdminDown                { position 1; }
                                bit noAaIf                         { position 2; }
                                bit aaIfDown                       { position 3; }
                                bit dnsDown                        { position 4; }
                                bit lookUpFailure                  { position 5; }
                                bit unreachable                    { position 6; }
                            }
                            description "The different conditions that affect the operating status of the web-service DNS resolution.";
                        }

                        leaf request-rate {
                            type yang:gauge32;
                            description "The average number of web-service requests sent per second over the last 10 second period.";
                        }

                        leaf round-trip-time {
                            type yang:gauge32;
                            units "microseconds";
                            description "The average amount of time it took to receive web-service Responses over the last 10 second period.";
                        }

                        container statistics {
                            description "Enter the statistics context";

                            leaf requests {
                                type yang:counter64;
                                description "The number of web service requests which have been sent to the web-service server.";
                            }

                            leaf request-errors {
                                type yang:counter64;
                                description "The number of web service requests that were unable to be sent to the web-service server.";
                            }

                            leaf late-response {
                                type yang:counter64;
                                description "The number of times the HTTP response was received prior to the web-service server response.";
                            }

                            leaf late-response-packets-discarded {
                                type yang:counter64;
                                description "The number of packets dropped while waiting for a web-service response.";
                            }

                            leaf late-response-octets-discarded {
                                type yang:counter64;
                                description "The number of bytes dropped while waiting for a web-service response.";
                            }

                            leaf cache-hit {
                                type yang:counter64;
                                description "The number of cache hits while performing url category classification requests.";
                            }

                            leaf cache-miss {
                                type yang:counter64;
                                description "The number of cache misses while performing url category classification requests.";
                            }

                            leaf override-hit {
                                type yang:counter64;
                                description "The number of URL lookups that matched entries in the classification override entries.";
                            }

                            leaf override-miss {
                                type yang:counter64;
                                description "The number of URL lookups that missed entries in the classification override entries.";
                            }

                            container result {
                                description "Enter the result context";

                                leaf allow {
                                    type yang:counter64;
                                    description "The number of web-service classifications which allowed the url for the subscriber's profile.";
                                }

                                leaf block {
                                    type yang:counter64;
                                    description "The number of web-service classifications which blocked the url for the subscriber's profile.";
                                }

                                leaf redirect {
                                    type yang:counter64;
                                    description "The number of web-service classifications which redirected the url for the subscriber's profile.";
                                }

                                leaf default-action {
                                    type yang:counter64;
                                    description
                                        "The number of times the web-service url-filter took the default-action due
                                         to the url filter's inability to send the request to the web-service server
                                         or due to receiving a malformed response from the web-service server.";
                                }

                            } // container result

                        } // container statistics

                    } // container web-service

                } // container summary

                container local-filtering {
                    description "Enter the local-filtering context";

                    list deny-list {
                        key "url-list-name";
                        description "Enter the deny-list list instance";

                        leaf url-list-name {
                            type leafref {
                                path "../../../../url-list/url-list-name";
                            }
                            description "URL list name";
                        }

                        list esa {
                            key "esa-id vm";
                            description "Enter the esa list instance";

                            leaf esa-id {
                                type types-esa:esa-id;
                                description "ESA ID";
                            }

                            leaf vm {
                                type types-esa:vm-id;
                                description "VM ID within the ESA";
                            }

                            container statistics {
                                description "Enter the statistics context";

                                leaf lookup {
                                    type yang:counter64;
                                    description "The number of url-list URL lookups.";
                                }

                                leaf match {
                                    type yang:counter64;
                                    description "The number of url-list URL lookups that matched and were blocked/redirected.";
                                }

                                leaf default-action {
                                    type yang:counter64;
                                    description "The number of url-list URL lookups that could not be performed and took the default-action.";
                                }

                            } // container statistics

                        } // list esa

                        list isa {
                            key "mda-id";
                            description "Enter the isa list instance";

                            leaf mda-id {
                                type types-isa:slot-mda;
                                description "MDA/ISA ID";
                            }

                            container statistics {
                                description "Enter the statistics context";

                                leaf lookup {
                                    type yang:counter64;
                                    description "The number of url-list URL lookups.";
                                }

                                leaf match {
                                    type yang:counter64;
                                    description "The number of url-list URL lookups that matched and were blocked/redirected.";
                                }

                                leaf default-action {
                                    type yang:counter64;
                                    description "The number of url-list URL lookups that could not be performed and took the default-action.";
                                }

                            } // container statistics

                        } // list isa

                        container summary {
                            description "Enter the summary context";

                            container statistics {
                                description "Enter the statistics context";

                                leaf lookup {
                                    type yang:counter64;
                                    description "The number of url-list URL lookups.";
                                }

                                leaf match {
                                    type yang:counter64;
                                    description "The number of url-list URL lookups that matched and were blocked/redirected.";
                                }

                                leaf default-action {
                                    type yang:counter64;
                                    description "The number of url-list URL lookups that could not be performed and took the default-action.";
                                }

                            } // container statistics

                        } // container summary

                    } // list deny-list

                } // container local-filtering

                container icap {
                    description "Enter the icap context";

                    list server {
                        key "ip-address port";
                        description "Enter the server list instance";

                        leaf ip-address {
                            type types-sros:ip-unicast-address;
                            description "ICAP server IP address";
                        }

                        leaf port {
                            type types-sros:tcp-udp-port-non-zero;
                            description "ICAP server port";
                        }

                        list esa {
                            key "esa-id vm";
                            description "Enter the esa list instance";

                            leaf esa-id {
                                type types-esa:esa-id;
                                description "ESA ID";
                            }

                            leaf vm {
                                type types-esa:vm-id;
                                description "VM ID within the ESA";
                            }

                            leaf oper-state {
                                type types-sros:oper-state;
                                description "The operational state of the ICAP server.";
                            }

                            leaf oper-flags {
                                type bits {
                                    bit admin-down                     { position 0; }
                                    bit tcp-conn-error                 { position 1; }
                                }
                                description "The different conditions that affect the operating status of an ICAP server.";
                            }

                            leaf allowed-connections {
                                type uint32;
                                description "The maximum number of TCP connections which can be established with the ICAP server.";
                            }

                            container statistics {
                                description "Enter the statistics context";

                                leaf established-connections {
                                    type yang:gauge32;
                                    description "The current number of TCP connections which are established with the ICAP server.";
                                }

                                leaf connection-utilization {
                                    type yang:gauge32 {
                                        range "0..100";
                                    }
                                    units "percent";
                                    description "The percentage of TCP connections utilized over the last 10 second period.";
                                }

                                leaf round-trip-time {
                                    type yang:gauge32;
                                    units "microseconds";
                                    description "The average amount of time it took to receive ICAP Responses over the last 10 second period.";
                                }

                                leaf request-rate {
                                    type yang:gauge32;
                                    description "The average number of ICAP requests sent per second over the last 10 second period.";
                                }

                                leaf icap-requests {
                                    type yang:counter64;
                                    description "The number of HTTP requests received.";
                                }

                                leaf icap-request-errors {
                                    type yang:counter64;
                                    description "The number of times the HTTP request that were unable to be sent to the ICAP server.";
                                }

                                container icap-response {
                                    description "Enter the icap-response context";

                                    leaf allow {
                                        type yang:counter64;
                                        description "The number of ICAP allow responses which have been received from the ICAP server.";
                                    }

                                    leaf block {
                                        type yang:counter64;
                                        description "The number of ICAP block responses which have been received from the ICAP server.";
                                    }

                                    leaf redirect {
                                        type yang:counter64;
                                        description "The number of ICAP redirect responses which have been received from the ICAP server.";
                                    }

                                } // container icap-response

                            } // container statistics

                        } // list esa

                        list isa {
                            key "mda-id";
                            description "Enter the isa list instance";

                            leaf mda-id {
                                type types-isa:slot-mda;
                                description "MDA/ISA ID";
                            }

                            leaf oper-state {
                                type types-sros:oper-state;
                                description "The operational state of the ICAP server.";
                            }

                            leaf oper-flags {
                                type bits {
                                    bit admin-down                     { position 0; }
                                    bit tcp-conn-error                 { position 1; }
                                }
                                description "The different conditions that affect the operating status of an ICAP server.";
                            }

                            leaf allowed-connections {
                                type uint32;
                                description "The maximum number of TCP connections which can be established with the ICAP server.";
                            }

                            container statistics {
                                description "Enter the statistics context";

                                leaf established-connections {
                                    type yang:gauge32;
                                    description "The current number of TCP connections which are established with the ICAP server.";
                                }

                                leaf connection-utilization {
                                    type yang:gauge32 {
                                        range "0..100";
                                    }
                                    units "percent";
                                    description "The percentage of TCP connections utilized over the last 10 second period.";
                                }

                                leaf round-trip-time {
                                    type yang:gauge32;
                                    units "microseconds";
                                    description "The average amount of time it took to receive ICAP Responses over the last 10 second period.";
                                }

                                leaf request-rate {
                                    type yang:gauge32;
                                    description "The average number of ICAP requests sent per second over the last 10 second period.";
                                }

                                leaf icap-requests {
                                    type yang:counter64;
                                    description "The number of HTTP requests received.";
                                }

                                leaf icap-request-errors {
                                    type yang:counter64;
                                    description "The number of times the HTTP request that were unable to be sent to the ICAP server.";
                                }

                                container icap-response {
                                    description "Enter the icap-response context";

                                    leaf allow {
                                        type yang:counter64;
                                        description "The number of ICAP allow responses which have been received from the ICAP server.";
                                    }

                                    leaf block {
                                        type yang:counter64;
                                        description "The number of ICAP block responses which have been received from the ICAP server.";
                                    }

                                    leaf redirect {
                                        type yang:counter64;
                                        description "The number of ICAP redirect responses which have been received from the ICAP server.";
                                    }

                                } // container icap-response

                            } // container statistics

                        } // list isa

                        container summary {
                            description "Enter the summary context";

                            leaf oper-state {
                                type types-sros:oper-state;
                                description "The operational state of the ICAP server.";
                            }

                            leaf oper-flags {
                                type bits {
                                    bit admin-down                     { position 0; }
                                    bit tcp-conn-error                 { position 1; }
                                }
                                description "The different conditions that affect the operating status of an ICAP server.";
                            }

                            leaf allowed-connections {
                                type uint32;
                                description "The maximum number of TCP connections which can be established with the ICAP server.";
                            }

                            container statistics {
                                description "Enter the statistics context";

                                leaf established-connections {
                                    type yang:gauge32;
                                    description "The current number of TCP connections which are established with the ICAP server.";
                                }

                                leaf connection-utilization {
                                    type yang:gauge32 {
                                        range "0..100";
                                    }
                                    units "percent";
                                    description "The percentage of TCP connections utilized over the last 10 second period.";
                                }

                                leaf round-trip-time {
                                    type yang:gauge32;
                                    units "microseconds";
                                    description "The average amount of time it took to receive ICAP Responses over the last 10 second period.";
                                }

                                leaf request-rate {
                                    type yang:gauge32;
                                    description "The average number of ICAP requests sent per second over the last 10 second period.";
                                }

                                leaf icap-requests {
                                    type yang:counter64;
                                    description "The number of HTTP requests received.";
                                }

                                leaf icap-request-errors {
                                    type yang:counter64;
                                    description "The number of times the HTTP request that were unable to be sent to the ICAP server.";
                                }

                                container icap-response {
                                    description "Enter the icap-response context";

                                    leaf allow {
                                        type yang:counter64;
                                        description "The number of ICAP allow responses which have been received from the ICAP server.";
                                    }

                                    leaf block {
                                        type yang:counter64;
                                        description "The number of ICAP block responses which have been received from the ICAP server.";
                                    }

                                    leaf redirect {
                                        type yang:counter64;
                                        description "The number of ICAP redirect responses which have been received from the ICAP server.";
                                    }

                                } // container icap-response

                            } // container statistics

                        } // container summary

                    } // list server

                } // container icap

            } // list url-filter

            container policer {
                description "Enter the policer context";

                list dual-bucket-bandwidth-policer {
                    key "policer-name";
                    description "Enter the dual-bucket-bandwidth-policer list instance";

                    leaf policer-name {
                        type types-sros:named-item;
                        description "Policer name";
                    }

                    leaf oper-mbs {
                        type types-aa:policer-burst-size;
                        description "The current operational maximum burst size (MBS) value.";
                    }

                    leaf oper-pir {
                        type types-aa:policer-ir;
                        description "The current operational peak information rate (PIR) value.";
                    }

                    leaf oper-cbs {
                        type types-aa:policer-burst-size;
                        description "The current operational committed burst size when the ANL, to which the subscriber belongs, is in a congested state.";
                    }

                    leaf oper-cir {
                        type types-aa:policer-cir;
                        description "The current operational committed information rate (CIR) value.";
                    }

                } // list dual-bucket-bandwidth-policer

                list flow-count-limit-policer {
                    key "policer-name";
                    description "Enter the flow-count-limit-policer list instance";

                    leaf policer-name {
                        type types-sros:named-item;
                        description "Policer name";
                    }

                    leaf oper-peak-flow-count {
                        type types-aa:policer-flow-count-limit;
                        description "The current operational peak flow count limit value.";
                    }

                } // list flow-count-limit-policer

                list flow-setup-rate-policer {
                    key "policer-name";
                    description "Enter the flow-setup-rate-policer list instance";

                    leaf policer-name {
                        type types-sros:named-item;
                        description "Policer name";
                    }

                    leaf oper-peak-flow-setup-rate {
                        type types-aa:policer-flow-rate;
                        description "The current operational peak flow rate value.";
                    }

                    leaf oper-flow-setup-rate-burst-size {
                        type types-aa:policer-flow-burst-size;
                        description "The current operational maximum flow burst value.";
                    }

                } // list flow-setup-rate-policer

                list single-bucket-bandwidth-policer {
                    key "policer-name";
                    description "Enter the single-bucket-bandwidth-policer list instance";

                    leaf policer-name {
                        type types-sros:named-item;
                        description "Policer name";
                    }

                    leaf oper-mbs {
                        type types-aa:policer-burst-size;
                        description "The current operational maximum burst size (MBS) value.";
                    }

                    leaf oper-pir {
                        type types-aa:policer-ir;
                        description "The current operational peak information rate (PIR) value.";
                    }

                } // list single-bucket-bandwidth-policer

            } // container policer

            list partition {
                key "aa-partition-id";
                description "Enter the partition list instance";

                leaf aa-partition-id {
                    type types-aa:aa-grp-part-id;
                    description "Partition ID within the AA group";
                }

                list aa-sub {
                    key "aa-sub-type aa-sub-name";
                    description "Enter the aa-sub list instance";

                    leaf aa-sub-type {
                        type types-aa:stats-aa-sub-type;
                        description "Specifies the AA subscriber type for statistics.";
                    }

                    leaf aa-sub-name {
                        type union {
                            type types-sros:sap;
                            type types-services:sdp-bind-id;
                            type types-sros:named-item;
                        }
                        description "Specifies AA subscriber identifier string.";
                    }

                    leaf has-overrides {
                        type boolean;
                        description "Indicates if the subscriber has policy overrides.";
                    }

                    leaf circuit-id {
                        type types-sros:display-string-or-empty {
                            length "0..64";
                        }
                        description "Indicates if the subscriber has policy overrides.";
                    }

                    leaf remote-id {
                        type types-sros:display-string-or-empty {
                            length "0..64";
                        }
                        description "Indicates if the subscriber has policy overrides.";
                    }

                    leaf isa-assigned {
                        type types-isa:slot-mda;
                        description "Specifies an MDA/ISA identifier <card slot number>/<mda slot number>";
                    }

                    leaf esa-assigned {
                        type types-esa:esa-id;
                        description "Specifies an ESA identifier";
                    }

                    leaf esa-vm-assigned {
                        type types-esa:vm-id;
                        description "Specifies an ESA VM identifier";
                    }

                    leaf app-profile-name {
                        type types-sros:named-item;
                        description "The name of the ISA-AA application profile associated with the subscriber.";
                    }

                    leaf aarp-id {
                        type types-services:bsx-aarp-id;
                        description "The AARP instance id to which this subscriber belongs.";
                    }

                    leaf quarantined {
                        type boolean;
                        description "Indicates if the subscriber is currently quarantined.";
                    }

                    leaf http-url-parameters {
                        type types-sros:http-redirect-url {
                            length "1..32";
                        }
                        description "The HTTP URL Parameters associated with this subscriber.";
                    }

                    leaf last-http-notified {
                        type yang:date-and-time;
                        description "Indicates when the last HTTP Notification occurred for this subscriber.";
                    }

                    leaf sap {
                        type types-sros:sap;
                        description "The VLAN ID on which the ISA-AA is expected to be emitting traffic.";
                    }

                    leaf mac {
                        type yang:mac-address;
                        description "The MAC address of the subscriber.";
                    }

                    leaf transit-ip-policy-id {
                        type uint32 {
                            range "1..65535";
                        }
                        description "Specifies the transit ip policy to which this subscriber belongs.";
                    }

                    leaf transit-prefix-policy-id {
                        type uint32 {
                            range "1..65535";
                        }
                        description "Specifies the transit prefix policy to which this subscriber belongs.";
                    }

                    leaf imsi {
                        type types-sros:display-string-or-empty {
                            length "0..15";
                        }
                        description "Indicates the International Mobile Subscriber Identity (IMSI) of this subscriber.";
                    }

                    leaf imei {
                        type types-sros:display-string-or-empty {
                            length "0..16";
                        }
                        description "Indicates the International Mobile Equipment Identity (IMEI) of this subscriber.";
                    }

                    leaf msisdn {
                        type types-sros:display-string-or-empty {
                            length "0..15";
                        }
                        description "Indicates the Mobile Subscriber Integrated Services Digital Network (MSISDN) number of this subscriber.";
                    }

                    leaf apn {
                        type types-sros:display-string-or-empty {
                            length "0..100";
                        }
                        description "Indicates the Access Point Name (APN) of this subscriber.";
                    }

                    leaf user-location {
                        type types-sros:display-string-or-empty {
                            length "0..255";
                        }
                        description "Indicates the mobile User Location Information (ULI) of this subscriber.";
                    }

                    leaf rat-type {
                        type types-aa:mobile-rat-type;
                        description "Indicates the Radio Access Technology (RAT) type of this subscriber";
                    }

                    leaf charging-id {
                        type uint32;
                        description "Indicates the mobile charging ID of this subscriber.";
                    }

                    leaf billing-type {
                        type uint32;
                        description "Indicates the mobile billing type of this subscriber.";
                    }

                    leaf plmn-id {
                        type uint32;
                        description "Indicates the Public Land Mobile Network (PLMN) of this subscriber.";
                    }

                    leaf pdn-gateway-addr {
                        type types-sros:ip-address;
                        description "Indicates the address of the connected PDN gateway interface of this subscriber.";
                    }

                    leaf pdn-gateway-addr-type {
                        type enumeration {
                            enum "unknown"                      { value 0; }
                            enum "ipv4"                         { value 1; }
                            enum "ipv6"                         { value 2; }
                            enum "ipv4z"                        { value 3; }
                            enum "ipv6z"                        { value 4; }
                            enum "dns"                          { value 16; }
                        }
                        description "Indicates the type of pdn-gateway-addr of this subscriber.";
                    }

                    list characteristic {
                        key "characteristic-name";
                        description "Enter the characteristic list instance";

                        leaf characteristic-name {
                            type types-sros:named-item;
                            description "Specifies an AA partition policy ASO characteristic name.";
                        }

                        leaf value {
                            type types-sros:named-item;
                            description "Specifies an AA partition policy ASO characteristic name.";
                        }

                        leaf derived-from {
                            type types-aa:aso-val-derived-from;
                            description "Indicates from where the characteristic value is derived from for the Application Assurance subscriber.";
                        }

                    } // list characteristic

                    list policer {
                        key "policer-type direction index";
                        description "Enter the policer list instance";

                        leaf policer-type {
                            type types-aa:policer-type;
                            description
                                "Indicates if the policer being applied to the subscriber is a bandwidth,
                                 flow rate, or a flow count policer.";
                        }

                        leaf direction {
                            type types-aa:traffic-direction;
                            description "The traffic direction of the policer being applied to the subscriber.";
                        }

                        leaf index {
                            type uint32 {
                                range "1..4096";
                            }
                            description "Indicates the index into a list of policers being applied to the subscriber.";
                        }

                        leaf applied-policer {
                            type types-sros:named-item;
                            description "The policer name being applied to the subscriber.";
                        }

                        leaf aqp-entry {
                            type uint32 {
                                range "1..max";
                            }
                            description "The entry-id that references the policer.";
                        }

                    } // list policer

                    list statistics-scope {
                        key "stats-scope";
                        description "Enter the statistics-scope list instance";

                        leaf stats-scope {
                            type types-aa:stats-scope;
                            description "Specifies to provide stats from most recent snapshot of closed flows or all-flows including realtime information from active flows.";
                        }

                        leaf tethering-state {
                            type types-aa:sub-tether-state;
                            description "The tethering state of an Application Assurance Subscriber.";
                        }

                        container statistics {
                            description "Enter the statistics context";

                            container sub-to-net {
                                description "Enter the sub-to-net context";

                                leaf active-flows {
                                    type yang:counter32;
                                    description "Number of allowed flows in the subscriber to network direction that are active.";
                                }

                                container admitted {
                                    description "Enter the admitted context";

                                    leaf octets {
                                        type yang:counter64;
                                        description "Number of bytes permitted for the subscriber to network direction.";
                                    }

                                    leaf packets {
                                        type yang:counter64;
                                        description "Number of packets permitted for the subscriber to network direction.";
                                    }

                                    leaf flows {
                                        type yang:counter64;
                                        description "Number of flows permitted for the subscriber to network direction.";
                                    }

                                } // container admitted

                                container denied {
                                    description "Enter the denied context";

                                    leaf octets {
                                        type yang:counter64;
                                        description "Number of bytes dropped for the subscriber to network direction.";
                                    }

                                    leaf packets {
                                        type yang:counter64;
                                        description "Number of packets dropped for the subscriber to network direction.";
                                    }

                                    leaf flows {
                                        type yang:counter64;
                                        description "Number of flows that dropped subsequent packets in the subscriber to network direction.";
                                    }

                                } // container denied

                            } // container sub-to-net

                            container net-to-sub {
                                description "Enter the net-to-sub context";

                                leaf active-flows {
                                    type yang:counter32;
                                    description "Number of allowed flows in the network to subscriber direction that are active.";
                                }

                                container admitted {
                                    description "Enter the admitted context";

                                    leaf octets {
                                        type yang:counter64;
                                        description "Number of bytes permitted for the network to subscriber direction.";
                                    }

                                    leaf packets {
                                        type yang:counter64;
                                        description "Number of packets permitted for the network to subscriber direction.";
                                    }

                                    leaf flows {
                                        type yang:counter64;
                                        description "Number of flows permitted for the network to subscriber direction.";
                                    }

                                } // container admitted

                                container denied {
                                    description "Enter the denied context";

                                    leaf octets {
                                        type yang:counter64;
                                        description "Number of bytes dropped for the network to subscriber direction.";
                                    }

                                    leaf packets {
                                        type yang:counter64;
                                        description "Number of packets dropped for the network to subscriber direction.";
                                    }

                                    leaf flows {
                                        type yang:counter64;
                                        description "Number of flows that dropped subsequent packets in the network to subscriber direction.";
                                    }

                                } // container denied

                            } // container net-to-sub

                            container flow {
                                description "Enter the flow context";

                                leaf terminated {
                                    type yang:counter64;
                                    description "Number of allowed flows in both directions that have terminated.";
                                }

                                container duration {
                                    description "Enter the duration context";

                                    leaf short {
                                        type yang:counter64;
                                        description "Number of flows with a duration less than or equal to 30 seconds, that have completed.";
                                    }

                                    leaf medium {
                                        type yang:counter64;
                                        description "Number of flows with a duration less than or equal to 180 seconds, but greater than 30 seconds, that have completed.";
                                    }

                                    leaf long {
                                        type yang:counter64;
                                        description "Number of flows with a duration greater than 180 seconds, that have completed.";
                                    }

                                    leaf total {
                                        type yang:counter64;
                                        description "The sum of all flow durations from first packet seen to last packet seen for flows that have terminated.";
                                    }

                                } // container duration

                            } // container flow

                        } // container statistics

                        list statistics-type {
                            key "stats-type stats-name";
                            description "Enter the statistics-type list instance";

                            leaf stats-type {
                                type enumeration {
                                    enum "protocol"                     { value 1; }
                                    enum "application"                  { value 2; }
                                    enum "app-group"                    { value 3; }
                                    enum "charging-group"               { value 4; }
                                }
                                description "Specifies the statistic type (protocol or application) that the study is using.";
                            }

                            leaf stats-name {
                                type types-sros:named-item;
                                description "Specifies the AA stats name of the correct type for which statistics are requested.";
                            }

                            container statistics {
                                description "Enter the statistics context";

                                container sub-to-net {
                                    description "Enter the sub-to-net context";

                                    leaf active-flows {
                                        type yang:counter32;
                                        description "Number of allowed flows in the subscriber to network direction that are active.";
                                    }

                                    container admitted {
                                        description "Enter the admitted context";

                                        leaf octets {
                                            type yang:counter64;
                                            description "Number of bytes permitted for the subscriber to network direction.";
                                        }

                                        leaf packets {
                                            type yang:counter64;
                                            description "Number of packets permitted for the subscriber to network direction.";
                                        }

                                        leaf flows {
                                            type yang:counter64;
                                            description "Number of flows permitted for the subscriber to network direction.";
                                        }

                                    } // container admitted

                                    container denied {
                                        description "Enter the denied context";

                                        leaf octets {
                                            type yang:counter64;
                                            description "Number of bytes dropped for the subscriber to network direction.";
                                        }

                                        leaf packets {
                                            type yang:counter64;
                                            description "Number of packets dropped for the subscriber to network direction.";
                                        }

                                        leaf flows {
                                            type yang:counter64;
                                            description "Number of flows that dropped subsequent packets in the subscriber to network direction.";
                                        }

                                    } // container denied

                                } // container sub-to-net

                                container net-to-sub {
                                    description "Enter the net-to-sub context";

                                    leaf active-flows {
                                        type yang:counter32;
                                        description "Number of allowed flows in the network to subscriber direction that are active.";
                                    }

                                    container admitted {
                                        description "Enter the admitted context";

                                        leaf octets {
                                            type yang:counter64;
                                            description "Number of bytes permitted for the network to subscriber direction.";
                                        }

                                        leaf packets {
                                            type yang:counter64;
                                            description "Number of packets permitted for the network to subscriber direction.";
                                        }

                                        leaf flows {
                                            type yang:counter64;
                                            description "Number of flows permitted for the network to subscriber direction.";
                                        }

                                    } // container admitted

                                    container denied {
                                        description "Enter the denied context";

                                        leaf octets {
                                            type yang:counter64;
                                            description "Number of bytes dropped for the network to subscriber direction.";
                                        }

                                        leaf packets {
                                            type yang:counter64;
                                            description "Number of packets dropped for the network to subscriber direction.";
                                        }

                                        leaf flows {
                                            type yang:counter64;
                                            description "Number of flows that dropped subsequent packets in the network to subscriber direction.";
                                        }

                                    } // container denied

                                } // container net-to-sub

                                container flow {
                                    description "Enter the flow context";

                                    leaf terminated {
                                        type yang:counter64;
                                        description "Number of allowed flows in both directions that have terminated.";
                                    }

                                    container duration {
                                        description "Enter the duration context";

                                        leaf short {
                                            type yang:counter64;
                                            description "Number of flows with a duration less than or equal to 30 seconds, that have completed.";
                                        }

                                        leaf medium {
                                            type yang:counter64;
                                            description "Number of flows with a duration less than or equal to 180 seconds, but greater than 30 seconds, that have completed.";
                                        }

                                        leaf long {
                                            type yang:counter64;
                                            description "Number of flows with a duration greater than 180 seconds, that have completed.";
                                        }

                                        leaf total {
                                            type yang:counter64;
                                            description "The sum of all flow durations from first packet seen to last packet seen for flows that have terminated.";
                                        }

                                    } // container duration

                                } // container flow

                            } // container statistics

                            container usage-monitoring {
                                description "Enter the usage-monitoring context";

                                leaf status {
                                    type types-aa:usage-monitor-oper-state;
                                    description "The operational state for the usage monitor.";
                                }

                                container net-to-sub {
                                    description "Enter the net-to-sub context";

                                    leaf grant-status {
                                        type types-aa:usage-monitor-grant-state;
                                        description "The grant status for the network to subscriber direction.";
                                    }

                                    container statistics {
                                        description "Enter the statistics context";

                                        leaf granted {
                                            type yang:counter64;
                                            description
                                                "The amount of credits allocated by the policy server
                                                 for the network to subscriber direction.";
                                        }

                                        leaf used {
                                            type yang:counter64;
                                            description "The amount of credits used by the network to subscriber direction.";
                                        }

                                        leaf used-percent {
                                            type uint32 {
                                                range "0..10000";
                                            }
                                            units "centipercent";
                                            description "The amount of credits used by the network to subscriber direction.";
                                        }

                                    } // container statistics

                                } // container net-to-sub

                                container sub-to-net {
                                    description "Enter the sub-to-net context";

                                    leaf grant-status {
                                        type types-aa:usage-monitor-grant-state;
                                        description "The grant status for the subscriber to network direction.";
                                    }

                                    container statistics {
                                        description "Enter the statistics context";

                                        leaf granted {
                                            type yang:counter64;
                                            description
                                                "The amount of credits allocated by the policy server
                                                 for the subscriber to network direction.";
                                        }

                                        leaf used {
                                            type yang:counter64;
                                            description "The amount of credits used by the subscriber to network direction.";
                                        }

                                        leaf used-percent {
                                            type uint32 {
                                                range "0..10000";
                                            }
                                            units "centipercent";
                                            description "The amount of credits used by the subscriber to network direction.";
                                        }

                                    } // container statistics

                                } // container sub-to-net

                                container both {
                                    description "Enter the both context";

                                    leaf grant-status {
                                        type types-aa:usage-monitor-grant-state;
                                        description "The grant status for either direction.";
                                    }

                                    container statistics {
                                        description "Enter the statistics context";

                                        leaf granted {
                                            type yang:counter64;
                                            description
                                                "The amount of credits allocated by the policy server
                                                 for either direction.";
                                        }

                                        leaf used {
                                            type yang:counter64;
                                            description "The amount of credits used by either direction.";
                                        }

                                        leaf used-percent {
                                            type uint32 {
                                                range "0..10000";
                                            }
                                            units "centipercent";
                                            description "The amount of credits used by either direction.";
                                        }

                                    } // container statistics

                                } // container both

                            } // container usage-monitoring

                        } // list statistics-type

                    } // list statistics-scope

                } // list aa-sub

                list aa-sub-study {
                    key "study-type";
                    description "Enter the aa-sub-study list instance";

                    leaf study-type {
                        type types-aa:study-stats-type;
                        description "Specifies the statistic type (protocol or application) that the study is using.";
                    }

                    list aa-sub {
                        key "aa-sub-type aa-sub-name";
                        description "Enter the aa-sub list instance";

                        leaf aa-sub-type {
                            type types-aa:stats-aa-sub-type;
                            description "Specifies the AA subscriber type for statistics.";
                        }

                        leaf aa-sub-name {
                            type union {
                                type types-sros:sap;
                                type types-services:sdp-bind-id;
                                type types-sros:named-item;
                            }
                            description "Specifies AA subscriber identifier string.";
                        }

                        list statistics-scope {
                            key "stats-scope";
                            description "Enter the statistics-scope list instance";

                            leaf stats-scope {
                                type types-aa:stats-scope;
                                description "Specifies to provide stats from most recent snapshot or to also include realtime information from active flows.";
                            }

                            list statistics-name {
                                key "stats-name";
                                description "Enter the statistics-name list instance";

                                leaf stats-name {
                                    type types-sros:named-item;
                                    description "Specifies to the protocol or application name.";
                                }

                                container statistics {
                                    description "Enter the statistics context";

                                    container sub-to-net {
                                        description "Enter the sub-to-net context";

                                        leaf active-flows {
                                            type yang:counter32;
                                            description "Number of allowed flows in the subscriber to network direction that are active.";
                                        }

                                        container admitted {
                                            description "Enter the admitted context";

                                            leaf octets {
                                                type yang:counter64;
                                                description "Number of bytes permitted for the subscriber to network direction.";
                                            }

                                            leaf packets {
                                                type yang:counter64;
                                                description "Number of packets permitted for the subscriber to network direction.";
                                            }

                                            leaf flows {
                                                type yang:counter64;
                                                description "Number of flows permitted for the subscriber to network direction.";
                                            }

                                        } // container admitted

                                        container denied {
                                            description "Enter the denied context";

                                            leaf octets {
                                                type yang:counter64;
                                                description "Number of bytes dropped for the subscriber to network direction.";
                                            }

                                            leaf packets {
                                                type yang:counter64;
                                                description "Number of packets dropped for the subscriber to network direction.";
                                            }

                                            leaf flows {
                                                type yang:counter64;
                                                description "Number of flows that dropped subsequent packets in the subscriber to network direction.";
                                            }

                                        } // container denied

                                    } // container sub-to-net

                                    container net-to-sub {
                                        description "Enter the net-to-sub context";

                                        leaf active-flows {
                                            type yang:counter32;
                                            description "Number of allowed flows in the network to subscriber direction that are active.";
                                        }

                                        container admitted {
                                            description "Enter the admitted context";

                                            leaf octets {
                                                type yang:counter64;
                                                description "Number of bytes permitted for the network to subscriber direction.";
                                            }

                                            leaf packets {
                                                type yang:counter64;
                                                description "Number of packets permitted for the network to subscriber direction.";
                                            }

                                            leaf flows {
                                                type yang:counter64;
                                                description "Number of flows permitted for the network to subscriber direction.";
                                            }

                                        } // container admitted

                                        container denied {
                                            description "Enter the denied context";

                                            leaf octets {
                                                type yang:counter64;
                                                description "Number of bytes dropped for the network to subscriber direction.";
                                            }

                                            leaf packets {
                                                type yang:counter64;
                                                description "Number of packets dropped for the network to subscriber direction.";
                                            }

                                            leaf flows {
                                                type yang:counter64;
                                                description "Number of flows that dropped subsequent packets in the network to subscriber direction.";
                                            }

                                        } // container denied

                                    } // container net-to-sub

                                    container flow {
                                        description "Enter the flow context";

                                        leaf terminated {
                                            type yang:counter64;
                                            description "Number of allowed flows in both directions that have terminated.";
                                        }

                                        container duration {
                                            description "Enter the duration context";

                                            leaf short {
                                                type yang:counter64;
                                                description "Number of flows with a duration less than or equal to 30 seconds, that have completed.";
                                            }

                                            leaf medium {
                                                type yang:counter64;
                                                description "Number of flows with a duration less than or equal to 180 seconds, but greater than 30 seconds, that have completed.";
                                            }

                                            leaf long {
                                                type yang:counter64;
                                                description "Number of flows with a duration greater than 180 seconds, that have completed.";
                                            }

                                            leaf total {
                                                type yang:counter64;
                                                description "The sum of all flow durations from first packet seen to last packet seen for flows that have terminated.";
                                            }

                                        } // container duration

                                    } // container flow

                                } // container statistics

                            } // list statistics-name

                        } // list statistics-scope

                    } // list aa-sub

                } // list aa-sub-study

                list app-group {
                    key "app-group-name";
                    description "Enter the app-group list instance";

                    leaf app-group-name {
                        type types-sros:named-item;
                        description "App-group to display statistics for.";
                    }

                    container statistics {
                        description "Enter the statistics context";

                        leaf active-subscribers {
                            type yang:gauge32;
                            description "The number of subscribers at the most recent 5-minute snapshot of statistics.";
                        }

                        container sub-to-net {
                            description "Enter the sub-to-net context";

                            leaf active-flows {
                                type yang:counter32;
                                description "Number of allowed flows in the subscriber to network direction that are active.";
                            }

                            container admitted {
                                description "Enter the admitted context";

                                leaf octets {
                                    type yang:counter64;
                                    description "Number of bytes permitted for the subscriber to network direction.";
                                }

                                leaf packets {
                                    type yang:counter64;
                                    description "Number of packets permitted for the subscriber to network direction.";
                                }

                                leaf flows {
                                    type yang:counter64;
                                    description "Number of flows permitted for the subscriber to network direction.";
                                }

                            } // container admitted

                            container denied {
                                description "Enter the denied context";

                                leaf octets {
                                    type yang:counter64;
                                    description "Number of bytes dropped for the subscriber to network direction.";
                                }

                                leaf packets {
                                    type yang:counter64;
                                    description "Number of packets dropped for the subscriber to network direction.";
                                }

                                leaf flows {
                                    type yang:counter64;
                                    description "Number of flows that dropped subsequent packets in the subscriber to network direction.";
                                }

                            } // container denied

                        } // container sub-to-net

                        container net-to-sub {
                            description "Enter the net-to-sub context";

                            leaf active-flows {
                                type yang:counter32;
                                description "Number of allowed flows in the network to subscriber direction that are active.";
                            }

                            container admitted {
                                description "Enter the admitted context";

                                leaf octets {
                                    type yang:counter64;
                                    description "Number of bytes permitted for the network to subscriber direction.";
                                }

                                leaf packets {
                                    type yang:counter64;
                                    description "Number of packets permitted for the network to subscriber direction.";
                                }

                                leaf flows {
                                    type yang:counter64;
                                    description "Number of flows permitted for the network to subscriber direction.";
                                }

                            } // container admitted

                            container denied {
                                description "Enter the denied context";

                                leaf octets {
                                    type yang:counter64;
                                    description "Number of bytes dropped for the network to subscriber direction.";
                                }

                                leaf packets {
                                    type yang:counter64;
                                    description "Number of packets dropped for the network to subscriber direction.";
                                }

                                leaf flows {
                                    type yang:counter64;
                                    description "Number of flows that dropped subsequent packets in the network to subscriber direction.";
                                }

                            } // container denied

                        } // container net-to-sub

                        container flow {
                            description "Enter the flow context";

                            leaf terminated {
                                type yang:counter64;
                                description "Number of allowed flows in both directions that have terminated.";
                            }

                            container duration {
                                description "Enter the duration context";

                                leaf short {
                                    type yang:counter64;
                                    description "Number of flows with a duration less than or equal to 30 seconds, that have completed.";
                                }

                                leaf medium {
                                    type yang:counter64;
                                    description "Number of flows with a duration less than or equal to 180 seconds, but greater than 30 seconds, that have completed.";
                                }

                                leaf long {
                                    type yang:counter64;
                                    description "Number of flows with a duration greater than 180 seconds, that have completed.";
                                }

                                leaf total {
                                    type yang:counter64;
                                    description "The sum of all flow durations from first packet seen to last packet seen for flows that have terminated.";
                                }

                            } // container duration

                        } // container flow

                    } // container statistics

                } // list app-group

                list application {
                    key "application-name";
                    description "Enter the application list instance";

                    leaf application-name {
                        type types-sros:named-item;
                        description "Application to display statistics for.";
                    }

                    container statistics {
                        description "Enter the statistics context";

                        leaf active-subscribers {
                            type yang:gauge32;
                            description "The number of subscribers at the most recent 5-minute snapshot of statistics.";
                        }

                        container sub-to-net {
                            description "Enter the sub-to-net context";

                            leaf active-flows {
                                type yang:counter32;
                                description "Number of allowed flows in the subscriber to network direction that are active.";
                            }

                            container admitted {
                                description "Enter the admitted context";

                                leaf octets {
                                    type yang:counter64;
                                    description "Number of bytes permitted for the subscriber to network direction.";
                                }

                                leaf packets {
                                    type yang:counter64;
                                    description "Number of packets permitted for the subscriber to network direction.";
                                }

                                leaf flows {
                                    type yang:counter64;
                                    description "Number of flows permitted for the subscriber to network direction.";
                                }

                            } // container admitted

                            container denied {
                                description "Enter the denied context";

                                leaf octets {
                                    type yang:counter64;
                                    description "Number of bytes dropped for the subscriber to network direction.";
                                }

                                leaf packets {
                                    type yang:counter64;
                                    description "Number of packets dropped for the subscriber to network direction.";
                                }

                                leaf flows {
                                    type yang:counter64;
                                    description "Number of flows that dropped subsequent packets in the subscriber to network direction.";
                                }

                            } // container denied

                        } // container sub-to-net

                        container net-to-sub {
                            description "Enter the net-to-sub context";

                            leaf active-flows {
                                type yang:counter32;
                                description "Number of allowed flows in the network to subscriber direction that are active.";
                            }

                            container admitted {
                                description "Enter the admitted context";

                                leaf octets {
                                    type yang:counter64;
                                    description "Number of bytes permitted for the network to subscriber direction.";
                                }

                                leaf packets {
                                    type yang:counter64;
                                    description "Number of packets permitted for the network to subscriber direction.";
                                }

                                leaf flows {
                                    type yang:counter64;
                                    description "Number of flows permitted for the network to subscriber direction.";
                                }

                            } // container admitted

                            container denied {
                                description "Enter the denied context";

                                leaf octets {
                                    type yang:counter64;
                                    description "Number of bytes dropped for the network to subscriber direction.";
                                }

                                leaf packets {
                                    type yang:counter64;
                                    description "Number of packets dropped for the network to subscriber direction.";
                                }

                                leaf flows {
                                    type yang:counter64;
                                    description "Number of flows that dropped subsequent packets in the network to subscriber direction.";
                                }

                            } // container denied

                        } // container net-to-sub

                        container flow {
                            description "Enter the flow context";

                            leaf terminated {
                                type yang:counter64;
                                description "Number of allowed flows in both directions that have terminated.";
                            }

                            container duration {
                                description "Enter the duration context";

                                leaf short {
                                    type yang:counter64;
                                    description "Number of flows with a duration less than or equal to 30 seconds, that have completed.";
                                }

                                leaf medium {
                                    type yang:counter64;
                                    description "Number of flows with a duration less than or equal to 180 seconds, but greater than 30 seconds, that have completed.";
                                }

                                leaf long {
                                    type yang:counter64;
                                    description "Number of flows with a duration greater than 180 seconds, that have completed.";
                                }

                                leaf total {
                                    type yang:counter64;
                                    description "The sum of all flow durations from first packet seen to last packet seen for flows that have terminated.";
                                }

                            } // container duration

                        } // container flow

                    } // container statistics

                } // list application

                list event-log {
                    key "event-log-name";
                    description "Enter the event-log list instance";

                    leaf event-log-name {
                        type types-sros:named-item;
                        description "Partition event log name";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            container syslog {
                                description "Enter the syslog context";

                                leaf events-sent {
                                    type yang:counter64;
                                    description "The number of syslog events that were sent to the configured syslog collector target.";
                                }

                                leaf events-failed {
                                    type yang:counter64;
                                    description
                                        "The number of syslog events that could not be sent to the configured syslog collector target
                                         due to configuration or processing problems.";
                                }

                            } // container syslog

                        } // container statistics

                    } // list esa

                    list isa {
                        key "mda-id";
                        description "Enter the isa list instance";

                        leaf mda-id {
                            type types-isa:slot-mda;
                            description "MDA/ISA ID";
                        }

                        container statistics {
                            description "Enter the statistics context";

                            container syslog {
                                description "Enter the syslog context";

                                leaf events-sent {
                                    type yang:counter64;
                                    description "The number of syslog events that were sent to the configured syslog collector target.";
                                }

                                leaf events-failed {
                                    type yang:counter64;
                                    description
                                        "The number of syslog events that could not be sent to the configured syslog collector target
                                         due to configuration or processing problems.";
                                }

                            } // container syslog

                        } // container statistics

                    } // list isa

                    container summary {
                        description "Enter the summary context";

                        container statistics {
                            description "Enter the statistics context";

                            container syslog {
                                description "Enter the syslog context";

                                leaf events-sent {
                                    type yang:counter64;
                                    description "The number of syslog events that were sent to the configured syslog collector target.";
                                }

                                leaf events-failed {
                                    type yang:counter64;
                                    description
                                        "The number of syslog events that could not be sent to the configured syslog collector target
                                         due to configuration or processing problems.";
                                }

                            } // container syslog

                        } // container statistics

                    } // container summary

                } // list event-log

                container flow-attribute {
                    description "Enter the flow-attribute context";

                    list name {
                        key "flow-attribute-name confidence-bin";
                        description "Enter the name list instance";

                        leaf flow-attribute-name {
                            type types-sros:named-item;
                            description "Specifies the flow-attribute name.";
                        }

                        leaf confidence-bin {
                            type uint32 {
                                range "0..4";
                            }
                            description "Specifies the flow-attribute confidence bin.";
                        }

                        list esa {
                            key "esa-id vm";
                            description "Enter the esa list instance";

                            leaf esa-id {
                                type types-esa:esa-id;
                                description "ESA ID";
                            }

                            leaf vm {
                                type types-esa:vm-id;
                                description "VM ID within the ESA";
                            }

                            leaf confidence-bin-name {
                                type types-sros:named-item;
                                description "Descriptive name of the flow-attribute confidence bin.";
                            }

                            container statistics {
                                description "Enter the statistics context";

                                container sub-to-net {
                                    description "Enter the sub-to-net context";

                                    leaf octets {
                                        type yang:counter64;
                                        description "Number of bytes in the subscriber to network direction for a flow attribute/confidence pair.";
                                    }

                                    leaf packets {
                                        type yang:counter64;
                                        description "Number of packets in the subscriber to network direction for a flow attribute/confidence pair.";
                                    }

                                    leaf flows {
                                        type yang:counter64;
                                        description "Number of flows in the subscriber to network direction for a flow attribute/confidence pair.";
                                    }

                                } // container sub-to-net

                                container net-to-sub {
                                    description "Enter the net-to-sub context";

                                    leaf octets {
                                        type yang:counter64;
                                        description "Number of bytes in the network to subscriber direction for a flow attribute/confidence pair.";
                                    }

                                    leaf packets {
                                        type yang:counter64;
                                        description "Number of packets in the network to subscriber direction for a flow attribute/confidence pair.";
                                    }

                                    leaf flows {
                                        type yang:counter64;
                                        description "Number of flows in the network to subscriber direction for a flow attribute/confidence pair.";
                                    }

                                } // container net-to-sub

                            } // container statistics

                        } // list esa

                        list isa {
                            key "mda-id";
                            description "Enter the isa list instance";

                            leaf mda-id {
                                type types-isa:slot-mda;
                                description "MDA/ISA ID";
                            }

                            leaf confidence-bin-name {
                                type types-sros:named-item;
                                description "Descriptive name of the flow-attribute confidence bin.";
                            }

                            container statistics {
                                description "Enter the statistics context";

                                container sub-to-net {
                                    description "Enter the sub-to-net context";

                                    leaf octets {
                                        type yang:counter64;
                                        description "Number of bytes in the subscriber to network direction for a flow attribute/confidence pair.";
                                    }

                                    leaf packets {
                                        type yang:counter64;
                                        description "Number of packets in the subscriber to network direction for a flow attribute/confidence pair.";
                                    }

                                    leaf flows {
                                        type yang:counter64;
                                        description "Number of flows in the subscriber to network direction for a flow attribute/confidence pair.";
                                    }

                                } // container sub-to-net

                                container net-to-sub {
                                    description "Enter the net-to-sub context";

                                    leaf octets {
                                        type yang:counter64;
                                        description "Number of bytes in the network to subscriber direction for a flow attribute/confidence pair.";
                                    }

                                    leaf packets {
                                        type yang:counter64;
                                        description "Number of packets in the network to subscriber direction for a flow attribute/confidence pair.";
                                    }

                                    leaf flows {
                                        type yang:counter64;
                                        description "Number of flows in the network to subscriber direction for a flow attribute/confidence pair.";
                                    }

                                } // container net-to-sub

                            } // container statistics

                        } // list isa

                        container summary {
                            description "Enter the summary context";

                            leaf confidence-bin-name {
                                type types-sros:named-item;
                                description "Descriptive name of the flow-attribute confidence bin.";
                            }

                            container statistics {
                                description "Enter the statistics context";

                                container sub-to-net {
                                    description "Enter the sub-to-net context";

                                    leaf octets {
                                        type yang:counter64;
                                        description "Number of bytes in the subscriber to network direction for a flow attribute/confidence pair.";
                                    }

                                    leaf packets {
                                        type yang:counter64;
                                        description "Number of packets in the subscriber to network direction for a flow attribute/confidence pair.";
                                    }

                                    leaf flows {
                                        type yang:counter64;
                                        description "Number of flows in the subscriber to network direction for a flow attribute/confidence pair.";
                                    }

                                } // container sub-to-net

                                container net-to-sub {
                                    description "Enter the net-to-sub context";

                                    leaf octets {
                                        type yang:counter64;
                                        description "Number of bytes in the network to subscriber direction for a flow attribute/confidence pair.";
                                    }

                                    leaf packets {
                                        type yang:counter64;
                                        description "Number of packets in the network to subscriber direction for a flow attribute/confidence pair.";
                                    }

                                    leaf flows {
                                        type yang:counter64;
                                        description "Number of flows in the network to subscriber direction for a flow attribute/confidence pair.";
                                    }

                                } // container net-to-sub

                            } // container statistics

                        } // container summary

                    } // list name

                } // container flow-attribute

                container gtp {
                    description "Enter the gtp context";

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            container sub-to-net {
                                description "Enter the sub-to-net context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container sub-to-net

                            container net-to-sub {
                                description "Enter the net-to-sub context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container net-to-sub

                        } // container statistics

                    } // list esa

                    list isa {
                        key "mda-id";
                        description "Enter the isa list instance";

                        leaf mda-id {
                            type types-isa:slot-mda;
                            description "MDA/ISA ID";
                        }

                        container statistics {
                            description "Enter the statistics context";

                            container sub-to-net {
                                description "Enter the sub-to-net context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container sub-to-net

                            container net-to-sub {
                                description "Enter the net-to-sub context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container net-to-sub

                        } // container statistics

                    } // list isa

                    container summary {
                        description "Enter the summary context";

                        container statistics {
                            description "Enter the statistics context";

                            container sub-to-net {
                                description "Enter the sub-to-net context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container sub-to-net

                            container net-to-sub {
                                description "Enter the net-to-sub context";

                                leaf packets-permitted {
                                    type yang:counter64;
                                    description "The number of GTP packets permitted.";
                                }

                                leaf packets-permitted-no-gtp-filter {
                                    type yang:counter64;
                                    description "The number of GTP packets permitted which were not subject to a GTP filter.";
                                }

                                container packets-denied {
                                    description "Enter the packets-denied context";

                                    leaf gtp-message-length {
                                        type yang:counter64;
                                        description "The number of GTP packets denied due to improper GTP message length.";
                                    }

                                    leaf udp-packet-length {
                                        type yang:counter64;
                                        description "The number of GTP packets denied due to improper UDP packet length.";
                                    }

                                    leaf gtp-version {
                                        type yang:counter64;
                                        description "The number of GTP packets denied due to unsupported GTP version.";
                                    }

                                    leaf traffic-flow-count-policer {
                                        type yang:counter64;
                                        description
                                            "The number of packets denied by the policer flow count limit due to the configuration of
                                             GTP flow count limiting against a flow count policer.";
                                    }

                                    leaf gtp-filter {
                                        type yang:counter64;
                                        description "The number of packets denied due to GTP filtering.";
                                    }

                                    leaf other {
                                        type yang:counter64;
                                        description "The number of packets denied due to non gtp-traffic policers, session filters, or flow resource exhaustion";
                                    }

                                } // container packets-denied

                            } // container net-to-sub

                        } // container statistics

                    } // container summary

                    list gtp-filter {
                        key "gtp-filter-name";
                        description "Enter the gtp-filter list instance";

                        leaf gtp-filter-name {
                            type types-sros:named-item;
                            description "GTP filter name";
                        }

                        list esa {
                            key "esa-id vm";
                            description "Enter the esa list instance";

                            leaf esa-id {
                                type types-esa:esa-id;
                                description "ESA ID";
                            }

                            leaf vm {
                                type types-esa:vm-id;
                                description "VM ID within the ESA";
                            }

                            container statistics {
                                description "Enter the statistics context";

                                leaf packets-permitted {
                                    type yang:counter64;
                                    description "The number of packets permitted through the GTP filter.";
                                }

                                container packets-denied {
                                    description "Enter the packets-denied context";

                                    leaf payload-length {
                                        type yang:counter64;
                                        description "The number of packets denied by the GTP filter due to the maximum payload length configured for the gtp-filter.";
                                    }

                                    leaf message-type {
                                        type yang:counter64;
                                        description "The number of packets denied by the GTP filter due to message ID configuration for the gtp-filter.";
                                    }

                                    leaf mandatory-header {
                                        type yang:counter64;
                                        description "The number of packets denied by the GTP filter due to a missing mandatory header.";
                                    }

                                    leaf extension-header {
                                        type yang:counter64;
                                        description "The number of packets denied by the GTP filter due to a missing extension header.";
                                    }

                                    leaf information-element {
                                        type yang:counter64;
                                        description "The number of packets denied by the GTP filter due to a missing, invalid, or malformed information element.";
                                    }

                                    leaf gtpv2-message-type {
                                        type yang:counter64;
                                        description "The number of GTPv2 packets denied by the GTP filter due to GTPv2 message ID configuration for the gtp-filter.";
                                    }

                                    leaf imsi-apn-filter {
                                        type yang:counter64;
                                        description "The number of packets denied by the GTP filter due to imsi-apn-filter configuration for the gtp-filter.";
                                    }

                                    leaf invalid-sequence-number {
                                        type yang:counter64;
                                        description "The number of packets denied by the GTP filter due to invalid sequence number.";
                                    }

                                    leaf invalid-teid {
                                        type yang:counter64;
                                        description "The number of packets denied by the GTP filter due to invalid TEID.";
                                    }

                                    leaf invalid-subscriber-ip {
                                        type yang:counter64;
                                        description "The number of packets denied by the GTP filter due to invalid subscriber IP address.";
                                    }

                                    leaf gtp-in-gtp {
                                        type yang:counter64;
                                        description "The number of packets denied by the GTP filter due to GTP encapsulated in GTP.";
                                    }

                                    leaf mandatory-information-element {
                                        type yang:counter64;
                                        description "The number of packets denied by the GTP filter due to missing mandatory information elements.";
                                    }

                                    leaf tunnel-database-full {
                                        type yang:counter64;
                                        description
                                            "The number of packets denied by the GTP filter due to the GTP tunnel database being full when
                                             a new tunnel needed to be allocated.";
                                    }

                                    leaf tunnel-endpoint-limit {
                                        type yang:counter64;
                                        description
                                            "The number of packets denied by the GTP filter due to receiving a 'create session request' at
                                             the time the GTP TEID default limit has already been reachedthe GTP tunnel database being
                                             full when a new tunnel needed to be allocated.";
                                    }

                                } // container packets-denied

                            } // container statistics

                        } // list esa

                        list isa {
                            key "mda-id";
                            description "Enter the isa list instance";

                            leaf mda-id {
                                type types-isa:slot-mda;
                                description "MDA/ISA ID";
                            }

                            container statistics {
                                description "Enter the statistics context";

                                leaf packets-permitted {
                                    type yang:counter64;
                                    description "The number of packets permitted through the GTP filter.";
                                }

                                container packets-denied {
                                    description "Enter the packets-denied context";

                                    leaf payload-length {
                                        type yang:counter64;
                                        description "The number of packets denied by the GTP filter due to the maximum payload length configured for the gtp-filter.";
                                    }

                                    leaf message-type {
                                        type yang:counter64;
                                        description "The number of packets denied by the GTP filter due to message ID configuration for the gtp-filter.";
                                    }

                                    leaf mandatory-header {
                                        type yang:counter64;
                                        description "The number of packets denied by the GTP filter due to a missing mandatory header.";
                                    }

                                    leaf extension-header {
                                        type yang:counter64;
                                        description "The number of packets denied by the GTP filter due to a missing extension header.";
                                    }

                                    leaf information-element {
                                        type yang:counter64;
                                        description "The number of packets denied by the GTP filter due to a missing, invalid, or malformed information element.";
                                    }

                                    leaf gtpv2-message-type {
                                        type yang:counter64;
                                        description "The number of GTPv2 packets denied by the GTP filter due to GTPv2 message ID configuration for the gtp-filter.";
                                    }

                                    leaf imsi-apn-filter {
                                        type yang:counter64;
                                        description "The number of packets denied by the GTP filter due to imsi-apn-filter configuration for the gtp-filter.";
                                    }

                                    leaf invalid-sequence-number {
                                        type yang:counter64;
                                        description "The number of packets denied by the GTP filter due to invalid sequence number.";
                                    }

                                    leaf invalid-teid {
                                        type yang:counter64;
                                        description "The number of packets denied by the GTP filter due to invalid TEID.";
                                    }

                                    leaf invalid-subscriber-ip {
                                        type yang:counter64;
                                        description "The number of packets denied by the GTP filter due to invalid subscriber IP address.";
                                    }

                                    leaf gtp-in-gtp {
                                        type yang:counter64;
                                        description "The number of packets denied by the GTP filter due to GTP encapsulated in GTP.";
                                    }

                                    leaf mandatory-information-element {
                                        type yang:counter64;
                                        description "The number of packets denied by the GTP filter due to missing mandatory information elements.";
                                    }

                                    leaf tunnel-database-full {
                                        type yang:counter64;
                                        description
                                            "The number of packets denied by the GTP filter due to the GTP tunnel database being full when
                                             a new tunnel needed to be allocated.";
                                    }

                                    leaf tunnel-endpoint-limit {
                                        type yang:counter64;
                                        description
                                            "The number of packets denied by the GTP filter due to receiving a 'create session request' at
                                             the time the GTP TEID default limit has already been reachedthe GTP tunnel database being
                                             full when a new tunnel needed to be allocated.";
                                    }

                                } // container packets-denied

                            } // container statistics

                        } // list isa

                        container summary {
                            description "Enter the summary context";

                            container statistics {
                                description "Enter the statistics context";

                                leaf packets-permitted {
                                    type yang:counter64;
                                    description "The number of packets permitted through the GTP filter.";
                                }

                                container packets-denied {
                                    description "Enter the packets-denied context";

                                    leaf payload-length {
                                        type yang:counter64;
                                        description "The number of packets denied by the GTP filter due to the maximum payload length configured for the gtp-filter.";
                                    }

                                    leaf message-type {
                                        type yang:counter64;
                                        description "The number of packets denied by the GTP filter due to message ID configuration for the gtp-filter.";
                                    }

                                    leaf mandatory-header {
                                        type yang:counter64;
                                        description "The number of packets denied by the GTP filter due to a missing mandatory header.";
                                    }

                                    leaf extension-header {
                                        type yang:counter64;
                                        description "The number of packets denied by the GTP filter due to a missing extension header.";
                                    }

                                    leaf information-element {
                                        type yang:counter64;
                                        description "The number of packets denied by the GTP filter due to a missing, invalid, or malformed information element.";
                                    }

                                    leaf gtpv2-message-type {
                                        type yang:counter64;
                                        description "The number of GTPv2 packets denied by the GTP filter due to GTPv2 message ID configuration for the gtp-filter.";
                                    }

                                    leaf imsi-apn-filter {
                                        type yang:counter64;
                                        description "The number of packets denied by the GTP filter due to imsi-apn-filter configuration for the gtp-filter.";
                                    }

                                    leaf invalid-sequence-number {
                                        type yang:counter64;
                                        description "The number of packets denied by the GTP filter due to invalid sequence number.";
                                    }

                                    leaf invalid-teid {
                                        type yang:counter64;
                                        description "The number of packets denied by the GTP filter due to invalid TEID.";
                                    }

                                    leaf invalid-subscriber-ip {
                                        type yang:counter64;
                                        description "The number of packets denied by the GTP filter due to invalid subscriber IP address.";
                                    }

                                    leaf gtp-in-gtp {
                                        type yang:counter64;
                                        description "The number of packets denied by the GTP filter due to GTP encapsulated in GTP.";
                                    }

                                    leaf mandatory-information-element {
                                        type yang:counter64;
                                        description "The number of packets denied by the GTP filter due to missing mandatory information elements.";
                                    }

                                    leaf tunnel-database-full {
                                        type yang:counter64;
                                        description
                                            "The number of packets denied by the GTP filter due to the GTP tunnel database being full when
                                             a new tunnel needed to be allocated.";
                                    }

                                    leaf tunnel-endpoint-limit {
                                        type yang:counter64;
                                        description
                                            "The number of packets denied by the GTP filter due to receiving a 'create session request' at
                                             the time the GTP TEID default limit has already been reachedthe GTP tunnel database being
                                             full when a new tunnel needed to be allocated.";
                                    }

                                } // container packets-denied

                            } // container statistics

                        } // container summary

                        container message-type {
                            description "Enter the message-type context";

                            list entry {
                                key "entry-id";
                                description "Enter the entry list instance";

                                leaf entry-id {
                                    type uint32 {
                                        range "1..255";
                                    }
                                    description "GTP filter entry ID";
                                }

                            } // list entry

                        } // container message-type

                        container message-type-gtp-v2 {
                            description "Enter the message-type-gtp-v2 context";

                            list entry {
                                key "entry-id";
                                description "Enter the entry list instance";

                                leaf entry-id {
                                    type uint32 {
                                        range "516..770";
                                    }
                                    description "GTPv2 filter entry ID";
                                }

                            } // list entry

                        } // container message-type-gtp-v2

                        container imsi-apn-filter {
                            description "Enter the imsi-apn-filter context";

                            list entry {
                                key "entry-id";
                                description "Enter the entry list instance";

                                leaf entry-id {
                                    type uint32 {
                                        range "1031..2030";
                                    }
                                    description "AA IMSI-APN filter entry ID";
                                }

                            } // list entry

                        } // container imsi-apn-filter

                    } // list gtp-filter

                } // container gtp

                list http-enrich {
                    key "http-enrich-name";
                    description "Enter the http-enrich list instance";

                    leaf http-enrich-name {
                        type types-sros:named-item;
                        description "Specifies the name of the AA group HTTP enrich object.";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            leaf enriched {
                                type yang:counter64;
                                description "The number of enriched requests.";
                            }

                            container not-enriched {
                                description "Enter the not-enriched context";

                                leaf out-of-resources {
                                    type yang:counter64;
                                    description "The number of HTTP requests not enriched due to resource issues.";
                                }

                                leaf missing-subscriber-data {
                                    type yang:counter64;
                                    description "The number of HTTP requests not enriched due to missing subscriber data.";
                                }

                                leaf templates-not-enabled {
                                    type yang:counter64;
                                    description "The number of HTTP requests not enriched due to the template not being enabled.";
                                }

                                leaf traffic-characteristics {
                                    type yang:counter64;
                                    description "The number of HTTP requests not enriched due to traffic characteristics.";
                                }

                                leaf exceeded-max-packet-size {
                                    type yang:counter64;
                                    description
                                        "The number of HTTP requests not enriched due to the packet size being
                                         greater than the maximum HTTP enrichment packet size specified in
                                         isa/application-assurance-group/http-enrich-max-packet-size.";
                                }

                                leaf session-dropped {
                                    type yang:counter64;
                                    description "The number of sessions that have been dropped due to segmentation or antispoof.";
                                }

                            } // container not-enriched

                            container anti-spoof {
                                description "Enter the anti-spoof context";

                                leaf header-mods {
                                    type yang:counter64;
                                    description
                                        "The number of HTTP header modifications that have been made for anti-spoofing.
                                         A value of 0 is returned if the value of anti-spoof is disabled.";
                                }

                                leaf header-mod-not-applied {
                                    type yang:counter64;
                                    description
                                        "The number of HTTP header modifications that were not made for anti-spoofing
                                         due to an HTTP header field value being short enough to result in a packet size increase
                                         if anti-spoofing were applied. A value of 0 is returned if the value of anti-spoof is disabled.";
                                }

                            } // container anti-spoof

                        } // container statistics

                    } // list esa

                    list isa {
                        key "mda-id";
                        description "Enter the isa list instance";

                        leaf mda-id {
                            type types-isa:slot-mda;
                            description "MDA/ISA ID";
                        }

                        container statistics {
                            description "Enter the statistics context";

                            leaf enriched {
                                type yang:counter64;
                                description "The number of enriched requests.";
                            }

                            container not-enriched {
                                description "Enter the not-enriched context";

                                leaf out-of-resources {
                                    type yang:counter64;
                                    description "The number of HTTP requests not enriched due to resource issues.";
                                }

                                leaf missing-subscriber-data {
                                    type yang:counter64;
                                    description "The number of HTTP requests not enriched due to missing subscriber data.";
                                }

                                leaf templates-not-enabled {
                                    type yang:counter64;
                                    description "The number of HTTP requests not enriched due to the template not being enabled.";
                                }

                                leaf traffic-characteristics {
                                    type yang:counter64;
                                    description "The number of HTTP requests not enriched due to traffic characteristics.";
                                }

                                leaf exceeded-max-packet-size {
                                    type yang:counter64;
                                    description
                                        "The number of HTTP requests not enriched due to the packet size being
                                         greater than the maximum HTTP enrichment packet size specified in
                                         isa/application-assurance-group/http-enrich-max-packet-size.";
                                }

                                leaf session-dropped {
                                    type yang:counter64;
                                    description "The number of sessions that have been dropped due to segmentation or antispoof.";
                                }

                            } // container not-enriched

                            container anti-spoof {
                                description "Enter the anti-spoof context";

                                leaf header-mods {
                                    type yang:counter64;
                                    description
                                        "The number of HTTP header modifications that have been made for anti-spoofing.
                                         A value of 0 is returned if the value of anti-spoof is disabled.";
                                }

                                leaf header-mod-not-applied {
                                    type yang:counter64;
                                    description
                                        "The number of HTTP header modifications that were not made for anti-spoofing
                                         due to an HTTP header field value being short enough to result in a packet size increase
                                         if anti-spoofing were applied. A value of 0 is returned if the value of anti-spoof is disabled.";
                                }

                            } // container anti-spoof

                        } // container statistics

                    } // list isa

                    container summary {
                        description "Enter the summary context";

                        container statistics {
                            description "Enter the statistics context";

                            leaf enriched {
                                type yang:counter64;
                                description "The number of enriched requests.";
                            }

                            container not-enriched {
                                description "Enter the not-enriched context";

                                leaf out-of-resources {
                                    type yang:counter64;
                                    description "The number of HTTP requests not enriched due to resource issues.";
                                }

                                leaf missing-subscriber-data {
                                    type yang:counter64;
                                    description "The number of HTTP requests not enriched due to missing subscriber data.";
                                }

                                leaf templates-not-enabled {
                                    type yang:counter64;
                                    description "The number of HTTP requests not enriched due to the template not being enabled.";
                                }

                                leaf traffic-characteristics {
                                    type yang:counter64;
                                    description "The number of HTTP requests not enriched due to traffic characteristics.";
                                }

                                leaf exceeded-max-packet-size {
                                    type yang:counter64;
                                    description
                                        "The number of HTTP requests not enriched due to the packet size being
                                         greater than the maximum HTTP enrichment packet size specified in
                                         isa/application-assurance-group/http-enrich-max-packet-size.";
                                }

                                leaf session-dropped {
                                    type yang:counter64;
                                    description "The number of sessions that have been dropped due to segmentation or antispoof.";
                                }

                            } // container not-enriched

                            container anti-spoof {
                                description "Enter the anti-spoof context";

                                leaf header-mods {
                                    type yang:counter64;
                                    description
                                        "The number of HTTP header modifications that have been made for anti-spoofing.
                                         A value of 0 is returned if the value of anti-spoof is disabled.";
                                }

                                leaf header-mod-not-applied {
                                    type yang:counter64;
                                    description
                                        "The number of HTTP header modifications that were not made for anti-spoofing
                                         due to an HTTP header field value being short enough to result in a packet size increase
                                         if anti-spoofing were applied. A value of 0 is returned if the value of anti-spoof is disabled.";
                                }

                            } // container anti-spoof

                        } // container statistics

                    } // container summary

                } // list http-enrich

                list http-error-redirect {
                    key "http-error-redirect-name error-code";
                    description "Enter the http-error-redirect list instance";

                    leaf http-error-redirect-name {
                        type types-sros:named-item;
                        description "Specifies the name of the AA group HTTP error redirect object.";
                    }

                    leaf error-code {
                        type uint32 {
                            range "400..999";
                        }
                        description "Specifies the HTTP error code value.";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            leaf redirects-sent {
                                type yang:counter64;
                                description "The number of redirected messages.";
                            }

                            container redirects-not-sent {
                                description "Enter the redirects-not-sent context";

                                leaf size-exceeded {
                                    type yang:counter64;
                                    description "The number of messages that have exceeded the custom message size associated with the error code.";
                                }

                                leaf out-of-resources {
                                    type yang:counter64;
                                    description "The number of message redirects that did not occur due to lack of resources.";
                                }

                                leaf wrong-file-type {
                                    type yang:counter64;
                                    description "The number of message redirects that did not occur due to the file type.";
                                }

                                leaf error {
                                    type yang:counter64;
                                    description "The number of message redirects that did not occur due to errors.";
                                }

                            } // container redirects-not-sent

                        } // container statistics

                    } // list esa

                    list isa {
                        key "mda-id";
                        description "Enter the isa list instance";

                        leaf mda-id {
                            type types-isa:slot-mda;
                            description "MDA/ISA ID";
                        }

                        container statistics {
                            description "Enter the statistics context";

                            leaf redirects-sent {
                                type yang:counter64;
                                description "The number of redirected messages.";
                            }

                            container redirects-not-sent {
                                description "Enter the redirects-not-sent context";

                                leaf size-exceeded {
                                    type yang:counter64;
                                    description "The number of messages that have exceeded the custom message size associated with the error code.";
                                }

                                leaf out-of-resources {
                                    type yang:counter64;
                                    description "The number of message redirects that did not occur due to lack of resources.";
                                }

                                leaf wrong-file-type {
                                    type yang:counter64;
                                    description "The number of message redirects that did not occur due to the file type.";
                                }

                                leaf error {
                                    type yang:counter64;
                                    description "The number of message redirects that did not occur due to errors.";
                                }

                            } // container redirects-not-sent

                        } // container statistics

                    } // list isa

                    container summary {
                        description "Enter the summary context";

                        container statistics {
                            description "Enter the statistics context";

                            leaf redirects-sent {
                                type yang:counter64;
                                description "The number of redirected messages.";
                            }

                            container redirects-not-sent {
                                description "Enter the redirects-not-sent context";

                                leaf size-exceeded {
                                    type yang:counter64;
                                    description "The number of messages that have exceeded the custom message size associated with the error code.";
                                }

                                leaf out-of-resources {
                                    type yang:counter64;
                                    description "The number of message redirects that did not occur due to lack of resources.";
                                }

                                leaf wrong-file-type {
                                    type yang:counter64;
                                    description "The number of message redirects that did not occur due to the file type.";
                                }

                                leaf error {
                                    type yang:counter64;
                                    description "The number of message redirects that did not occur due to errors.";
                                }

                            } // container redirects-not-sent

                        } // container statistics

                    } // container summary

                } // list http-error-redirect

                list http-notification {
                    key "http-notification-name";
                    description "Enter the http-notification list instance";

                    leaf http-notification-name {
                        type types-sros:named-item;
                        description "Specifies the name of the AA group HTTP notification object.";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            leaf notified {
                                type yang:counter64;
                                description "The number of times the script URL was inserted into a message.";
                            }

                            leaf notified-success {
                                type yang:counter64;
                                description "The number of times a HTTP notification success report was received.";
                            }

                            leaf criteria-not-matched {
                                type yang:counter64;
                                description
                                    "The number of messages which did not match the selection criteria
                                     for insertion of the script URL.";
                            }

                            leaf notified-failure {
                                type yang:counter64;
                                description "The number of times a HTTP notification is known to have failed.";
                            }

                        } // container statistics

                    } // list esa

                    list isa {
                        key "mda-id";
                        description "Enter the isa list instance";

                        leaf mda-id {
                            type types-isa:slot-mda;
                            description "MDA/ISA ID";
                        }

                        container statistics {
                            description "Enter the statistics context";

                            leaf notified {
                                type yang:counter64;
                                description "The number of times the script URL was inserted into a message.";
                            }

                            leaf notified-success {
                                type yang:counter64;
                                description "The number of times a HTTP notification success report was received.";
                            }

                            leaf criteria-not-matched {
                                type yang:counter64;
                                description
                                    "The number of messages which did not match the selection criteria
                                     for insertion of the script URL.";
                            }

                            leaf notified-failure {
                                type yang:counter64;
                                description "The number of times a HTTP notification is known to have failed.";
                            }

                        } // container statistics

                    } // list isa

                    container summary {
                        description "Enter the summary context";

                        container statistics {
                            description "Enter the statistics context";

                            leaf notified {
                                type yang:counter64;
                                description "The number of times the script URL was inserted into a message.";
                            }

                            leaf notified-success {
                                type yang:counter64;
                                description "The number of times a HTTP notification success report was received.";
                            }

                            leaf criteria-not-matched {
                                type yang:counter64;
                                description
                                    "The number of messages which did not match the selection criteria
                                     for insertion of the script URL.";
                            }

                            leaf notified-failure {
                                type yang:counter64;
                                description "The number of times a HTTP notification is known to have failed.";
                            }

                        } // container statistics

                    } // container summary

                } // list http-notification

                list http-redirect {
                    key "http-redirect-name";
                    description "Enter the http-redirect list instance";

                    leaf http-redirect-name {
                        type types-sros:named-item;
                        description "Specifies the name of the AA group HTTP redirect object.";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            leaf redirects-sent {
                                type yang:counter64;
                                description "The number of redirected sessions.";
                            }

                            leaf client-resets-sent {
                                type yang:counter64;
                                description "The number of TCP client resets that have been sent.";
                            }

                            container redirects-not-sent {
                                description "Enter the redirects-not-sent context";

                                leaf out-of-resources {
                                    type yang:counter64;
                                    description "The number of sessions that were not redirected due to lack of resources.";
                                }

                                leaf config-errors {
                                    type yang:counter64;
                                    description "The number of sessions that were not redirected due to configuration errors.";
                                }

                                leaf other-errors {
                                    type yang:counter64;
                                    description "The number of sessions that were not redirected due to traffic attributes.";
                                }

                            } // container redirects-not-sent

                        } // container statistics

                    } // list esa

                    list isa {
                        key "mda-id";
                        description "Enter the isa list instance";

                        leaf mda-id {
                            type types-isa:slot-mda;
                            description "MDA/ISA ID";
                        }

                        container statistics {
                            description "Enter the statistics context";

                            leaf redirects-sent {
                                type yang:counter64;
                                description "The number of redirected sessions.";
                            }

                            leaf client-resets-sent {
                                type yang:counter64;
                                description "The number of TCP client resets that have been sent.";
                            }

                            container redirects-not-sent {
                                description "Enter the redirects-not-sent context";

                                leaf out-of-resources {
                                    type yang:counter64;
                                    description "The number of sessions that were not redirected due to lack of resources.";
                                }

                                leaf config-errors {
                                    type yang:counter64;
                                    description "The number of sessions that were not redirected due to configuration errors.";
                                }

                                leaf other-errors {
                                    type yang:counter64;
                                    description "The number of sessions that were not redirected due to traffic attributes.";
                                }

                            } // container redirects-not-sent

                        } // container statistics

                    } // list isa

                    container summary {
                        description "Enter the summary context";

                        container statistics {
                            description "Enter the statistics context";

                            leaf redirects-sent {
                                type yang:counter64;
                                description "The number of redirected sessions.";
                            }

                            leaf client-resets-sent {
                                type yang:counter64;
                                description "The number of TCP client resets that have been sent.";
                            }

                            container redirects-not-sent {
                                description "Enter the redirects-not-sent context";

                                leaf out-of-resources {
                                    type yang:counter64;
                                    description "The number of sessions that were not redirected due to lack of resources.";
                                }

                                leaf config-errors {
                                    type yang:counter64;
                                    description "The number of sessions that were not redirected due to configuration errors.";
                                }

                                leaf other-errors {
                                    type yang:counter64;
                                    description "The number of sessions that were not redirected due to traffic attributes.";
                                }

                            } // container redirects-not-sent

                        } // container statistics

                    } // container summary

                } // list http-redirect

                list protocol {
                    key "protocol-name";
                    description "Enter the protocol list instance";

                    leaf protocol-name {
                        type types-sros:named-item;
                        description "Protocol configured to collect statistics for each aa-sub.";
                    }

                    container statistics {
                        description "Enter the statistics context";

                        leaf active-subscribers {
                            type yang:gauge32;
                            description "The number of subscribers at the most recent 5-minute snapshot of statistics.";
                        }

                        container sub-to-net {
                            description "Enter the sub-to-net context";

                            leaf active-flows {
                                type yang:counter32;
                                description "Number of allowed flows in the subscriber to network direction that are active.";
                            }

                            container admitted {
                                description "Enter the admitted context";

                                leaf octets {
                                    type yang:counter64;
                                    description "Number of bytes permitted for the subscriber to network direction.";
                                }

                                leaf packets {
                                    type yang:counter64;
                                    description "Number of packets permitted for the subscriber to network direction.";
                                }

                                leaf flows {
                                    type yang:counter64;
                                    description "Number of flows permitted for the subscriber to network direction.";
                                }

                            } // container admitted

                            container denied {
                                description "Enter the denied context";

                                leaf octets {
                                    type yang:counter64;
                                    description "Number of bytes dropped for the subscriber to network direction.";
                                }

                                leaf packets {
                                    type yang:counter64;
                                    description "Number of packets dropped for the subscriber to network direction.";
                                }

                                leaf flows {
                                    type yang:counter64;
                                    description "Number of flows that dropped subsequent packets in the subscriber to network direction.";
                                }

                            } // container denied

                        } // container sub-to-net

                        container net-to-sub {
                            description "Enter the net-to-sub context";

                            leaf active-flows {
                                type yang:counter32;
                                description "Number of allowed flows in the network to subscriber direction that are active.";
                            }

                            container admitted {
                                description "Enter the admitted context";

                                leaf octets {
                                    type yang:counter64;
                                    description "Number of bytes permitted for the network to subscriber direction.";
                                }

                                leaf packets {
                                    type yang:counter64;
                                    description "Number of packets permitted for the network to subscriber direction.";
                                }

                                leaf flows {
                                    type yang:counter64;
                                    description "Number of flows permitted for the network to subscriber direction.";
                                }

                            } // container admitted

                            container denied {
                                description "Enter the denied context";

                                leaf octets {
                                    type yang:counter64;
                                    description "Number of bytes dropped for the network to subscriber direction.";
                                }

                                leaf packets {
                                    type yang:counter64;
                                    description "Number of packets dropped for the network to subscriber direction.";
                                }

                                leaf flows {
                                    type yang:counter64;
                                    description "Number of flows that dropped subsequent packets in the network to subscriber direction.";
                                }

                            } // container denied

                        } // container net-to-sub

                        container flow {
                            description "Enter the flow context";

                            leaf terminated {
                                type yang:counter64;
                                description "Number of allowed flows in both directions that have terminated.";
                            }

                            container duration {
                                description "Enter the duration context";

                                leaf short {
                                    type yang:counter64;
                                    description "Number of flows with a duration less than or equal to 30 seconds, that have completed.";
                                }

                                leaf medium {
                                    type yang:counter64;
                                    description "Number of flows with a duration less than or equal to 180 seconds, but greater than 30 seconds, that have completed.";
                                }

                                leaf long {
                                    type yang:counter64;
                                    description "Number of flows with a duration greater than 180 seconds, that have completed.";
                                }

                                leaf total {
                                    type yang:counter64;
                                    description "The sum of all flow durations from first packet seen to last packet seen for flows that have terminated.";
                                }

                            } // container duration

                        } // container flow

                    } // container statistics

                } // list protocol

                list sctp-filter {
                    key "sctp-filter-name";
                    description "Enter the sctp-filter list instance";

                    leaf sctp-filter-name {
                        type types-sros:named-item;
                        description "SCTP filter name";
                    }

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            leaf packets-permitted {
                                type yang:counter64;
                                description "Number of packets permitted through the SCTP filter.";
                            }

                            container packets-denied {
                                description "Enter the packets-denied context";

                                leaf malformed-packet {
                                    type yang:counter64;
                                    description "Number of packets denied by the SCTP filter due to the packet being malformed.";
                                }

                                leaf ppid-out-of-range {
                                    type yang:counter64;
                                    description
                                        "Number of packets denied by the SCTP filter due to PPID being out of range of the
                                         corresponding ppid-range-mix/ppid-range-max.";
                                }

                                leaf ppid-denied {
                                    type yang:counter64;
                                    description "Number of packets denied by the SCTP filter due to PPID value configuration in ppid.";
                                }

                            } // container packets-denied

                        } // container statistics

                    } // list esa

                    list isa {
                        key "mda-id";
                        description "Enter the isa list instance";

                        leaf mda-id {
                            type types-isa:slot-mda;
                            description "MDA/ISA ID";
                        }

                        container statistics {
                            description "Enter the statistics context";

                            leaf packets-permitted {
                                type yang:counter64;
                                description "Number of packets permitted through the SCTP filter.";
                            }

                            container packets-denied {
                                description "Enter the packets-denied context";

                                leaf malformed-packet {
                                    type yang:counter64;
                                    description "Number of packets denied by the SCTP filter due to the packet being malformed.";
                                }

                                leaf ppid-out-of-range {
                                    type yang:counter64;
                                    description
                                        "Number of packets denied by the SCTP filter due to PPID being out of range of the
                                         corresponding ppid-range-mix/ppid-range-max.";
                                }

                                leaf ppid-denied {
                                    type yang:counter64;
                                    description "Number of packets denied by the SCTP filter due to PPID value configuration in ppid.";
                                }

                            } // container packets-denied

                        } // container statistics

                    } // list isa

                    container summary {
                        description "Enter the summary context";

                        container statistics {
                            description "Enter the statistics context";

                            leaf packets-permitted {
                                type yang:counter64;
                                description "Number of packets permitted through the SCTP filter.";
                            }

                            container packets-denied {
                                description "Enter the packets-denied context";

                                leaf malformed-packet {
                                    type yang:counter64;
                                    description "Number of packets denied by the SCTP filter due to the packet being malformed.";
                                }

                                leaf ppid-out-of-range {
                                    type yang:counter64;
                                    description
                                        "Number of packets denied by the SCTP filter due to PPID being out of range of the
                                         corresponding ppid-range-mix/ppid-range-max.";
                                }

                                leaf ppid-denied {
                                    type yang:counter64;
                                    description "Number of packets denied by the SCTP filter due to PPID value configuration in ppid.";
                                }

                            } // container packets-denied

                        } // container statistics

                    } // container summary

                    container ppid {
                        description "Enter the ppid context";

                        list entry {
                            key "entry-id";
                            description "Enter the entry list instance";

                            leaf entry-id {
                                type uint32 {
                                    range "1..255";
                                }
                                description "SCTP filter PPID entry ID";
                            }

                        } // list entry

                    } // container ppid

                } // list sctp-filter

                list tcp-validate {
                    key "tcp-validate-name";
                    description "Enter the tcp-validate list instance";

                    leaf tcp-validate-name {
                        type types-sros:named-item;
                        description "TCP validation policy name";
                    }

                    list direction {
                        key "traffic-direction units";
                        description "Enter the direction list instance";

                        leaf traffic-direction {
                            type types-aa:traffic-direction;
                            description "Specify direction of the traffic for tcp-validate state.";
                        }

                        leaf units {
                            type enumeration {
                                enum "octets"                       { value 1; }
                                enum "packets"                      { value 2; }
                            }
                            description "Specifies whether to request octet or packet state.";
                        }

                        list esa {
                            key "esa-id vm";
                            description "Enter the esa list instance";

                            leaf esa-id {
                                type types-esa:esa-id;
                                description "ESA ID";
                            }

                            leaf vm {
                                type types-esa:vm-id;
                                description "VM ID within the ESA";
                            }

                            container statistics {
                                description "Enter the statistics context";

                                container total {
                                    description "Enter the total context";

                                    leaf allowed {
                                        type yang:counter64;
                                        description "Number of packets/octets allowed by the TCP validation template.";
                                    }

                                    leaf dropped {
                                        type yang:counter64;
                                        description "Number of packets/octets allowed by the TCP validation template.";
                                    }

                                } // container total

                                container dropped-reason {
                                    description "Enter the dropped-reason context";

                                    leaf already-established {
                                        type yang:counter64;
                                        description "Number of packets/octets dropped by the TCP validation template due to the TCP being already established.";
                                    }

                                    leaf asymmetric-traffic {
                                        type yang:counter64;
                                        description "Number of packets/octets dropped by the TCP validation template due to asymmetric routing.";
                                    }

                                    leaf bad-flags {
                                        type yang:counter64;
                                        description "Number of packets/octets dropped by the TCP validation template due to an invalid flag.";
                                    }

                                    leaf bad-options {
                                        type yang:counter64;
                                        description "Number of packets/octets dropped by the TCP validation template due to an invalid Option.";
                                    }

                                    leaf bad-sequence-number {
                                        type yang:counter64;
                                        description "Number of packets/octets dropped by the TCP validation template due to an invalid sequence number (SEQ).";
                                    }

                                    leaf bad-acknowledgment-number {
                                        type yang:counter64;
                                        description "Number of packets/octets dropped by the TCP validation template due to an invalid acknowledgement number (ACK).";
                                    }

                                    leaf fragmented {
                                        type yang:counter64;
                                        description "Number of packets/octets dropped by the TCP validation template due to fragmentation.";
                                    }

                                    leaf not-established {
                                        type yang:counter64;
                                        description "Number of packets/octets dropped by the TCP validation template due to the TCP session not being established.";
                                    }

                                    leaf traffic-after-reset {
                                        type yang:counter64;
                                        description "Number of packets/octets dropped by the TCP validation template due to use after a reset (RST).";
                                    }

                                } // container dropped-reason

                            } // container statistics

                        } // list esa

                        list isa {
                            key "mda-id";
                            description "Enter the isa list instance";

                            leaf mda-id {
                                type types-isa:slot-mda;
                                description "MDA/ISA ID";
                            }

                            container statistics {
                                description "Enter the statistics context";

                                container total {
                                    description "Enter the total context";

                                    leaf allowed {
                                        type yang:counter64;
                                        description "Number of packets/octets allowed by the TCP validation template.";
                                    }

                                    leaf dropped {
                                        type yang:counter64;
                                        description "Number of packets/octets allowed by the TCP validation template.";
                                    }

                                } // container total

                                container dropped-reason {
                                    description "Enter the dropped-reason context";

                                    leaf already-established {
                                        type yang:counter64;
                                        description "Number of packets/octets dropped by the TCP validation template due to the TCP being already established.";
                                    }

                                    leaf asymmetric-traffic {
                                        type yang:counter64;
                                        description "Number of packets/octets dropped by the TCP validation template due to asymmetric routing.";
                                    }

                                    leaf bad-flags {
                                        type yang:counter64;
                                        description "Number of packets/octets dropped by the TCP validation template due to an invalid flag.";
                                    }

                                    leaf bad-options {
                                        type yang:counter64;
                                        description "Number of packets/octets dropped by the TCP validation template due to an invalid Option.";
                                    }

                                    leaf bad-sequence-number {
                                        type yang:counter64;
                                        description "Number of packets/octets dropped by the TCP validation template due to an invalid sequence number (SEQ).";
                                    }

                                    leaf bad-acknowledgment-number {
                                        type yang:counter64;
                                        description "Number of packets/octets dropped by the TCP validation template due to an invalid acknowledgement number (ACK).";
                                    }

                                    leaf fragmented {
                                        type yang:counter64;
                                        description "Number of packets/octets dropped by the TCP validation template due to fragmentation.";
                                    }

                                    leaf not-established {
                                        type yang:counter64;
                                        description "Number of packets/octets dropped by the TCP validation template due to the TCP session not being established.";
                                    }

                                    leaf traffic-after-reset {
                                        type yang:counter64;
                                        description "Number of packets/octets dropped by the TCP validation template due to use after a reset (RST).";
                                    }

                                } // container dropped-reason

                            } // container statistics

                        } // list isa

                        container summary {
                            description "Enter the summary context";

                            container statistics {
                                description "Enter the statistics context";

                                container total {
                                    description "Enter the total context";

                                    leaf allowed {
                                        type yang:counter64;
                                        description "Number of packets/octets allowed by the TCP validation template.";
                                    }

                                    leaf dropped {
                                        type yang:counter64;
                                        description "Number of packets/octets allowed by the TCP validation template.";
                                    }

                                } // container total

                                container dropped-reason {
                                    description "Enter the dropped-reason context";

                                    leaf already-established {
                                        type yang:counter64;
                                        description "Number of packets/octets dropped by the TCP validation template due to the TCP being already established.";
                                    }

                                    leaf asymmetric-traffic {
                                        type yang:counter64;
                                        description "Number of packets/octets dropped by the TCP validation template due to asymmetric routing.";
                                    }

                                    leaf bad-flags {
                                        type yang:counter64;
                                        description "Number of packets/octets dropped by the TCP validation template due to an invalid flag.";
                                    }

                                    leaf bad-options {
                                        type yang:counter64;
                                        description "Number of packets/octets dropped by the TCP validation template due to an invalid Option.";
                                    }

                                    leaf bad-sequence-number {
                                        type yang:counter64;
                                        description "Number of packets/octets dropped by the TCP validation template due to an invalid sequence number (SEQ).";
                                    }

                                    leaf bad-acknowledgment-number {
                                        type yang:counter64;
                                        description "Number of packets/octets dropped by the TCP validation template due to an invalid acknowledgement number (ACK).";
                                    }

                                    leaf fragmented {
                                        type yang:counter64;
                                        description "Number of packets/octets dropped by the TCP validation template due to fragmentation.";
                                    }

                                    leaf not-established {
                                        type yang:counter64;
                                        description "Number of packets/octets dropped by the TCP validation template due to the TCP session not being established.";
                                    }

                                    leaf traffic-after-reset {
                                        type yang:counter64;
                                        description "Number of packets/octets dropped by the TCP validation template due to use after a reset (RST).";
                                    }

                                } // container dropped-reason

                            } // container statistics

                        } // container summary

                    } // list direction

                } // list tcp-validate

                container tls-traffic {
                    description "Enter the tls-traffic context";

                    list esa {
                        key "esa-id vm";
                        description "Enter the esa list instance";

                        leaf esa-id {
                            type types-esa:esa-id;
                            description "ESA ID";
                        }

                        leaf vm {
                            type types-esa:vm-id;
                            description "VM ID within the ESA";
                        }

                        container statistics {
                            description "Enter the statistics context";

                            container quic {
                                description "Enter the quic context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic

                            container quic-esni {
                                description "Enter the quic-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-esni

                            container quic-existing {
                                description "Enter the quic-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-existing

                            container quic-unknown {
                                description "Enter the quic-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-unknown

                            container tls-1-0 {
                                description "Enter the tls-1-0 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-0

                            container tls-1-1 {
                                description "Enter the tls-1-1 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-1

                            container tls-1-2 {
                                description "Enter the tls-1-2 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-2

                            container tls-1-3 {
                                description "Enter the tls-1-3 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3

                            container tls-1-3-esni {
                                description "Enter the tls-1-3-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3-esni

                            container tls-existing {
                                description "Enter the tls-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-existing

                            container tls-unknown {
                                description "Enter the tls-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-unknown

                        } // container statistics

                    } // list esa

                    list isa {
                        key "mda-id";
                        description "Enter the isa list instance";

                        leaf mda-id {
                            type types-isa:slot-mda;
                            description "MDA/ISA ID";
                        }

                        container statistics {
                            description "Enter the statistics context";

                            container quic {
                                description "Enter the quic context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic

                            container quic-esni {
                                description "Enter the quic-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-esni

                            container quic-existing {
                                description "Enter the quic-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-existing

                            container quic-unknown {
                                description "Enter the quic-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-unknown

                            container tls-1-0 {
                                description "Enter the tls-1-0 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-0

                            container tls-1-1 {
                                description "Enter the tls-1-1 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-1

                            container tls-1-2 {
                                description "Enter the tls-1-2 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-2

                            container tls-1-3 {
                                description "Enter the tls-1-3 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3

                            container tls-1-3-esni {
                                description "Enter the tls-1-3-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3-esni

                            container tls-existing {
                                description "Enter the tls-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-existing

                            container tls-unknown {
                                description "Enter the tls-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-unknown

                        } // container statistics

                    } // list isa

                    container summary {
                        description "Enter the summary context";

                        container statistics {
                            description "Enter the statistics context";

                            container quic {
                                description "Enter the quic context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic

                            container quic-esni {
                                description "Enter the quic-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-esni

                            container quic-existing {
                                description "Enter the quic-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-existing

                            container quic-unknown {
                                description "Enter the quic-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container quic-unknown

                            container tls-1-0 {
                                description "Enter the tls-1-0 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-0

                            container tls-1-1 {
                                description "Enter the tls-1-1 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-1

                            container tls-1-2 {
                                description "Enter the tls-1-2 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-2

                            container tls-1-3 {
                                description "Enter the tls-1-3 context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3

                            container tls-1-3-esni {
                                description "Enter the tls-1-3-esni context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-1-3-esni

                            container tls-existing {
                                description "Enter the tls-existing context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-existing

                            container tls-unknown {
                                description "Enter the tls-unknown context";

                                container admitted {
                                    description "Enter the admitted context";

                                    leaf octets {
                                        type yang:counter64;
                                        description "Total number of bytes permitted.";
                                    }

                                    leaf packets {
                                        type yang:counter64;
                                        description "Total number of packets permitted.";
                                    }

                                    leaf flows {
                                        type yang:counter64;
                                        description "Total number of flows permitted.";
                                    }

                                } // container admitted

                                container denied {
                                    description "Enter the denied context";

                                    leaf octets {
                                        type yang:counter64;
                                        description "Total number of bytes dropped.";
                                    }

                                    leaf packets {
                                        type yang:counter64;
                                        description "Total number of packets dropped.";
                                    }

                                    leaf flows {
                                        type yang:counter64;
                                        description "Total number of flows dropped.";
                                    }

                                } // container denied

                            } // container tls-unknown

                        } // container statistics

                    } // container summary

                } // container tls-traffic

                list traffic-type {
                    key "ip-protocol ip-family";
                    description "Enter the traffic-type list instance";

                    leaf ip-protocol {
                        type enumeration {
                            enum "other"                        { value 1; }
                            enum "tcp"                          { value 2; }
                            enum "udp"                          { value 3; }
                        }
                        description "The IP Protocol for the traffic statistics.";
                    }

                    leaf ip-family {
                        type enumeration {
                            enum "ipv4"                         { value 1; }
                            enum "ipv6"                         { value 2; }
                            enum "ds-lite"                      { value 3; }
                            enum "six-rd"                       { value 4; }
                            enum "teredo"                       { value 5; }
                            enum "v4inv4-gtp"                   { value 6; }
                            enum "v4inv6-gtp"                   { value 7; }
                            enum "v6inv4-gtp"                   { value 8; }
                            enum "v6inv6-gtp"                   { value 9; }
                        }
                        description "The IP Protocol for the traffic statistics.";
                    }

                    container statistics {
                        description "Enter the statistics context";

                        container sub-to-net {
                            description "Enter the sub-to-net context";

                            leaf active-flows {
                                type yang:counter32;
                                description "Number of allowed flows in the subscriber to network direction that are active.";
                            }

                            container admitted {
                                description "Enter the admitted context";

                                leaf octets {
                                    type yang:counter64;
                                    description "Number of bytes permitted for the subscriber to network direction.";
                                }

                                leaf packets {
                                    type yang:counter64;
                                    description "Number of packets permitted for the subscriber to network direction.";
                                }

                                leaf flows {
                                    type yang:counter64;
                                    description "Number of flows permitted for the subscriber to network direction.";
                                }

                            } // container admitted

                            container denied {
                                description "Enter the denied context";

                                leaf octets {
                                    type yang:counter64;
                                    description "Number of bytes dropped for the subscriber to network direction.";
                                }

                                leaf packets {
                                    type yang:counter64;
                                    description "Number of packets dropped for the subscriber to network direction.";
                                }

                                leaf flows {
                                    type yang:counter64;
                                    description "Number of flows that dropped subsequent packets in the subscriber to network direction.";
                                }

                            } // container denied

                        } // container sub-to-net

                        container net-to-sub {
                            description "Enter the net-to-sub context";

                            leaf active-flows {
                                type yang:counter32;
                                description "Number of allowed flows in the network to subscriber direction that are active.";
                            }

                            container admitted {
                                description "Enter the admitted context";

                                leaf octets {
                                    type yang:counter64;
                                    description "Number of bytes permitted for the network to subscriber direction.";
                                }

                                leaf packets {
                                    type yang:counter64;
                                    description "Number of packets permitted for the network to subscriber direction.";
                                }

                                leaf flows {
                                    type yang:counter64;
                                    description "Number of flows permitted for the network to subscriber direction.";
                                }

                            } // container admitted

                            container denied {
                                description "Enter the denied context";

                                leaf octets {
                                    type yang:counter64;
                                    description "Number of bytes dropped for the network to subscriber direction.";
                                }

                                leaf packets {
                                    type yang:counter64;
                                    description "Number of packets dropped for the network to subscriber direction.";
                                }

                                leaf flows {
                                    type yang:counter64;
                                    description "Number of flows that dropped subsequent packets in the network to subscriber direction.";
                                }

                            } // container denied

                        } // container net-to-sub

                        container flow {
                            description "Enter the flow context";

                            leaf terminated {
                                type yang:counter64;
                                description "Number of allowed flows in both directions that have terminated.";
                            }

                            container duration {
                                description "Enter the duration context";

                                leaf short {
                                    type yang:counter64;
                                    description "Number of flows with a duration less than or equal to 30 seconds, that have completed.";
                                }

                                leaf medium {
                                    type yang:counter64;
                                    description "Number of flows with a duration less than or equal to 180 seconds, but greater than 30 seconds, that have completed.";
                                }

                                leaf long {
                                    type yang:counter64;
                                    description "Number of flows with a duration greater than 180 seconds, that have completed.";
                                }

                                leaf total {
                                    type yang:counter64;
                                    description "The sum of all flow durations from first packet seen to last packet seen for flows that have terminated.";
                                }

                            } // container duration

                        } // container flow

                    } // container statistics

                } // list traffic-type

                list session-filter {
                    key "session-filter-name";
                    description "Enter the session-filter list instance";

                    leaf session-filter-name {
                        type types-sros:named-item;
                        description "Session filter name";
                    }

                    list entry {
                        key "entry-id";
                        description "Enter the entry list instance";

                        leaf entry-id {
                            type uint32 {
                                range "1..65535";
                            }
                            description "Entry ID for the session filter entry";
                        }

                        container statistics {
                            description "Enter the statistics context";

                            leaf hits {
                                type yang:counter64;
                                description "The number of flows that have hit this entry.";
                            }

                        } // container statistics

                    } // list entry

                } // list session-filter

                container policy {
                    description "Enter the policy context";

                    container app-filter {
                        description "Enter the app-filter context";

                        list entry {
                            key "entry-id";
                            description "Enter the entry list instance";

                            leaf entry-id {
                                type uint32 {
                                    range "1..65535";
                                }
                                description "Application filter entry ID";
                            }

                            container statistics {
                                description "Enter the statistics context";

                                leaf flows {
                                    type yang:counter64;
                                    description "Number of flows that have matched this entry.";
                                }

                                leaf octets {
                                    type yang:counter64;
                                    description "Number of octets in the flows that have matched this entry.";
                                }

                            } // container statistics

                        } // list entry

                    } // container app-filter

                    container app-qos-policy {
                        description "Enter the app-qos-policy context";

                        list entry {
                            key "entry-id";
                            description "Enter the entry list instance";

                            leaf entry-id {
                                type uint32 {
                                    range "1..65535";
                                }
                                description "AQP entry ID";
                            }

                            container statistics {
                                description "Enter the statistics context";

                                leaf hits {
                                    type yang:counter64;
                                    description "The number of flows that have hit this entry.";
                                }

                                leaf conflicts {
                                    type yang:counter64;
                                    description "The number of flows that have hit this AQP entry, but resulted in a conflict with the match criteria.";
                                }

                            } // container statistics

                        } // list entry

                    } // container app-qos-policy

                } // container policy

                list transit-ip-policy {
                    key "ip-policy-id";
                    description "Enter the transit-ip-policy list instance";

                    leaf ip-policy-id {
                        type uint32 {
                            range "1..65535";
                        }
                        description "IP transit policy ID";
                    }

                    leaf ipv4-entries {
                        type uint32;
                        description "The number of IPv4 address entries within this transit IP policy.";
                    }

                    leaf ipv6-entries {
                        type uint32;
                        description "The number of IPv6 address entries within this transit IP policy.";
                    }

                    leaf subscribers {
                        type uint32;
                        description "The number of subscribers within this transit IP policy.";
                    }

                    list static-aa-sub {
                        key "transit-aa-sub-name";
                        description "Enter the static-aa-sub list instance";

                        leaf transit-aa-sub-name {
                            type types-sros:named-item;
                            description "Static transit subscriber name";
                        }

                        leaf address-count {
                            type uint32;
                            description
                                "The total number of IP addresses that reference this transit
                                 subscriber in the transit-ip-policy.";
                        }

                    } // list static-aa-sub

                    list summary {
                        key "transit-aa-sub-name address";
                        description "Enter the summary list instance";

                        leaf transit-aa-sub-name {
                            type types-sros:named-item;
                            description "A name that uniquely identifies a transit subscriber name.";
                        }

                        leaf address {
                            type types-sros:ip-address;
                            description "AA static transit subscriber ip-address.";
                        }

                        leaf app-profile-name {
                            type types-sros:named-item;
                            description "The name of the application profile to be applied to the subscriber.";
                        }

                        leaf origin {
                            type types-aa:trans-sub-orig;
                            description "The way the transit subscriber was created.";
                        }

                    } // list summary

                } // list transit-ip-policy

                list transit-prefix-policy {
                    key "prefix-policy-id";
                    description "Enter the transit-prefix-policy list instance";

                    leaf prefix-policy-id {
                        type uint32 {
                            range "1..65535";
                        }
                        description "Transit prefix policy ID";
                    }

                    leaf subscribers {
                        type uint32;
                        description "The total number of subscribers within this transit prefix policy.";
                    }

                    leaf entries {
                        type uint32;
                        description "The total number of entries within this transit prefix policy.";
                    }

                    leaf ipv4-entries {
                        type uint32;
                        description "The total number of valid IPv4 entries within this transit prefix policy";
                    }

                    leaf ipv6-entries {
                        type uint32;
                        description "The total number of valid IPv6 entries within this transit prefix policy";
                    }

                } // list transit-prefix-policy

                container cflowd {
                    description "Enter the cflowd context";

                    list export-type {
                        key "flow-export-type";
                        description "Enter the export-type list instance";

                        leaf flow-export-type {
                            type types-aa:cflowd-export-type;
                            description "Cflowd flow export type for the partition";
                        }

                        container statistics {
                            description "Enter the statistics context";

                            leaf records-reported {
                                type yang:counter64;
                                description "The total number of flow records reported.";
                            }

                            leaf records-dropped {
                                type yang:counter64;
                                description "The total number of flow records dropped.";
                            }

                            leaf flows-not-allocated {
                                type yang:counter64;
                                description
                                    "The total number of flows that were selected for export
                                     but failed to obtain Cflowd resources.";
                            }

                            leaf unsupported-ssrc-streams {
                                type yang:counter64;
                                description
                                    "The number of synchronization source (SSRC) records which had to
                                     be aborted (due to reasons such as unknown codec type, non media stream, codec switch, etc).";
                            }

                        } // container statistics

                    } // list export-type

                } // container cflowd

                container threshold-crossing-alert {
                    description "Enter the threshold-crossing-alert context";

                    list criteria {
                        key "criteria-id direction";
                        description "Enter the criteria list instance";

                        leaf criteria-id {
                            type types-aa:tca-criteria;
                            description "Statistics TCA criteria ID";
                        }

                        leaf direction {
                            type types-aa:tca-direction;
                            description "Direction of traffic for the criteria statistics TCA";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list criteria

                    list gtp-filter {
                        key "gtp-filter-name criteria direction";
                        description "Enter the gtp-filter list instance";

                        leaf gtp-filter-name {
                            type leafref {
                                path "../../../gtp/gtp-filter/gtp-filter-name";
                            }
                            description "GTP filter name for TCA generation";
                        }

                        leaf criteria {
                            type types-aa:tca-gtp-criteria;
                            description "Criteria ID for GTP filter TCA";
                        }

                        leaf direction {
                            type types-aa:tca-direction;
                            description "Direction of traffic for the GTP filter TCA";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list gtp-filter

                    list gtp-filter-entry {
                        key "gtp-filter-name entry-id direction";
                        description "Enter the gtp-filter-entry list instance";

                        leaf gtp-filter-name {
                            type leafref {
                                path "../../../gtp/gtp-filter/gtp-filter-name";
                            }
                            description "AA GTP filter name for TCA configuration";
                        }

                        leaf entry-id {
                            type uint32;
                            description "Entry ID";
                        }

                        leaf direction {
                            type types-aa:tca-direction;
                            description "Traffic direction for GTP filter entry TCA";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list gtp-filter-entry

                    list session-filter {
                        key "session-filter-name criteria direction";
                        description "Enter the session-filter list instance";

                        leaf session-filter-name {
                            type leafref {
                                path "../../../session-filter/session-filter-name";
                            }
                            description "AA session filter name for TCA configuration";
                        }

                        leaf criteria {
                            type types-aa:tca-session-criteria;
                            description "ID for session filter entry TCA";
                        }

                        leaf direction {
                            type types-aa:tca-direction;
                            description "Direction of traffic for TCA configuration";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list session-filter

                    list session-filter-entry {
                        key "session-filter-name entry-id direction";
                        description "Enter the session-filter-entry list instance";

                        leaf session-filter-name {
                            type leafref {
                                path "../../../session-filter/session-filter-name";
                            }
                            description "AA session filter name for TCA configuration";
                        }

                        leaf entry-id {
                            type leafref {
                                path "../../../session-filter[session-filter-name=current()/../session-filter-name]/entry/entry-id";
                            }
                            description "ID for session filter entry TCA";
                        }

                        leaf direction {
                            type types-aa:tca-direction;
                            description "Direction of traffic for TCA configuration";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list session-filter-entry

                    list sctp-filter {
                        key "sctp-filter-name criteria direction";
                        description "Enter the sctp-filter list instance";

                        leaf sctp-filter-name {
                            type leafref {
                                path "../../../sctp-filter/sctp-filter-name";
                            }
                            description "SCTP filter name for TCA generation";
                        }

                        leaf criteria {
                            type types-aa:tca-sctp-criteria;
                            description "Criteria ID for SCTP filter TCA";
                        }

                        leaf direction {
                            type types-aa:tca-direction;
                            description "Direction of traffic for SCTP filter TCA";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list sctp-filter

                    list sctp-filter-entry {
                        key "sctp-filter-name entry-id direction";
                        description "Enter the sctp-filter-entry list instance";

                        leaf sctp-filter-name {
                            type leafref {
                                path "../../../sctp-filter/sctp-filter-name";
                            }
                            description "AA SCTP filter name for TCA configuration";
                        }

                        leaf entry-id {
                            type leafref {
                                path "../../../sctp-filter[sctp-filter-name=current()/../sctp-filter-name]/ppid/entry/entry-id";
                            }
                            description "ID for SCTP filter entry TCA";
                        }

                        leaf direction {
                            type types-aa:tca-direction;
                            description "Direction of traffic for TCA configuration";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list sctp-filter-entry

                    list policer {
                        key "policer-name direction";
                        description "Enter the policer list instance";

                        leaf policer-name {
                            type types-sros:named-item;
                            description "Policer name for TCA generation";
                        }

                        leaf direction {
                            type types-aa:tca-direction;
                            description "Direction of traffic for the policer TCA";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list policer

                    list tcp-validate {
                        key "tcp-validate-name direction";
                        description "Enter the tcp-validate list instance";

                        leaf tcp-validate-name {
                            type leafref {
                                path "../../../tcp-validate/tcp-validate-name";
                            }
                            description "AA TCP validate name for configuration";
                        }

                        leaf direction {
                            type types-aa:tca-direction;
                            description "Direction of traffic for TCA configuration";
                        }

                        leaf last-raised {
                            type yang:date-and-time;
                            description "The last time, since system startup, when the tca-state changed from 'cleared' to 'raised'.";
                        }

                        leaf last-cleared {
                            type yang:date-and-time;
                            description "The last time, since system startup, when the tca-state changed from 'cleared' to 'raised'.";
                        }

                        leaf state {
                            type types-aa:tca-state;
                            description "The state of the Threshold Crossing Alert.";
                        }

                        leaf trigger-type {
                            type types-aa:tca-trigger-type;
                            description "The trigger type used.";
                        }

                    } // list tcp-validate

                } // container threshold-crossing-alert

            } // list partition

        } // list group

    } // grouping state-aa-group

}
