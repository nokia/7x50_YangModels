submodule nokia-state-port-network {

    yang-version "1.1";

    belongs-to nokia-state { prefix "state"; }

    import ietf-yang-types                { prefix "yang"; }
    import nokia-sros-yang-extensions     { prefix "sros-ext"; }
    import nokia-types-qos                { prefix "types-qos"; }
    import nokia-types-sros               { prefix "types-sros"; }


    sros-ext:sros-major-release "rel21";

    organization "Nokia";

    contact
        "Nokia SR OS Support
         Web: <http://www.nokia.com>";

    description
        "Nokia YANG Data model with operational state for network port parameters on SR OS based routers.

         Copyright 2016 Nokia. All rights reserved. Reproduction of this document
         is authorized on the condition that the foregoing copyright notice is included.

         This nokia-state-port-network YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-07-08";

    grouping state-port-network {
        container network {
            description "Enter the network context";

            container egress {
                description "Enter the egress context";

                list pool {
                    key "name";
                    description "Enter the pool list instance";

                    leaf name {
                        type types-sros:named-item;
                        description "Pool name";
                    }

                    container pool-usage {
                        description "Enter the pool-usage context";

                        leaf total-pool-size {
                            type uint32;
                            units "kilobytes";
                            description "Total buffer pools size.";
                        }

                        leaf total-pool-in-use {
                            type uint32;
                            units "kilobytes";
                            description "Total buffer pools size in use.";
                        }

                        leaf shared-pool-size {
                            type uint32;
                            units "kilobytes";
                            description "Total shared pools size.";
                        }

                        leaf shared-pool-in-use {
                            type uint32;
                            units "kilobytes";
                            description "Total shared pools size in use.";
                        }

                        leaf reserved-pool-size {
                            type uint32;
                            units "kilobytes";
                            description "Total reserved pools size.";
                        }

                        leaf reserved-pool-in-use {
                            type uint32;
                            units "kilobytes";
                            description "Total reserved pools size in use.";
                        }

                    } // container pool-usage

                } // list pool

                list queue {
                    key "queue-id";
                    description "Enter the queue list instance";

                    leaf queue-id {
                        type uint32 {
                            range "1..16";
                        }
                        description "The identifier which uniquely identifies a network egress queue for the port.";
                    }

                    container statistics {
                        description "Enter the statistics context";

                        leaf in-profile-forwarded-packets {
                            type yang:counter64;
                            description "Indicates the number of conforming network packets forwarded on the port for the queue.";
                        }

                        leaf in-profile-forwarded-octets {
                            type yang:counter64;
                            description "Indicates the number of conforming network octets forwarded on the port for the queue.";
                        }

                        leaf in-profile-dropped-packets {
                            type yang:counter64;
                            description "Indicates the number of conforming network packets dropped on the port for the queue.";
                        }

                        leaf in-profile-dropped-octets {
                            type yang:counter64;
                            description "Indicates the number of conforming network octets dropped on the port for the queue.";
                        }

                        leaf out-profile-forwarded-packets {
                            type yang:counter64;
                            description "Indicates the number of exceeding network packets forwarded on the port for the queue.";
                        }

                        leaf out-profile-forwarded-octets {
                            type yang:counter64;
                            description "Indicates the number of exceeding network octets forwarded on the port for the queue.";
                        }

                        leaf out-profile-dropped-packets {
                            type yang:counter64;
                            description "Indicates the number of exceeding network packets dropped on the port for the queue.";
                        }

                        leaf out-profile-dropped-octets {
                            type yang:counter64;
                            description "Indicates the number of exceeding network octets dropped on the port for the queue.";
                        }

                    } // container statistics

                    list hardware-queue {
                        key "hardware-queue-string";
                        description "Enter the hardware-queue list instance";

                        leaf hardware-queue-string {
                            type types-sros:named-item-255;
                            description "Name of the queue formatted by IOM.";
                        }

                        leaf adapted-admin-mbs {
                            type types-qos:bytes;
                            units "bytes";
                            description "Admin MBS.";
                        }

                        leaf exceed-droptail {
                            type types-qos:queue-burst-size-64-override-max;
                            description "Exceed droptail.";
                        }

                        leaf high-droptail {
                            type types-qos:queue-burst-size-64-override-max;
                            description "High droptail.";
                        }

                        leaf high-plus-droptail {
                            type types-qos:queue-burst-size-64-override-max;
                            description "Highplus droptail.";
                        }

                        leaf low-droptail {
                            type types-qos:queue-burst-size-64-override-max;
                            description "Low droptail.";
                        }

                        leaf operational-cbs {
                            type types-qos:bytes;
                            units "bytes";
                            description "Oper CBS.";
                        }

                        leaf operational-cir {
                            type types-qos:int-max;
                            description "Oper CIR.";
                        }

                        leaf operational-mbs {
                            type types-qos:bytes;
                            units "bytes";
                            description "Oper MBS.";
                        }

                        leaf operational-pir {
                            type types-qos:int-max;
                            description "Oper PIR.";
                        }

                        leaf burst-limit {
                            type union {
                                type int32;
                                type enumeration {
                                    enum "auto"                         { value -1; }
                                }
                            }
                            description "Oper burst limit.";
                        }

                    } // list hardware-queue

                } // list queue

            } // container egress

            container ingress {
                description "Enter the ingress context";

                list queue {
                    key "queue-id";
                    description "Enter the queue list instance";

                    leaf queue-id {
                        type uint32 {
                            range "1..16";
                        }
                        description "The identifier which uniquely identifies a network ingress queue on the port.";
                    }

                    container statistics {
                        description "Enter the statistics context";

                        leaf in-profile-forwarded-packets {
                            type yang:counter64;
                            description "Indicates the number of conforming network packets forwarded on the port for the queue.";
                        }

                        leaf in-profile-forwarded-octets {
                            type yang:counter64;
                            description "Indicates the number of conforming network octets forwarded on the port for the queue.";
                        }

                        leaf in-profile-dropped-packets {
                            type yang:counter64;
                            description "Indicates the number of conforming network packets dropped on the port for the queue.";
                        }

                        leaf in-profile-dropped-octets {
                            type yang:counter64;
                            description "Indicates the number of conforming network octets dropped on the port for the queue.";
                        }

                        leaf out-profile-forwarded-packets {
                            type yang:counter64;
                            description "Indicates the number of exceeding network packets forwarded on the port for the queue.";
                        }

                        leaf out-profile-forwarded-octets {
                            type yang:counter64;
                            description "Indicates the number of exceeding network octets forwarded on the port for the queue.";
                        }

                        leaf out-profile-dropped-packets {
                            type yang:counter64;
                            description "Indicates the number of exceeding network packets dropped on the port for the queue.";
                        }

                        leaf out-profile-dropped-octets {
                            type yang:counter64;
                            description "Indicates the number of exceeding network octets dropped on the port for the queue.";
                        }

                    } // container statistics

                } // list queue

            } // container ingress

        } // container network

    } // grouping state-port-network

}
