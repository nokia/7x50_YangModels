submodule nokia-conf-svc-ies {

    yang-version "1.1";

    belongs-to nokia-conf { prefix "conf"; }

    import ietf-yang-types                { prefix "yang"; }
    import nokia-sros-yang-extensions     { prefix "sros-ext"; }
    import nokia-types-eth-cfm            { prefix "types-eth-cfm"; }
    import nokia-types-ipsec              { prefix "types-ipsec"; }
    import nokia-types-qos                { prefix "types-qos"; }
    import nokia-types-router             { prefix "types-router"; }
    import nokia-types-services           { prefix "types-services"; }
    import nokia-types-sros               { prefix "types-sros"; }
    import nokia-types-subscriber-mgmt    { prefix "types-submgt"; }

    include nokia-conf-aa-group;
    include nokia-conf-application-assurance;
    include nokia-conf-bfd;
    include nokia-conf-eth-cfm;
    include nokia-conf-filter;
    include nokia-conf-filter-ip-exception;
    include nokia-conf-groups;
    include nokia-conf-ipsec;
    include nokia-conf-isa;
    include nokia-conf-log;
    include nokia-conf-policy-options;
    include nokia-conf-python;
    include nokia-conf-qos;
    include nokia-conf-router;
    include nokia-conf-router-dhcp-server;
    include nokia-conf-routing-options;
    include nokia-conf-service;
    include nokia-conf-submgt-local-user-db;
    include nokia-conf-subscriber-mgmt;
    include nokia-conf-svc-epipe;
    include nokia-conf-svc-ies-sub-if;
    include nokia-conf-svc-ies-vdo-if;
    include nokia-conf-system;
    include nokia-conf-system-security;
    include nokia-conf-test-oam;
    include nokia-conf-vrrp;


    sros-ext:sros-major-release "rel21";

    organization "Nokia";

    contact
        "Nokia SR OS Support
         Web: <http://www.nokia.com>";

    description
        "Nokia YANG Data model to configure ies services on SR OS based routers.

         Copyright 2016 Nokia. All rights reserved. Reproduction of this document
         is authorized on the condition that the foregoing copyright notice is included.

         This nokia-conf-svc-ies YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-11-08";

    grouping conf-svc-ies {
        list ies {
            key "service-name";
            description "Enter the ies list instance";

            leaf service-name {
                type types-services:service-name;
                description "Administrative service name";
            }

            leaf service-id {
                type types-services:external-service-id;
                sros-ext:immutable;
                description "Service ID";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the service";
            }

            leaf vpn-id {
                type types-services:vpn-id;
                sros-ext:immutable;
                description "VPN identifier for the service";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container eth-cfm {
                description "Enter the eth-cfm context";

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container eth-cfm

            list aa-interface {
                key "interface-name";
                description "Enter the aa-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list sap {
                    key "sap-id";
                    max-elements 1;
                    description "Enter the sap list instance";

                    leaf sap-id {
                        type types-sros:sap;
                        description "SAP ID";
                    }

                    leaf description {
                        type types-sros:long-description;
                        description "Text description";
                    }

                    leaf admin-state {
                        type types-sros:admin-state;
                        default "enable";
                        description "Administrative state of the SAP";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        container qos {
                            description "Enter the qos context";

                            container sap-ingress {
                                description "Enter the sap-ingress context";

                                leaf policy-name {
                                    type leafref {
                                        path "../../../../../../../../qos/sap-ingress/sap-ingress-policy-name";
                                    }
                                    description "Policy ID";
                                }

                                container overrides {
                                    description "Enter the overrides context";

                                } // container overrides

                            } // container sap-ingress

                        } // container qos

                    } // container ingress

                    container egress {
                        description "Enter the egress context";

                        container qos {
                            description "Enter the qos context";

                            container sap-egress {
                                description "Enter the sap-egress context";

                                leaf policy-name {
                                    type leafref {
                                        path "../../../../../../../../qos/sap-egress/sap-egress-policy-name";
                                    }
                                    description "Policy ID to associate with SAP for mirrored service";
                                }

                            } // container sap-egress

                        } // container qos

                        container filter {
                            description "Enter the filter context";

                            leaf ip {
                                type leafref {
                                    path "../../../../../../../filter/ip-filter/filter-name";
                                }
                                description "IPv4 filter policy name";
                            }

                        } // container filter

                    } // container egress

                    container lag {
                        description "Enter the lag context";

                    } // container lag

                    container fwd-wholesale {
                        description "Enter the fwd-wholesale context";

                        leaf pppoe-service {
                            type leafref {
                                path "../../../../../epipe/service-name";
                            }
                            description "PPPoE service name";
                        }

                    } // container fwd-wholesale

                } // list sap

                container ipv4 {
                    description "Enter the ipv4 context";

                    container primary {
                        presence "Enable the primary context";
                        description "Enter the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                } // container ipv4

            } // list aa-interface

            list interface {
                key "interface-name";
                description "Enter the interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf radius-auth-policy {
                    type leafref {
                        path "../../../../subscriber-mgmt/radius-authentication-policy/name";
                    }
                    description "Authentication policy";
                }

                leaf tunnel {
                    type boolean;
                    sros-ext:immutable;
                    default "false";
                    description "Enable/disable tunnel interface";
                }

                leaf loopback {
                    type boolean;
                    default "false";
                    description "Use interface as a loopback interface";
                }

                leaf monitor-oper-group {
                    type leafref {
                        path "../../../oper-group/name";
                    }
                    description "Operational group to monitor";
                }

                leaf shcv-policy-ipv4 {
                    when "not(../tunnel = 'true')";
                    type leafref {
                        path "../../../../subscriber-mgmt/shcv-policy/name";
                    }
                    description "Host connectivity IPv4 policy";
                }

                leaf cpu-protection {
                    type leafref {
                        path "../../../../system/security/cpu-protection/policy/policy-id";
                    }
                    description "CPU protection policy";
                }

                leaf ip-mtu {
                    type types-router:ip-mtu-ext;
                    units "bytes";
                    description "IP MTU applied to outgoing packets";
                }

                leaf mac {
                    type types-sros:mac-unicast-address;
                    description "MAC address for the interface";
                }

                leaf tos-marking-state {
                    type types-router:tos-marking-state;
                    default "untrusted";
                    description "TOS marking state";
                }

                leaf multicast-network-domain {
                    type leafref {
                        path "../../../../router/network-domains/network-domain/domain-name";
                    }
                    description "Network domain name";
                }

                leaf ingress-stats {
                    type boolean;
                    default "false";
                    description "Collect ingress statistics";
                }

                leaf mac-accounting {
                    type boolean;
                    default "false";
                    description "Enable MAC accounting functionality";
                }

                leaf vas-if-type {
                    when "../tunnel = 'false'";
                    type types-router:vas-if-type;
                    description "VAS interface type";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice shunting {
                    description "shunting options";
                    case nexthop {

                        leaf static-tunnel-redundant-nexthop {
                            type types-sros:ipv4-unicast-address;
                            description "Address for the static ISA tunnel redundant next-hop";
                        }

                        leaf dynamic-tunnel-redundant-nexthop {
                            type types-sros:ipv4-unicast-address;
                            description "Redundant next-hop address for the dynamic IPsec tunnel";
                        }

                    }
                }
                container ptp-hw-assist {
                    description "Enter the ptp-hw-assist context";

                    leaf admin-state {
                        type types-sros:admin-state;
                        default "disable";
                        description "Administrative state of the PTP timestamping assist";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ptp-hw-assist

                container ingress {
                    description "Enter the ingress context";

                    leaf policy-accounting {
                        type leafref {
                            path "../../../../../routing-options/policy-accounting/policy-acct-template/name";
                        }
                        description "Ingress policy accounting template name";
                    }

                    leaf destination-class-lookup {
                        type boolean;
                        default "false";
                        description "Enable BGP destination class lookup";
                    }

                } // container ingress

                container load-balancing {
                    description "Enter the load-balancing context";

                    leaf ip-load-balancing {
                        type types-router:ip-load-balancing;
                        default "both";
                        description "IP load-balancing algorithm";
                    }

                    leaf spi-load-balancing {
                        type boolean;
                        default "false";
                        description "Enable SPI use in hashing";
                    }

                    leaf teid-load-balancing {
                        type boolean;
                        default "false";
                        description "Enable use of TEID in hashing";
                    }

                    leaf flow-label-load-balancing {
                        type boolean;
                        default "false";
                        description "Enable flow label load balancing";
                    }

                } // container load-balancing

                container ping-template {
                    presence "Enable the ping-template context";
                    description "Enter the ping-template context";

                    leaf name {
                        type leafref {
                            path "../../../../../test-oam/icmp/ping-template/name";
                        }
                        sros-ext:immutable;
                        mandatory true;
                        description "Ping template name";
                    }

                    leaf admin-state {
                        type types-sros:admin-state;
                        default "disable";
                        description "Administrative state of the ping template";
                    }

                    leaf destination-address {
                        type types-sros:ipv4-unicast-address;
                        sros-ext:auto-restart-to-modify;
                        description "Ping template destination address";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container ping-template

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of the SDP binding to the service";
                    }

                    leaf collect-stats {
                        type boolean;
                        default "false";
                        description "Allow agent to collect accounting statistics";
                    }

                    leaf accounting-policy {
                        type leafref {
                            path "../../../../../log/accounting-policy/policy-id";
                        }
                        description "Policy to collect accounting statistics";
                    }

                    leaf control-word {
                        type boolean;
                        default "false";
                        description "Use the control word as preferred";
                    }

                    leaf app-profile {
                        type leafref {
                            path "../../../../../application-assurance/group/partition/policy/app-profile/app-profile-name";
                        }
                        description "Application profile name for this SDP";
                    }

                    leaf bfd-template {
                        status obsolete;
                        type leafref {
                            path "../../../../../bfd/bfd-template/name";
                        }
                        description "BFD template associated with SDP binding";
                    }

                    leaf vc-type {
                        type types-services:ies-sdp-bind-vc-type;
                        sros-ext:immutable;
                        default "ether";
                        description "Virtual circuit type associated with the SDP binding";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    choice label {
                        case entropy {

                            leaf entropy-label {
                                type empty;
                                description "Enable the use of entropy labels for spoke SDPs";
                            }

                        }
                        case hash {

                            container hash-label {
                                presence "Enable the hash-label context";
                                description "Enable the hash-label context";

                                leaf signal-capability {
                                    type empty;
                                    description "Enable the signaling of the hash label between PE nodes";
                                }

                            } // container hash-label

                        }
                    }
                    container ingress {
                        description "Enter the ingress context";

                        leaf vc-label {
                            type types-services:ingress-vc-label;
                            sros-ext:auto-restart-to-modify;
                            description "Ingress MPLS VC label to send packets to the far end";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Network policy ID";
                                }

                                container fp-redirect-group {
                                    description "Enter the fp-redirect-group context";

                                    leaf group-name {
                                        type leafref {
                                            path "../../../../../../../../../qos/queue-group-templates/ingress/queue-group/ingress-queue-group-name";
                                        }
                                        description "Name of the forwarding plane queue group template";
                                    }

                                    leaf instance {
                                        type types-services:qos-qgrp-instance-id;
                                        description "Instance of FP ingress queue group for the SDP binding";
                                    }

                                } // container fp-redirect-group

                            } // container network

                        } // container qos

                    } // container ingress

                    container egress {
                        description "Enter the egress context";

                        leaf vc-label {
                            type types-services:egress-vc-label;
                            sros-ext:auto-restart-to-modify;
                            description "Egress MPLS VC label to send packets to the far end";
                        }

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container qos {
                            description "Enter the qos context";

                            container network {
                                description "Enter the network context";

                                leaf policy-name {
                                    type leafref {
                                        path "../../../../../../../../qos/network/network-policy-name";
                                    }
                                    description "Network policy ID";
                                }

                                container port-redirect-group {
                                    description "Enter the port-redirect-group context";

                                    leaf group-name {
                                        type leafref {
                                            path "../../../../../../../../../qos/queue-group-templates/egress/queue-group/egress-queue-group-name";
                                        }
                                        description "Name of the egress port queue group";
                                    }

                                    leaf instance {
                                        type types-services:qos-qgrp-instance-id;
                                        description "Queue-group instance ID";
                                    }

                                } // container port-redirect-group

                            } // container network

                        } // container qos

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable the eth-cfm-monitoring context";
                                    description "Enable the eth-cfm-monitoring context";

                                    leaf aggregate {
                                        type empty;
                                        description "Apply rate limit to the sum of the per peer packet rates";
                                    }

                                    leaf car {
                                        type empty;
                                        description "Ignore Ethernet CFM packets when enforcing overall rate";
                                    }

                                } // container eth-cfm-monitoring

                            }
                            case ip {

                                leaf ip-src-monitoring {
                                    type empty;
                                    description "Enable IP source monitoring for CPU protection";
                                }

                            }
                        }
                    } // container cpu-protection

                    container aarp {
                        presence "Enable the aarp context";
                        description "Enter the aarp context";

                        leaf id {
                            type leafref {
                                path "../../../../../../application-assurance/aarp/aarp-id";
                            }
                            description "AARP instance ID";
                        }

                        leaf type {
                            type types-services:dual-homing-bsx-aarp-service-ref-type;
                            description "Role referenced by the AARP";
                        }

                    } // container aarp

                    container bfd-liveness {
                        status obsolete;
                        presence "Enable the bfd-liveness context";
                        description "Enable the bfd-liveness context";

                        leaf encap {
                            status obsolete;
                            type types-services:bfd-encap;
                            default "ipv4";
                            description "BFD encapsulation used on the SDP binding";
                        }

                    } // container bfd-liveness

                    container bfd {
                        description "Enter the bfd context";

                        leaf bfd-template {
                            type leafref {
                                path "../../../../../../bfd/bfd-template/name";
                            }
                            description "BFD template associated with the SDP binding";
                        }

                        leaf failure-action {
                            type types-services:sbind-bfd-fail-action;
                            default "none";
                            description "VCCV BFD action taken on the SDP binding";
                        }

                        leaf wait-for-up-timer {
                            type uint32 {
                                range "1..60";
                            }
                            units "seconds";
                            description "Time waited for BFD up status";
                        }

                        container bfd-liveness {
                            presence "Enable the bfd-liveness context";
                            description "Enter the bfd-liveness context";

                            leaf encap {
                                type types-services:bfd-encap;
                                default "ipv4";
                                description "BFD encapsulation used on the SDP binding";
                            }

                        } // container bfd-liveness

                    } // container bfd

                    container transit-policy {
                        presence "Enable the transit-policy context";
                        description "Enter the transit-policy context";

                        choice transit-policy {
                            mandatory true;
                            case prefix {

                                leaf prefix {
                                    type leafref {
                                        path "../../../../../../application-assurance/group/partition/transit-prefix-policy/prefix-policy-id";
                                    }
                                    sros-ext:immutable;
                                    description "IP prefix policy ID";
                                }

                            }
                            case ip {

                                leaf ip {
                                    type leafref {
                                        path "../../../../../../application-assurance/group/partition/transit-ip-policy/ip-policy-id";
                                    }
                                    sros-ext:immutable;
                                    description "IP transit policy ID";
                                }

                            }
                        }
                    } // container transit-policy

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "Levels for which ETH-CFM packets are silently discarded";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Maintenance Domain (MD) name";
                            }

                            leaf ma-admin-name {
                                type leafref {
                                    path "../../../../../../../eth-cfm/domain[md-admin-name=current()/../md-admin-name]/association/ma-admin-name";
                                }
                                description "Maintenance Association (MA) name";
                            }

                            leaf mep-id {
                                type types-eth-cfm:mep-id-type;
                                description "Maintenance Endpoint (MEP) ID";
                            }

                            leaf admin-state {
                                type types-sros:admin-state;
                                default "disable";
                                description "Administrative state of the MEP";
                            }

                            leaf description {
                                type types-sros:description;
                                description "Text description";
                            }

                            leaf low-priority-defect {
                                type types-eth-cfm:lowest-alarm-priority;
                                default "mac-rem-err-xcon";
                                description "Lowest priority defect allowed to generate fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for the one-way delay test";
                            }

                            leaf ais {
                                type boolean;
                                default "false";
                                description "Enable the generation and the reception of AIS messages";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "Enable the csf context";
                                description "Enter the csf context";

                                leaf multiplier {
                                    type decimal64 {
                                        range "0.0|2.0..30.0";
                                        fraction-digits 1;
                                    }
                                    default "3.5";
                                    description "Multiplication factor used to clear the CSF condition";
                                }

                            } // container csf

                            container eth-test {
                                presence "Enable the eth-test context";
                                description "Enable the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for Ethernet Test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED expected defect window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                } // list spoke-sdp

                container cflowd-parameters {
                    description "Enter the cflowd-parameters context";

                    list sampling {
                        key "sampling-type";
                        description "Enter the sampling list instance";

                        leaf sampling-type {
                            type types-router:cflowd-sampling;
                            description "Traffic sampling type";
                        }

                        leaf type {
                            when "not(../sampling-type = 'both')";
                            type enumeration {
                                enum "acl"                          { value 1; }
                                enum "interface"                    { value 2; }
                            }
                            mandatory true;
                            description "Type of cflowd analysis";
                        }

                        leaf direction {
                            type enumeration {
                                enum "ingress-only"                 { value 1; }
                                enum "egress-only"                  { value 2; }
                                enum "both"                         { value 3; }
                            }
                            default "ingress-only";
                            description "Direction of traffic for cflowd sampling";
                        }

                        leaf sample-profile {
                            type union {
                                type enumeration {
                                    enum "1"                            { value 1; }
                                }
                                type uint32;
                            }
                            description "Sample profile ID";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list sampling

                } // container cflowd-parameters

                list sap {
                    key "sap-id";
                    max-elements 1;
                    description "Enter the sap list instance";

                    leaf sap-id {
                        type types-sros:sap;
                        description "SAP ID";
                    }

                    leaf description {
                        type types-sros:long-description;
                        description "Text description";
                    }

                    leaf admin-state {
                        type types-sros:admin-state;
                        default "enable";
                        description "Administrative state of the SAP";
                    }

                    leaf accounting-policy {
                        type leafref {
                            path "../../../../../log/accounting-policy/policy-id";
                        }
                        description "Accounting policy";
                    }

                    leaf anti-spoof {
                        type types-services:anti-spoof-option;
                        description "Anti-spoof filtering";
                    }

                    leaf app-profile {
                        type leafref {
                            path "../../../../../application-assurance/group/partition/policy/app-profile/app-profile-name";
                        }
                        description "Application profile name";
                    }

                    leaf bandwidth {
                        type types-services:sap-bandwidth;
                        units "kilobps";
                        description "SAP bandwidth";
                    }

                    leaf calling-station-id {
                        type types-sros:string-not-all-spaces {
                            length "1..64";
                        }
                        description "Calling station ID";
                    }

                    leaf collect-stats {
                        type boolean;
                        default "false";
                        description "Collect accounting statistics";
                    }

                    leaf dist-cpu-protection {
                        type leafref {
                            path "../../../../../system/security/dist-cpu-protection/policy/policy-name";
                        }
                        description "Distributed CPU protection policy for SAP";
                    }

                    leaf host-admin-state {
                        type types-sros:admin-state;
                        default "enable";
                        description "Administrative state of host creation on the SAP";
                    }

                    leaf host-lockout-policy {
                        type leafref {
                            path "../../../../../subscriber-mgmt/host-lockout-policy/name";
                        }
                        description "Host lockout policy";
                    }

                    leaf multi-service-site {
                        type leafref {
                            path "../../../../customer/multi-service-site/multi-service-site-name";
                        }
                        description "Multi service site name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf queue-group-redirect-list {
                            type leafref {
                                path "../../../../../../qos/queue-group-redirect-list/name";
                            }
                            description "Queue group redirect list";
                        }

                        container qos {
                            description "Enter the qos context";

                            leaf match-qinq-dot1p {
                                type enumeration {
                                    enum "top"                          { value 2; }
                                    enum "bottom"                       { value 3; }
                                }
                                description "Ingress match QinQ Dot1p";
                            }

                            container sap-ingress {
                                description "Enter the sap-ingress context";

                                leaf policy-name {
                                    type leafref {
                                        path "../../../../../../../../qos/sap-ingress/sap-ingress-policy-name";
                                    }
                                    description "Policy ID";
                                }

                                leaf queuing-type {
                                    type types-services:services-sap-queuing-type;
                                    description "Queuing type";
                                }

                                container fp-redirect-group {
                                    description "Enter the fp-redirect-group context";

                                    leaf group-name {
                                        type leafref {
                                            path "../../../../../../../../../qos/queue-group-templates/ingress/queue-group/ingress-queue-group-name";
                                        }
                                        description "Queue group template name created on forwarding plane";
                                    }

                                    leaf instance {
                                        type types-services:qos-qgrp-instance-id;
                                        description "Queue group instance";
                                    }

                                } // container fp-redirect-group

                                container overrides {
                                    description "Enter the overrides context";

                                    container ip-criteria {
                                        description "Enter the ip-criteria context";

                                        leaf activate-entry-tag {
                                            type int32 {
                                                range "1..255";
                                            }
                                            description "Tag ID activated for IPv4 criteria";
                                        }

                                    } // container ip-criteria

                                    container ipv6-criteria {
                                        description "Enter the ipv6-criteria context";

                                        leaf activate-entry-tag {
                                            type int32 {
                                                range "1..255";
                                            }
                                            description "Tag ID activated for IPv6 criteria";
                                        }

                                    } // container ipv6-criteria

                                    list queue {
                                        key "queue-id";
                                        description "Enter the queue list instance";

                                        leaf queue-id {
                                            type leafref {
                                                path "../../../../../../../../../../qos/sap-ingress[sap-ingress-policy-name=current()/../../../policy-name]/queue/queue-id";
                                            }
                                            description "Policer unique ID";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            status deprecated;
                                            type boolean;
                                            default "false";
                                            description "Monitor queue depth";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container monitor-queue-depth {
                                            presence "Enable the monitor-queue-depth context";
                                            description "Enter the monitor-queue-depth context";

                                            leaf fast-polling {
                                                type boolean;
                                                default "false";
                                                description "Enable fast polling of the queue depth";
                                            }

                                        } // container monitor-queue-depth

                                    } // list queue

                                    list policer {
                                        key "policer-id";
                                        description "Enter the policer list instance";

                                        leaf policer-id {
                                            type leafref {
                                                path "../../../../../../../../../../qos/sap-ingress[sap-ingress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:ingress-per-packet-offset-override;
                                            description "Packet size modification for policing information";
                                        }

                                        leaf stat-mode {
                                            type types-qos:ingress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                } // container overrides

                            } // container sap-ingress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Enable the overrides context";
                                    description "Enable the overrides context";

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                                leaf-list apply-groups-exclude {
                                                    type leafref {
                                                        path "../../../../../../../../../../../../groups/group/name";
                                                    }
                                                    max-elements 8;
                                                    ordered-by user;
                                                    description "Exclude a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler name";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        container parent {
                                            description "Enter the parent context";

                                            leaf weight {
                                                type types-qos:weight;
                                                description "Relative weight of the scheduler to feed the queue";
                                            }

                                            leaf cir-weight {
                                                type types-qos:weight;
                                                description "Weight used at the within-CIR port priority level";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "PIR at which the queue is to operate";
                                            }

                                            leaf cir {
                                                type union {
                                                    type int64 {
                                                        range "0..6400000000";
                                                    }
                                                    type enumeration {
                                                        enum "sum"                          { value -3; }
                                                        enum "max"                          { value -1; }
                                                    }
                                                }
                                                description "CIR at which the queue it to operate";
                                            }

                                        } // container rate

                                    } // list scheduler

                                } // container overrides

                            } // container scheduler-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container aggregate-policer {
                            description "Enter the aggregate-policer context";

                            leaf rate {
                                type types-qos:aggr-policer-rate;
                                default "max";
                                description "Aggregate policer rate";
                            }

                            leaf burst {
                                type types-qos:aggr-policer-burst;
                                default "default";
                                description "Aggregate policer burst";
                            }

                            leaf cir {
                                type types-qos:aggr-policer-cir;
                                description "Aggregate policer CIR";
                            }

                            leaf cbs {
                                type types-qos:aggr-policer-cbs;
                                description "Aggregate policer CBS";
                            }

                        } // container aggregate-policer

                    } // container ingress

                    container egress {
                        description "Enter the egress context";

                        leaf queue-group-redirect-list {
                            type leafref {
                                path "../../../../../../qos/queue-group-redirect-list/name";
                            }
                            description "Assign queue-group redirect list";
                        }

                        container qos {
                            description "Enter the qos context";

                            leaf qinq-mark-top-only {
                                type boolean;
                                default "false";
                                description "Mark top Q-tags";
                            }

                            container sap-egress {
                                description "Enter the sap-egress context";

                                leaf policy-name {
                                    type leafref {
                                        path "../../../../../../../../qos/sap-egress/sap-egress-policy-name";
                                    }
                                    description "Policy ID to associate with SAP for mirrored service";
                                }

                                container port-redirect-group {
                                    description "Enter the port-redirect-group context";

                                    leaf group-name {
                                        type leafref {
                                            path "../../../../../../../../../qos/queue-group-templates/egress/queue-group/egress-queue-group-name";
                                        }
                                        description "Name of the queue group redirect list policy";
                                    }

                                    leaf instance {
                                        type types-services:qos-qgrp-instance-id;
                                        description "Instance of port queue group";
                                    }

                                } // container port-redirect-group

                                container overrides {
                                    description "Enter the overrides context";

                                    leaf hs-secondary-shaper {
                                        type types-sros:named-item;
                                        description "HS Secondary Shaper";
                                    }

                                    container hsmda-queues {
                                        status obsolete;
                                        description "Enter the hsmda-queues context";

                                        leaf secondary-shaper {
                                            status obsolete;
                                            type types-sros:named-item;
                                            description "Secondary shaper for the HSMDA queue";
                                        }

                                        leaf packet-byte-offset {
                                            status obsolete;
                                            type types-services:egress-hsmda-queue-packet-byte-offset;
                                            description "Packet byte offset for HSMDA queue";
                                        }

                                        leaf wrr-policy {
                                            status obsolete;
                                            type leafref {
                                                path "../../../../../../../../../../qos/hsmda-wrr-policy/hsmda-wrr-policy-name";
                                            }
                                            description "WRR policy for the HSMDA queue";
                                        }

                                        list queue {
                                            status obsolete;
                                            key "queue-id";
                                            description "Enter the queue list instance";

                                            leaf queue-id {
                                                status obsolete;
                                                type leafref {
                                                    path "../../../../../../../../../../../qos/sap-egress[sap-egress-policy-name=current()/../../../../policy-name]/hsmda-queues/queue/queue-id";
                                                }
                                                description "Egress HSMDA queue ID";
                                            }

                                            leaf mbs {
                                                status obsolete;
                                                type types-qos:hsmda-queue-burst-size-override;
                                                units "bytes";
                                                description "Buffer space allowed for the queue";
                                            }

                                            leaf rate {
                                                status obsolete;
                                                type types-qos:hsmda-queue-pir-rate-override;
                                                description "PIR for the queue";
                                            }

                                            leaf slope-policy {
                                                status obsolete;
                                                type leafref {
                                                    path "../../../../../../../../../../../qos/hsmda-slope-policy/hsmda-slope-policy-name";
                                                }
                                                description "Name of the slope-policy which is used to override the default slope-policy for the named buffer pool.";
                                            }

                                            leaf wrr-weight {
                                                status obsolete;
                                                type types-qos:hsmda-wrr-weight-override;
                                                description "Weight value for the HSMDA queue";
                                            }

                                            leaf-list apply-groups {
                                                status obsolete;
                                                type leafref {
                                                    path "../../../../../../../../../../../groups/group/name";
                                                }
                                                max-elements 8;
                                                ordered-by user;
                                                description "Apply a configuration group at this level";
                                            }

                                            leaf-list apply-groups-exclude {
                                                status obsolete;
                                                type leafref {
                                                    path "../../../../../../../../../../../groups/group/name";
                                                }
                                                max-elements 8;
                                                ordered-by user;
                                                description "Exclude a configuration group at this level";
                                            }

                                        } // list queue

                                    } // container hsmda-queues

                                    list queue {
                                        key "queue-id";
                                        description "Enter the queue list instance";

                                        leaf queue-id {
                                            type leafref {
                                                path "../../../../../../../../../../qos/sap-egress[sap-egress-policy-name=current()/../../../policy-name]/queue/queue-id";
                                            }
                                            description "Policer unique ID";
                                        }

                                        leaf avg-frame-overhead {
                                            type decimal64 {
                                                range "0.00..100.00";
                                                fraction-digits 2;
                                            }
                                            description "Average packet-to-frame encapsulation overhead";
                                        }

                                        leaf burst-limit {
                                            type union {
                                                type types-qos:bytes {
                                                    range "1..14000000";
                                                }
                                                type enumeration {
                                                    enum "auto"                         { value -1; }
                                                }
                                            }
                                            description "Explicit shaping burst size for the queue";
                                        }

                                        leaf cbs {
                                            type union {
                                                type uint32 {
                                                    range "0..1048576";
                                                }
                                                type enumeration {
                                                    enum "auto"                         { value -1; }
                                                }
                                            }
                                            units "kilobytes";
                                            description "CBS";
                                        }

                                        leaf mbs {
                                            type union {
                                                type types-qos:bytes {
                                                    range "0..1073741824";
                                                }
                                                type enumeration {
                                                    enum "auto"                         { value -1; }
                                                }
                                            }
                                            units "bytes";
                                            description "MBS";
                                        }

                                        leaf monitor-depth {
                                            status obsolete;
                                            type boolean;
                                            default "false";
                                            description "Monitor queue depth";
                                        }

                                        leaf hs-wrr-weight {
                                            type types-qos:hs-wrr-weight-override;
                                            default "1";
                                            description "WRR weight to parent with the queue into the scheduler";
                                        }

                                        leaf hs-class-weight {
                                            type types-qos:hs-class-weight-override;
                                            description "Class weight override for the queue";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice queue-override-rate {
                                            case rate {

                                                container rate {
                                                    description "Enter the rate context";

                                                    leaf pir {
                                                        type types-services:sap-pir-rate-ovr;
                                                        units "kilobps";
                                                        description "PIR rate";
                                                    }

                                                    leaf cir {
                                                        type types-services:sap-cir-rate-ovr;
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                        container adaptation-rule {
                                            description "Enter the adaptation-rule context";

                                            leaf pir {
                                                type types-qos:adaptation-rule-override;
                                                description "Constraint used when deriving the operational PIR value";
                                            }

                                            leaf cir {
                                                type types-qos:adaptation-rule-override;
                                                description "Constraint used when deriving the operational CIR value";
                                            }

                                        } // container adaptation-rule

                                        container drop-tail {
                                            description "Enter the drop-tail context";

                                            container low {
                                                description "Enter the low context";

                                                leaf percent-reduction-from-mbs {
                                                    type types-qos:burst-percent-or-default-override;
                                                    description "Percentage reduction from the MBS for a queue drop tail";
                                                }

                                            } // container low

                                        } // container drop-tail

                                        container parent {
                                            description "Enter the parent context";

                                            leaf weight {
                                                type types-qos:weight-override;
                                                description "PIR parameter that overrides parent for queue group";
                                            }

                                            leaf cir-weight {
                                                type types-qos:weight-override;
                                                description "CIR parameter that overrides parent for queue group";
                                            }

                                        } // container parent

                                        container monitor-queue-depth {
                                            presence "Enable the monitor-queue-depth context";
                                            description "Enter the monitor-queue-depth context";

                                            leaf fast-polling {
                                                type boolean;
                                                default "false";
                                                description "Enable fast polling of the queue depth";
                                            }

                                            leaf violation-threshold {
                                                type decimal64 {
                                                    range "0.01..99.99";
                                                    fraction-digits 2;
                                                }
                                                description "Threshold for queue depth before violation is raised";
                                            }

                                        } // container monitor-queue-depth

                                        container hs-wred-queue {
                                            description "Enter the hs-wred-queue context";

                                            leaf policy {
                                                type leafref {
                                                    path "../../../../../../../../../../../qos/slope-policy/slope-policy-name";
                                                }
                                                description "Slope policy applied to the HSQ queue group queue";
                                            }

                                        } // container hs-wred-queue

                                    } // list queue

                                    list policer {
                                        key "policer-id";
                                        description "Enter the policer list instance";

                                        leaf policer-id {
                                            type leafref {
                                                path "../../../../../../../../../../qos/sap-egress[sap-egress-policy-name=current()/../../../policy-name]/policer/policer-id";
                                            }
                                            description "Policer unique ID";
                                        }

                                        leaf cbs {
                                            type union {
                                                type types-qos:bytes {
                                                    range "0..16777216";
                                                }
                                                type enumeration {
                                                    enum "auto"                         { value -1; }
                                                }
                                            }
                                            units "bytes";
                                            description "CBS";
                                        }

                                        leaf mbs {
                                            type union {
                                                type types-qos:bytes {
                                                    range "0..1073741824";
                                                }
                                                type enumeration {
                                                    enum "auto"                         { value -1; }
                                                }
                                            }
                                            description "MBS";
                                        }

                                        leaf packet-byte-offset {
                                            type types-qos:egress-per-packet-offset-override;
                                            description "Packet size modification for policing information";
                                        }

                                        leaf stat-mode {
                                            type types-qos:egress-policer-stat-mode;
                                            description "Mode of statistics collected by the policer";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice policer-override-rate {
                                            case rate {

                                                container rate {
                                                    description "Enter the rate context";

                                                    leaf pir {
                                                        type union {
                                                            type int64 {
                                                                range "1..6400000000";
                                                            }
                                                            type enumeration {
                                                                enum "max"                          { value -1; }
                                                            }
                                                        }
                                                        units "kilobps";
                                                        description "PIR rate";
                                                    }

                                                    leaf cir {
                                                        type union {
                                                            type int64 {
                                                                range "0..6400000000";
                                                            }
                                                            type enumeration {
                                                                enum "max"                          { value -1; }
                                                            }
                                                        }
                                                        units "kilobps";
                                                        description "CIR rate";
                                                    }

                                                } // container rate

                                            }
                                            case percent-rate {

                                                container percent-rate {
                                                    description "Enter the percent-rate context";

                                                    leaf pir {
                                                        type decimal64 {
                                                            range "0.01..100.00";
                                                            fraction-digits 2;
                                                        }
                                                        description "PIR percent rate";
                                                    }

                                                    leaf cir {
                                                        type decimal64 {
                                                            range "0.00..100.00";
                                                            fraction-digits 2;
                                                        }
                                                        description "CIR percent rate";
                                                    }

                                                } // container percent-rate

                                            }
                                        }
                                    } // list policer

                                    list hs-wrr-group {
                                        key "group-id";
                                        description "Enter the hs-wrr-group list instance";

                                        leaf group-id {
                                            type leafref {
                                                path "../../../../../../../../../../qos/sap-egress[sap-egress-policy-name=current()/../../../policy-name]/hs-wrr-group/group-id";
                                            }
                                            description "HS WRR group identifier";
                                        }

                                        leaf hs-class-weight {
                                            type types-qos:hs-class-weight-override;
                                            description "Class weight override of the WRR group";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        choice rate-or-percent-rate {
                                            case rate {

                                                leaf rate {
                                                    type union {
                                                        type uint32 {
                                                            range "1..2000000000";
                                                        }
                                                        type enumeration {
                                                            enum "max"                          { value -1; }
                                                        }
                                                    }
                                                    units "kilobps";
                                                    description "Scheduling rate override applied to the HS WRR group";
                                                }

                                            }
                                            case percent-rate {

                                                leaf percent-rate {
                                                    type decimal64 {
                                                        range "0.01..100.00";
                                                        fraction-digits 2;
                                                    }
                                                    description "Percent rate override applied to the HS WRR group";
                                                }

                                            }
                                        }
                                    } // list hs-wrr-group

                                } // container overrides

                            } // container sap-egress

                            container policer-control-policy {
                                description "Enter the policer-control-policy context";

                                leaf policy-name {
                                    type leafref {
                                        path "../../../../../../../../qos/policer-control-policy/policer-control-policy-name";
                                    }
                                    description "Policer control policy name";
                                }

                                container overrides {
                                    presence "Enable the overrides context";
                                    description "Enable the overrides context";

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container root {
                                        description "Enter the root context";

                                        leaf max-rate {
                                            type types-services:sap-max-rate-ovr;
                                            description "Maximum frame-based bandwidth limit";
                                        }

                                        container priority-mbs-thresholds {
                                            description "Enter the priority-mbs-thresholds context";

                                            leaf min-thresh-separation {
                                                type union {
                                                    type types-qos:bytes {
                                                        range "0..16777216";
                                                    }
                                                    type enumeration {
                                                        enum "auto"                         { value -1; }
                                                    }
                                                }
                                                units "bytes";
                                                description "Minimum amount of separation buffer space";
                                            }

                                            list priority {
                                                key "priority-level";
                                                description "Enter the priority list instance";

                                                leaf priority-level {
                                                    type types-qos:hierarchy-level;
                                                    description "Priority level";
                                                }

                                                leaf mbs-contribution {
                                                    type union {
                                                        type types-qos:bytes {
                                                            range "0..16777216";
                                                        }
                                                        type enumeration {
                                                            enum "auto"                         { value -1; }
                                                        }
                                                    }
                                                    units "bytes";
                                                    description "Minimum amount of cumulative buffer space allowed";
                                                }

                                                leaf-list apply-groups {
                                                    type leafref {
                                                        path "../../../../../../../../../../../../groups/group/name";
                                                    }
                                                    max-elements 8;
                                                    ordered-by user;
                                                    description "Apply a configuration group at this level";
                                                }

                                                leaf-list apply-groups-exclude {
                                                    type leafref {
                                                        path "../../../../../../../../../../../../groups/group/name";
                                                    }
                                                    max-elements 8;
                                                    ordered-by user;
                                                    description "Exclude a configuration group at this level";
                                                }

                                            } // list priority

                                        } // container priority-mbs-thresholds

                                    } // container root

                                } // container overrides

                            } // container policer-control-policy

                            container scheduler-policy {
                                description "Enter the scheduler-policy context";

                                leaf policy-name {
                                    type leafref {
                                        path "../../../../../../../../qos/scheduler-policy/scheduler-policy-name";
                                    }
                                    description "Scheduler policy name";
                                }

                                container overrides {
                                    description "Enter the overrides context";

                                    list scheduler {
                                        key "scheduler-name";
                                        description "Enter the scheduler list instance";

                                        leaf scheduler-name {
                                            type types-sros:named-item;
                                            description "Scheduler name";
                                        }

                                        leaf-list apply-groups {
                                            type leafref {
                                                path "../../../../../../../../../../groups/group/name";
                                            }
                                            max-elements 8;
                                            ordered-by user;
                                            description "Apply a configuration group at this level";
                                        }

                                        leaf-list apply-groups-exclude {
                                            type leafref {
                                                path "../../../../../../../../../../groups/group/name";
                                            }
                                            max-elements 8;
                                            ordered-by user;
                                            description "Exclude a configuration group at this level";
                                        }

                                        container parent {
                                            description "Enter the parent context";

                                            leaf weight {
                                                type types-qos:weight;
                                                description "Relative weight of the scheduler to feed the queue";
                                            }

                                            leaf cir-weight {
                                                type types-qos:weight;
                                                description "Weight used at the within-CIR port priority level";
                                            }

                                        } // container parent

                                        container rate {
                                            description "Enter the rate context";

                                            leaf pir {
                                                type union {
                                                    type int64 {
                                                        range "1..6400000000";
                                                    }
                                                    type enumeration {
                                                        enum "max"                          { value -1; }
                                                    }
                                                }
                                                description "PIR at which the queue is to operate";
                                            }

                                            leaf cir {
                                                type union {
                                                    type int64 {
                                                        range "0..6400000000";
                                                    }
                                                    type enumeration {
                                                        enum "sum"                          { value -3; }
                                                        enum "max"                          { value -1; }
                                                    }
                                                }
                                                description "CIR at which the queue it to operate";
                                            }

                                        } // container rate

                                    } // list scheduler

                                } // container overrides

                            } // container scheduler-policy

                            container vlan-qos-policy {
                                description "Enter the vlan-qos-policy context";

                                leaf policy-name {
                                    type leafref {
                                        path "../../../../../../../../qos/vlan-qos-policy/vlan-qos-policy-name";
                                    }
                                    description "Egress vlan-qos-policy name";
                                }

                                leaf port-redirect {
                                    type boolean;
                                    default "false";
                                    description "Enable egress vlan-qos-policy port-redirect";
                                }

                            } // container vlan-qos-policy

                            container egress-remark-policy {
                                description "Enter the egress-remark-policy context";

                                leaf policy-name {
                                    type leafref {
                                        path "../../../../../../../../qos/egress-remark-policy/egress-remark-policy-name";
                                    }
                                    description "Egress-remark-policy name";
                                }

                            } // container egress-remark-policy

                        } // container qos

                        container filter {
                            description "Enter the filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container filter

                        container agg-rate {
                            description "Enter the agg-rate context";

                            leaf limit-unused-bandwidth {
                                type boolean;
                                default "false";
                                description "Enable aggregate rate overrun protection";
                            }

                            leaf rate {
                                type types-services:agg-rate-rate;
                                description "Enforced aggregate rate for all queues";
                            }

                            leaf queue-frame-based-accounting {
                                type boolean;
                                default "false";
                                description "Enable frame based accounting on policers and queues";
                            }

                            leaf cir {
                                type union {
                                    type int32 {
                                        range "0..400000000";
                                    }
                                    type enumeration {
                                        enum "max"                          { value -1; }
                                    }
                                }
                                units "kilobps";
                                default "0";
                                description "Administrative CIR";
                            }

                        } // container agg-rate

                    } // container egress

                    container cpu-protection {
                        description "Enter the cpu-protection context";

                        leaf policy-id {
                            type leafref {
                                path "../../../../../../system/security/cpu-protection/policy/policy-id";
                            }
                            description "CPM protection policy";
                        }

                        choice monitoring {
                            case mac {

                                leaf mac-monitoring {
                                    type empty;
                                    description "Monitor MAC for CPU protection";
                                }

                            }
                            case cfm {

                                container eth-cfm-monitoring {
                                    presence "Enable the eth-cfm-monitoring context";
                                    description "Enable the eth-cfm-monitoring context";

                                    leaf aggregate {
                                        type empty;
                                        description "Apply rate limit to the sum of the per peer packet rates";
                                    }

                                    leaf car {
                                        type empty;
                                        description "Ignore Ethernet CFM packets when enforcing overall rate";
                                    }

                                } // container eth-cfm-monitoring

                            }
                            case ip {

                                leaf ip-src-monitoring {
                                    type empty;
                                    description "Enable IP source monitoring for CPU protection";
                                }

                            }
                        }
                    } // container cpu-protection

                    container lag {
                        description "Enter the lag context";

                        leaf link-map-profile {
                            type types-services:link-map-profile-id;
                            description "LAG link map profile for a SAP or network interface";
                        }

                        container per-link-hash {
                            description "Enter the per-link-hash context";

                            leaf class {
                                type types-services:sap-lag-per-link-hash-class;
                                default "1";
                                description "Class used on LAG egress using weighted per-link-hash";
                            }

                            leaf weight {
                                type types-services:sap-lag-per-link-hash-weight;
                                default "1";
                                description "Weight used on LAG egress using weighted per-link-hash";
                            }

                        } // container per-link-hash

                    } // container lag

                    container fwd-wholesale {
                        description "Enter the fwd-wholesale context";

                        leaf pppoe-service {
                            type leafref {
                                path "../../../../../epipe/service-name";
                            }
                            description "PPPoE service name";
                        }

                    } // container fwd-wholesale

                    container aarp {
                        presence "Enable the aarp context";
                        description "Enter the aarp context";

                        leaf id {
                            type leafref {
                                path "../../../../../../application-assurance/aarp/aarp-id";
                            }
                            description "AARP instance ID";
                        }

                        leaf type {
                            type types-services:dual-homing-bsx-aarp-service-ref-type;
                            description "Role referenced by the AARP";
                        }

                    } // container aarp

                    container transit-policy {
                        presence "Enable the transit-policy context";
                        description "Enter the transit-policy context";

                        choice transit-policy {
                            mandatory true;
                            case prefix {

                                leaf prefix {
                                    type leafref {
                                        path "../../../../../../application-assurance/group/partition/transit-prefix-policy/prefix-policy-id";
                                    }
                                    sros-ext:immutable;
                                    description "IP prefix policy ID";
                                }

                            }
                            case ip {

                                leaf ip {
                                    type leafref {
                                        path "../../../../../../application-assurance/group/partition/transit-ip-policy/ip-policy-id";
                                    }
                                    sros-ext:immutable;
                                    description "IP transit policy ID";
                                }

                            }
                        }
                    } // container transit-policy

                    container eth-cfm {
                        description "Enter the eth-cfm context";

                        leaf collect-lmm-stats {
                            type boolean;
                            default "false";
                            description "Collect statistics for loss measurement message tests";
                        }

                        leaf-list squelch-ingress-levels {
                            type uint32 {
                                range "0..7";
                            }
                            max-elements 8;
                            description "Levels for which ETH-CFM packets are silently discarded";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container collect-lmm-fc-stats {
                            description "Enter the collect-lmm-fc-stats context";

                            leaf-list fc {
                                type types-eth-cfm:fc-type;
                                max-elements 8;
                                description "Forwarding class name for profile-unaware counter";
                            }

                            leaf-list fc-in-profile {
                                type types-eth-cfm:fc-type;
                                max-elements 8;
                                description "Forwarding class name for profile-aware counter";
                            }

                        } // container collect-lmm-fc-stats

                        list mep {
                            key "md-admin-name ma-admin-name mep-id";
                            description "Enter the mep list instance";

                            leaf md-admin-name {
                                type leafref {
                                    path "../../../../../../../eth-cfm/domain/md-admin-name";
                                }
                                description "Maintenance Domain (MD) name";
                            }

                            leaf ma-admin-name {
                                type leafref {
                                    path "../../../../../../../eth-cfm/domain[md-admin-name=current()/../md-admin-name]/association/ma-admin-name";
                                }
                                description "Maintenance Association (MA) name";
                            }

                            leaf mep-id {
                                type types-eth-cfm:mep-id-type;
                                description "Maintenance Endpoint (MEP) ID";
                            }

                            leaf admin-state {
                                type types-sros:admin-state;
                                default "disable";
                                description "Administrative state of the MEP";
                            }

                            leaf description {
                                type types-sros:description;
                                description "Text description";
                            }

                            leaf low-priority-defect {
                                type types-eth-cfm:lowest-alarm-priority;
                                default "mac-rem-err-xcon";
                                description "Lowest priority defect allowed to generate fault alarm";
                            }

                            leaf fault-propagation {
                                type types-eth-cfm:fault-propagation-type;
                                description "Fault propagation for the MEP";
                            }

                            leaf ccm {
                                type boolean;
                                default "false";
                                description "Generate CCM messages";
                            }

                            leaf ccm-ltm-priority {
                                type types-eth-cfm:frame-priority;
                                default "7";
                                description "Priority of CCM and LTM messages transmitted by the MEP";
                            }

                            leaf ccm-padding-size {
                                type uint32 {
                                    range "3..1500";
                                }
                                description "Number of octets of padding to insert in CCM packets";
                            }

                            leaf one-way-delay-threshold {
                                type uint32 {
                                    range "0..600";
                                }
                                units "seconds";
                                default "3";
                                description "Threshold time limit for the one-way delay test";
                            }

                            leaf ais {
                                type boolean;
                                default "false";
                                description "Enable the generation and the reception of AIS messages";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container alarm-notification {
                                description "Enter the alarm-notification context";

                                leaf fng-alarm-time {
                                    type int32 {
                                        range "250|500|1000";
                                    }
                                    units "centiseconds";
                                    description "Time that must expire before an FNG alarm is raised";
                                }

                                leaf fng-reset-time {
                                    type int32 {
                                        range "250|500|1000";
                                    }
                                    units "centiseconds";
                                    description "Time that must expire before an FNG alarm is reset";
                                }

                            } // container alarm-notification

                            container csf {
                                presence "Enable the csf context";
                                description "Enter the csf context";

                                leaf multiplier {
                                    type decimal64 {
                                        range "0.0|2.0..30.0";
                                        fraction-digits 1;
                                    }
                                    default "3.5";
                                    description "Multiplication factor used to clear the CSF condition";
                                }

                            } // container csf

                            container eth-test {
                                presence "Enable the eth-test context";
                                description "Enable the eth-test context";

                                leaf bit-error-threshold {
                                    type uint32 {
                                        range "0..11840";
                                    }
                                    units "bit errors";
                                    default "1";
                                    description "Lowest priority defect allowed to generate fault alarm";
                                }

                                container test-pattern {
                                    description "Enter the test-pattern context";

                                    leaf pattern {
                                        type enumeration {
                                            enum "all-zeros"                    { value 0; }
                                            enum "all-ones"                     { value 1; }
                                        }
                                        default "all-zeros";
                                        description "Test pattern for Ethernet Test frames";
                                    }

                                    leaf crc-tlv {
                                        type boolean;
                                        default "false";
                                        description "Generate a CRC checksum";
                                    }

                                } // container test-pattern

                            } // container eth-test

                            container grace {
                                description "Enter the grace context";

                                container eth-ed {
                                    description "Enter the eth-ed context";

                                    leaf max-rx-defect-window {
                                        type uint32 {
                                            range "1..86400";
                                        }
                                        units "seconds";
                                        description "Maximum received ETH-ED expected defect window duration";
                                    }

                                    leaf priority {
                                        type int32 {
                                            range "0..7";
                                        }
                                        description "Transmission priority for ETH-ED PDUs";
                                    }

                                    leaf rx-eth-ed {
                                        type boolean;
                                        default "true";
                                        description "Receive and process ETH-ED ITU-T Y.1731 PDUs on the MEP";
                                    }

                                    leaf tx-eth-ed {
                                        type boolean;
                                        default "false";
                                        description "Transmit ETH-ED PDUs from the MEP";
                                    }

                                } // container eth-ed

                                container eth-vsm-grace {
                                    description "Enter the eth-vsm-grace context";

                                    leaf rx-eth-vsm-grace {
                                        type boolean;
                                        default "true";
                                        description "Receive and process Nokia ETH-CFM Grace PDU on the MEP";
                                    }

                                    leaf tx-eth-vsm-grace {
                                        type boolean;
                                        default "true";
                                        description "Transmit ETH-ED PDUs from the MEP";
                                    }

                                } // container eth-vsm-grace

                            } // container grace

                        } // list mep

                    } // container eth-cfm

                    list ip-tunnel {
                        key "tunnel-name";
                        max-elements 1;
                        description "Enter the ip-tunnel list instance";

                        leaf tunnel-name {
                            type types-sros:interface-name;
                            description "IP tunnel name";
                        }

                        leaf admin-state {
                            type types-sros:admin-state;
                            default "disable";
                            description "Administrative state of the IP tunnel";
                        }

                        leaf description {
                            type types-sros:description;
                            sros-ext:auto-restart-to-modify;
                            description "Text description";
                        }

                        leaf clear-df-bit {
                            type boolean;
                            sros-ext:auto-restart-to-modify;
                            default "false";
                            description "Clear the Do-not-Fragment bit";
                        }

                        leaf delivery-service {
                            type types-services:service-name;
                            sros-ext:auto-restart-to-modify;
                            description "Service to originate and terminate GRE packets";
                        }

                        leaf dscp {
                            type types-qos:dscp-name;
                            sros-ext:auto-restart-to-modify;
                            description "Differentiated Services Code Point (DSCP) name";
                        }

                        leaf encapsulated-ip-mtu {
                            type uint32 {
                                range "512..9000";
                            }
                            units "bytes";
                            sros-ext:auto-restart-to-modify;
                            description "Maximum size of the encapsulated tunnel packet";
                        }

                        leaf ip-mtu {
                            type uint32 {
                                range "512..9000";
                            }
                            units "bytes";
                            sros-ext:auto-restart-to-modify;
                            description "IP MTU for the interface";
                        }

                        leaf public-tcp-mss-adjust {
                            type union {
                                type uint32 {
                                    range "512..9000";
                                }
                                type enumeration {
                                    enum "auto"                         { value 0; }
                                }
                            }
                            units "bytes";
                            sros-ext:auto-restart-to-modify;
                            description "TCP Maximum Segment Size (MSS) on the public side";
                        }

                        leaf private-tcp-mss-adjust {
                            type int32 {
                                range "512..9000";
                            }
                            units "bytes";
                            sros-ext:auto-restart-to-modify;
                            description "TCP Maximum Segment Size (MSS) on the private side";
                        }

                        leaf reassembly {
                            type union {
                                type int32 {
                                    range "1..5000";
                                }
                                type enumeration {
                                    enum "use-tunnel-group-setting"     { value -1; }
                                    enum "none"                         { value 0; }
                                }
                            }
                            units "milliseconds";
                            sros-ext:auto-restart-to-modify;
                            description "Maximum reassembly wait time";
                        }

                        leaf remote-ip-address {
                            type types-sros:ip-address;
                            sros-ext:auto-restart-to-modify;
                            description "Remote IP address of the tunnel";
                        }

                        leaf backup-remote-ip-address {
                            type types-sros:ip-address;
                            sros-ext:auto-restart-to-modify;
                            description "Backup remote IP address that is applied to this tunnel";
                        }

                        leaf local-ip-address {
                            type types-sros:ip-address;
                            sros-ext:auto-restart-to-modify;
                            description "Local IP address of this tunnel";
                        }

                        leaf ipsec-transport-mode-profile {
                            type leafref {
                                path "../../../../../../ipsec/ipsec-transport-mode-profile/name";
                            }
                            sros-ext:auto-restart-to-modify;
                            description "IPsec transport mode profile name";
                        }

                        leaf propagate-pmtu-v4 {
                            type boolean;
                            sros-ext:auto-restart-to-modify;
                            description "Enable propagation of the path MTU to IPv4 hosts";
                        }

                        leaf propagate-pmtu-v6 {
                            type boolean;
                            sros-ext:auto-restart-to-modify;
                            description "Enable propagation of path MTU to IPv6 hosts";
                        }

                        leaf pmtu-discovery-aging {
                            type uint32 {
                                range "900..3600";
                            }
                            units "seconds";
                            sros-ext:auto-restart-to-modify;
                            default "900";
                            description "Time to age out the learned path MTU";
                        }

                        leaf-list apply-groups {
                            type leafref {
                                path "../../../../../../groups/group/name";
                            }
                            max-elements 8;
                            ordered-by user;
                            sros-ext:auto-restart-to-modify;
                            description "Apply a configuration group at this level";
                        }

                        leaf-list apply-groups-exclude {
                            type leafref {
                                path "../../../../../../groups/group/name";
                            }
                            max-elements 8;
                            ordered-by user;
                            sros-ext:auto-restart-to-modify;
                            description "Exclude a configuration group at this level";
                        }

                        container icmp6-generation {
                            sros-ext:auto-restart-to-modify;
                            description "Enter the icmp6-generation context";

                            container packet-too-big {
                                sros-ext:auto-restart-to-modify;
                                description "Enter the packet-too-big context";

                                leaf admin-state {
                                    type types-sros:admin-state;
                                    sros-ext:auto-restart-to-modify;
                                    description "Administrative state of sending Packet Too Big messages";
                                }

                                leaf number {
                                    type uint32 {
                                        range "10..1000";
                                    }
                                    sros-ext:auto-restart-to-modify;
                                    default "100";
                                    description "Maximum number of PTB ICMPv6 messages that can be sent";
                                }

                                leaf seconds {
                                    type uint32 {
                                        range "1..60";
                                    }
                                    units "seconds";
                                    sros-ext:auto-restart-to-modify;
                                    default "10";
                                    description "Maximum interval when PTB messages can be sent";
                                }

                            } // container packet-too-big

                        } // container icmp6-generation

                        container gre-header {
                            sros-ext:auto-restart-to-modify;
                            description "Enter the gre-header context";

                            leaf admin-state {
                                type types-sros:admin-state;
                                sros-ext:auto-restart-to-modify;
                                description "Administrative state of the GRE header in the tunnel";
                            }

                            container key {
                                sros-ext:auto-restart-to-modify;
                                description "Enter the key context";

                                leaf admin-state {
                                    type types-sros:admin-state;
                                    sros-ext:auto-restart-to-modify;
                                    default "disable";
                                    description "Administrative state of the keys in the GRE header";
                                }

                                leaf send {
                                    type uint32;
                                    sros-ext:auto-restart-to-modify;
                                    default "0";
                                    description "Send key of the GRE header";
                                }

                                leaf receive {
                                    type uint32;
                                    sros-ext:auto-restart-to-modify;
                                    default "0";
                                    description "Receive key of the GRE header";
                                }

                            } // container key

                        } // container gre-header

                        container icmp-generation {
                            sros-ext:auto-restart-to-modify;
                            description "Enter the icmp-generation context";

                            container frag-required {
                                sros-ext:auto-restart-to-modify;
                                description "Enter the frag-required context";

                                leaf admin-state {
                                    type types-sros:admin-state;
                                    sros-ext:auto-restart-to-modify;
                                    description "Send fragmentation required messages";
                                }

                                leaf message-count {
                                    type uint32 {
                                        range "10..1000";
                                    }
                                    sros-ext:auto-restart-to-modify;
                                    default "100";
                                    description "Maximum number of ICMP messages sent";
                                }

                                leaf interval {
                                    type uint32 {
                                        range "1..60";
                                    }
                                    units "seconds";
                                    sros-ext:auto-restart-to-modify;
                                    default "10";
                                    description "Maximum interval that the ICMP messages can be sent";
                                }

                            } // container frag-required

                        } // container icmp-generation

                        list dest-ip {
                            key "dest-ip-address";
                            sros-ext:auto-restart-to-modify;
                            description "Add a list entry for dest-ip";

                            leaf dest-ip-address {
                                type types-sros:ip-address;
                                description "IP address of the remote IP tunnel endpoint";
                            }

                        } // list dest-ip

                    } // list ip-tunnel

                    list ipsec-gateway {
                        key "name";
                        max-elements 1;
                        description "Enter the ipsec-gateway list instance";

                        leaf name {
                            type types-sros:named-item;
                            description "IPsec gateway name";
                        }

                        leaf admin-state {
                            type types-sros:admin-state;
                            default "disable";
                            description "Administrative state of the IPsec gateway";
                        }

                        leaf default-tunnel-template {
                            type leafref {
                                path "../../../../../../ipsec/tunnel-template/id";
                            }
                            description "Default tunnel policy template for the gateway";
                        }

                        leaf ike-policy {
                            type leafref {
                                path "../../../../../../ipsec/ike-policy/id";
                            }
                            description "IKE policy ID";
                        }

                        leaf pre-shared-key {
                            type types-sros:encrypted-leaf {
                                length "1..115";
                            }
                            description "Pre-shared key for the IPsec gateway";
                        }

                        leaf ts-list {
                            type leafref {
                                path "../../../../../../ipsec/ts-list/name";
                            }
                            description "TS list used for IKEv2 TS negotiation";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container dhcp-address-assignment {
                            description "Enter the dhcp-address-assignment context";

                            container dhcpv4 {
                                presence "Enable the dhcpv4 context";
                                description "Enter the dhcpv4 context";

                                leaf admin-state {
                                    type types-sros:admin-state;
                                    default "disable";
                                    description "Administrative state of the IPsec DHCPv4 server";
                                }

                                leaf gi-address {
                                    type types-sros:ipv4-unicast-address;
                                    description "Gateway IP address of DHCPv4 packets sent by the system";
                                }

                                leaf send-release {
                                    type boolean;
                                    default "true";
                                    description "Send DHCPv4 release message when IPsec tunnel removed";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container server {
                                    description "Enter the server context";

                                    leaf-list address {
                                        type types-sros:ipv4-unicast-address;
                                        max-elements 8;
                                        description "DHCPv4 server addresses";
                                    }

                                    leaf router-instance {
                                        type types-sros:router-instance-base-vprn-loose;
                                        description "Router instance used to reach the DHCPv4 server";
                                    }

                                } // container server

                            } // container dhcpv4

                            container dhcpv6 {
                                presence "Enable the dhcpv6 context";
                                description "Enter the dhcpv6 context";

                                leaf admin-state {
                                    type types-sros:admin-state;
                                    default "disable";
                                    description "Administrative state of the DHCPv6 server";
                                }

                                leaf link-address {
                                    type types-sros:ipv6-unicast-address;
                                    description "Link address of the relayed DHCPv6 packets";
                                }

                                leaf send-release {
                                    type boolean;
                                    default "true";
                                    description "Send DHCPv6 release message when IPsec tunnel removed";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container server {
                                    description "Enter the server context";

                                    leaf-list address {
                                        type types-sros:ipv6-unicast-address;
                                        max-elements 8;
                                        description "DHCPv6 server addresses";
                                    }

                                    leaf router-instance {
                                        type types-sros:router-instance-base-vprn-loose;
                                        description "Router instance to reach the DHCPv6 server";
                                    }

                                } // container server

                            } // container dhcpv6

                        } // container dhcp-address-assignment

                        container cert {
                            description "Enter the cert context";

                            leaf cert-profile {
                                type leafref {
                                    path "../../../../../../../ipsec/cert-profile/name";
                                }
                                description "Certificate profile name";
                            }

                            leaf trust-anchor-profile {
                                type leafref {
                                    path "../../../../../../../ipsec/trust-anchor-profile/name";
                                }
                                description "Trust anchor profile name";
                            }

                            container status-verify {
                                description "Enter the status-verify context";

                                leaf default-result {
                                    type enumeration {
                                        enum "revoked"                      { value 0; }
                                        enum "good"                         { value 1; }
                                    }
                                    default "revoked";
                                    description "Default result of Certificate Status Verification (CSV)";
                                }

                                leaf primary {
                                    type types-ipsec:cert-revocation-status;
                                    default "crl";
                                    description "Primary method of CSV to verify the revocation status";
                                }

                                leaf secondary {
                                    type types-ipsec:cert-revocation-status-with-none;
                                    default "none";
                                    description "Secondary method of CSV to verify the revocation status";
                                }

                            } // container status-verify

                        } // container cert

                        container client-db {
                            presence "Enable the client-db context";
                            description "Enable the client-db context";

                            leaf name {
                                type leafref {
                                    path "../../../../../../../ipsec/client-db/name";
                                }
                                mandatory true;
                                description "Client database name";
                            }

                            leaf fallback {
                                type boolean;
                                default "true";
                                description "Fall back to the default authentication policy";
                            }

                        } // container client-db

                        container default-secure-service {
                            presence "Enable the default-secure-service context";
                            description "Enable the default-secure-service context";

                            leaf service-name {
                                type types-services:service-name;
                                sros-ext:auto-restart-to-modify;
                                description "Default security service name";
                            }

                            leaf interface {
                                type types-sros:interface-name;
                                sros-ext:auto-restart-to-modify;
                                description "Private IPsec tunnel interface name";
                            }

                        } // container default-secure-service

                        container local {
                            description "Enter the local context";

                            leaf gateway-address {
                                type types-sros:ip-address;
                                sros-ext:auto-restart-to-modify;
                                description "Local gateway address of the IPsec gateway";
                            }

                            container id {
                                description "Enter the id context";

                                choice id {
                                    default "auto";
                                    case auto {

                                        leaf auto {
                                            type empty;
                                            sros-ext:auto-restart-to-modify;
                                            description "Select ID based on authentication method in IKE policy";
                                        }

                                    }
                                    case ipv4 {

                                        leaf ipv4 {
                                            type types-sros:ipv4-unicast-address;
                                            sros-ext:auto-restart-to-modify;
                                            description "IPv4 address as the local ID type";
                                        }

                                    }
                                    case ipv6 {

                                        leaf ipv6 {
                                            type types-sros:ip-address;
                                            sros-ext:auto-restart-to-modify;
                                            description "IPv6 address as the local ID type";
                                        }

                                    }
                                    case fqdn {

                                        leaf fqdn {
                                            type types-sros:fully-qualified-domain-name;
                                            sros-ext:auto-restart-to-modify;
                                            description "FQDN as the local ID type";
                                        }

                                    }
                                }
                            } // container id

                            container address-assignment {
                                presence "Enable the address-assignment context";
                                description "Enter the address-assignment context";

                                leaf admin-state {
                                    type types-sros:admin-state;
                                    default "disable";
                                    description "Administrative state of local address assignments";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container ipv4 {
                                    presence "Enable the ipv4 context";
                                    description "Enter the ipv4 context";

                                    leaf router-instance {
                                        type types-sros:router-instance-base-vprn-loose;
                                        mandatory true;
                                        description "Router instance ID for the local DHCPv4 server";
                                    }

                                    leaf dhcp-server {
                                        type types-sros:named-item;
                                        mandatory true;
                                        description "Local DHCPv4 server name";
                                    }

                                    leaf pool {
                                        type types-sros:named-item;
                                        mandatory true;
                                        description "Name of the pool defined in the specified DHCPv4 server";
                                    }

                                    leaf secondary-pool {
                                        type types-sros:named-item;
                                        description "Name of the secondary pool defined in the DHCPv4 server";
                                    }

                                } // container ipv4

                                container ipv6 {
                                    presence "Enable the ipv6 context";
                                    description "Enter the ipv6 context";

                                    leaf router-instance {
                                        type types-sros:router-instance-base-vprn-loose;
                                        mandatory true;
                                        description "Router instance ID hosting the DHCPv6 connection";
                                    }

                                    leaf dhcp-server {
                                        type types-sros:named-item;
                                        mandatory true;
                                        description "Local DHCPv6 server name";
                                    }

                                    leaf pool {
                                        type types-sros:named-item;
                                        mandatory true;
                                        description "Secondary pool name defined in the DHCPv6 server";
                                    }

                                } // container ipv6

                            } // container address-assignment

                        } // container local

                        container radius {
                            description "Enter the radius context";

                            leaf accounting-policy {
                                type leafref {
                                    path "../../../../../../../ipsec/radius/accounting-policy/name";
                                }
                                description "RADIUS accounting policy";
                            }

                            leaf authentication-policy {
                                type leafref {
                                    path "../../../../../../../ipsec/radius/authentication-policy/name";
                                }
                                description "RADIUS authentication policy";
                            }

                        } // container radius

                        container max-history-key-records {
                            description "Enter the max-history-key-records context";

                            leaf ike {
                                type uint32 {
                                    range "1..3";
                                }
                                description "Maximum number of historical IKE keys recorded";
                            }

                            leaf esp {
                                type uint32 {
                                    range "1..48";
                                }
                                description "Maximum number of recent records";
                            }

                        } // container max-history-key-records

                    } // list ipsec-gateway

                    container static-host {
                        description "Enter the static-host context";

                        list ipv4 {
                            key "ip mac";
                            description "Enter the ipv4 list instance";

                            leaf ip {
                                type types-sros:ipv4-address;
                                description "IP address";
                            }

                            leaf mac {
                                type types-sros:mac-unicast-address;
                                description "MAC address";
                            }

                            leaf admin-state {
                                type types-sros:admin-state;
                                default "disable";
                                description "Administrative state of the static host";
                            }

                            leaf sub-profile {
                                type leafref {
                                    path "../../../../../../../subscriber-mgmt/sub-profile/name";
                                }
                                description "Sub-profile name";
                            }

                            leaf sla-profile {
                                type leafref {
                                    path "../../../../../../../subscriber-mgmt/sla-profile/name";
                                }
                                description "SLA profile name";
                            }

                            leaf ancp-string {
                                type types-submgt:ancp-string;
                                description "ANCP string";
                            }

                            leaf int-dest-id {
                                type types-submgt:int-dest-id;
                                description "Intermediate destination ID";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container app-profile {
                                description "Enter the app-profile context";

                                leaf profile {
                                    type leafref {
                                        path "../../../../../../../../application-assurance/group/partition/policy/app-profile/app-profile-name";
                                    }
                                    description "Application profile used by the static host";
                                }

                            } // container app-profile

                            container subscriber-id {
                                description "Enter the subscriber-id context";

                                choice subscriber-id {
                                    case string {

                                        leaf string {
                                            type types-submgt:subscriber-id;
                                            description "Subscriber identification";
                                        }

                                    }
                                    case use-sap-id {

                                        leaf use-sap-id {
                                            type empty;
                                            description "Use the SAP id as subscriber ID";
                                        }

                                    }
                                }
                            } // container subscriber-id

                        } // list ipv4

                    } // container static-host

                } // list sap

                list vpls {
                    when "../tunnel = 'false'";
                    key "vpls-name";
                    max-elements 1;
                    description "Enter the vpls list instance";

                    leaf vpls-name {
                        type types-sros:named-item-64;
                        description "VPLS service";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container evpn {
                        description "Enter the evpn context";

                        container arp {
                            description "Enter the arp context";

                            leaf learn-dynamic {
                                type boolean;
                                default "true";
                                description "Process ARP or ND messages on EVPN tunnels";
                            }

                            leaf flood-garp-and-unknown-req {
                                type boolean;
                                default "true";
                                description "Allow CPM originated ARP frames to flood R-VPLS service";
                            }

                            list advertise {
                                key "route-type";
                                description "Enter the advertise list instance";

                                leaf route-type {
                                    type enumeration {
                                        enum "static"                       { value 1; }
                                        enum "dynamic"                      { value 2; }
                                    }
                                    description "Type of ARP or ND entries that generate host routes";
                                }

                                leaf route-tag {
                                    type uint32 {
                                        range "0..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list advertise

                        } // container arp

                        container nd {
                            description "Enter the nd context";

                            leaf learn-dynamic {
                                type boolean;
                                default "true";
                                description "Process ARP or ND messages on EVPN tunnels";
                            }

                            list advertise {
                                key "route-type";
                                description "Enter the advertise list instance";

                                leaf route-type {
                                    type enumeration {
                                        enum "static"                       { value 1; }
                                        enum "dynamic"                      { value 2; }
                                    }
                                    description "Type of ARP or ND entries that generate host routes";
                                }

                                leaf route-tag {
                                    type uint32 {
                                        range "0..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list advertise

                        } // container nd

                    } // container evpn

                    container egress {
                        description "Enter the egress context";

                        leaf reclassify-using-qos {
                            type leafref {
                                path "../../../../../../qos/sap-egress/sap-egress-policy-name";
                            }
                            description "Egress QoS policy";
                        }

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container egress

                    container ingress {
                        description "Enter the ingress context";

                        container routed-override-filter {
                            description "Enter the routed-override-filter context";

                            leaf ip {
                                type leafref {
                                    path "../../../../../../../filter/ip-filter/filter-name";
                                }
                                description "IPv4 filter policy name";
                            }

                            leaf ipv6 {
                                type leafref {
                                    path "../../../../../../../filter/ipv6-filter/filter-name";
                                }
                                description "IPv6 filter policy name";
                            }

                        } // container routed-override-filter

                    } // container ingress

                } // list vpls

                container hold-time {
                    when "../tunnel = 'false' or not(../loopback != 'false')";
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                    container ipv6 {
                        description "Enter the ipv6 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv6

                } // container hold-time

                container ipv4 {
                    description "Enter the ipv4 context";

                    leaf tcp-mss {
                        type types-router:ipv4-tcp-mss-ext;
                        description "TCP maximum segment size for the interface";
                    }

                    leaf allow-directed-broadcasts {
                        type boolean;
                        default "false";
                        description "Forward directed broadcasts";
                    }

                    leaf local-dhcp-server {
                        when "../../tunnel = 'false'";
                        type leafref {
                            path "../../../../../router/dhcp-server/dhcpv4/name";
                        }
                        description "DHCP server for the interface";
                    }

                    leaf qos-route-lookup {
                        type types-router:qos-route-lookup;
                        description "QoS Route lookup";
                    }

                    leaf ip-helper-address {
                        type types-sros:ipv4-unicast-address;
                        description "Gateway address";
                    }

                    container icmp {
                        description "Enter the icmp context";

                        leaf mask-reply {
                            type boolean;
                            default "true";
                            description "Allow responses to ICMP mask requests on the interface";
                        }

                        container redirects {
                            description "Enter the redirects context";

                            leaf admin-state {
                                type types-sros:admin-state;
                                default "enable";
                                description "Administrative state of sending ICMP redirect messages";
                            }

                            leaf number {
                                type uint16 {
                                    range "10..1000";
                                }
                                default "100";
                                description "Maximum number of ICMP redirect messages to send";
                            }

                            leaf seconds {
                                type uint16 {
                                    range "1..60";
                                }
                                units "seconds";
                                default "10";
                                description "Time used to limit the number of ICMP redirect messages";
                            }

                        } // container redirects

                        container ttl-expired {
                            description "Enter the ttl-expired context";

                            leaf admin-state {
                                type types-sros:admin-state;
                                default "enable";
                                description "Administrative state of sending TTL expired messages";
                            }

                            leaf number {
                                type uint16 {
                                    range "10..2000";
                                }
                                default "100";
                                description "Maximum number of TTL expired messages to send";
                            }

                            leaf seconds {
                                type uint16 {
                                    range "1..60";
                                }
                                units "seconds";
                                default "10";
                                description "Time used to limit the number of TTL expired messages";
                            }

                        } // container ttl-expired

                        container unreachables {
                            description "Enter the unreachables context";

                            leaf admin-state {
                                type types-sros:admin-state;
                                default "enable";
                                description "Administrative state of sending unreachable messages";
                            }

                            leaf number {
                                type uint16 {
                                    range "10..2000";
                                }
                                default "100";
                                description "Maximum number of unreachable messages to send";
                            }

                            leaf seconds {
                                type uint16 {
                                    range "1..60";
                                }
                                units "seconds";
                                default "10";
                                description "Time to limit the number of ICMP unreachable messages";
                            }

                        } // container unreachables

                        container param-problem {
                            description "Enter the param-problem context";

                            leaf admin-state {
                                type types-sros:admin-state;
                                default "enable";
                                description "Administrative state of sent Parameter Problem messages";
                            }

                            leaf number {
                                type uint32 {
                                    range "10..1000";
                                }
                                default "100";
                                description "Maximum number of Parameter Problem messages to send";
                            }

                            leaf seconds {
                                type uint32 {
                                    range "1..60";
                                }
                                units "seconds";
                                default "10";
                                description "Time used to limit number of Parameter Problem messages";
                            }

                        } // container param-problem

                    } // container icmp

                    container unnumbered {
                        description "Enter the unnumbered context";

                        choice source {
                            case ip-address {

                                leaf ip-address {
                                    type types-sros:ipv4-unicast-address;
                                    description "IP address of the unnumbered interface";
                                }

                            }
                            case ip-int-name {

                                leaf ip-int-name {
                                    type types-sros:interface-name;
                                    description "IP interface name";
                                }

                            }
                            case ip-int-system {

                                leaf system {
                                    type empty;
                                    description "IP interface as an unnumbered interface";
                                }

                            }
                        }
                    } // container unnumbered

                    container urpf-check {
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for the BFD session";
                        }

                    } // container bfd

                    container primary {
                        presence "Enable the primary context";
                        description "Enable the primary context";

                        leaf address {
                            type types-sros:ipv4-unicast-address;
                            mandatory true;
                            description "Primary IPv4 address assigned to the interface";
                        }

                        leaf prefix-length {
                            type uint32 {
                                range "0..32";
                            }
                            mandatory true;
                            description "IPv4 address prefix length";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                    list secondary {
                        key "address";
                        description "Enter the secondary list instance";

                        leaf address {
                            type types-sros:ipv4-unicast-address;
                            description "Secondary IPv4 address assigned to the interface";
                        }

                        leaf prefix-length {
                            type uint32 {
                                range "0..32";
                            }
                            mandatory true;
                            description "IPv4 address prefix length";
                        }

                        leaf igp-inhibit {
                            type boolean;
                            default "false";
                            description "Disable the running IGP from recognizing secondary IP";
                        }

                        leaf broadcast {
                            type types-services:broadcast-address-format;
                            default "host-ones";
                            description "Broadcast address format";
                        }

                        leaf track-srrp {
                            type uint32 {
                                range "1..4294967295";
                            }
                            description "SRRP instance whose state is tracked on this IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list secondary

                    container addresses {
                        description "Enter the addresses context";

                        list address {
                            key "ipv4-address";
                            description "Enter the address list instance";

                            leaf ipv4-address {
                                type types-sros:ipv4-unicast-address;
                                description "IPv4 address for the interface";
                            }

                            leaf prefix-length {
                                type uint32 {
                                    range "0..32";
                                }
                                mandatory true;
                                description "IPv4 address prefix length";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list address

                    } // container addresses

                    container neighbor-discovery {
                        when "../../tunnel = 'false'";
                        description "Enter the neighbor-discovery context";

                        leaf timeout {
                            type uint32 {
                                range "0..65535";
                            }
                            units "seconds";
                            default "14400";
                            description "Timeout for an ARP entry learned on the interface";
                        }

                        leaf retry-timer {
                            type uint32 {
                                range "1..300";
                            }
                            units "deciseconds";
                            default "50";
                            description "ARP retry interval";
                        }

                        leaf learn-unsolicited {
                            type boolean;
                            default "false";
                            description "Learn new entries from any received NA message";
                        }

                        leaf proactive-refresh {
                            type boolean;
                            default "false";
                            description "Send a single refresh message before entry timeout";
                        }

                        leaf populate {
                            type boolean;
                            default "false";
                            description "Allow static and dynamic hosts to be populated in system ARP cache";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        leaf local-proxy-arp {
                            type boolean;
                            description "Enable local proxy ARP on interface";
                        }

                        leaf remote-proxy-arp {
                            type boolean;
                            default "false";
                            description "Enable remote proxy ARP on the interface";
                        }

                        leaf-list proxy-arp-policy {
                            type leafref {
                                path "../../../../../../policy-options/policy-statement/name";
                            }
                            max-elements 5;
                            ordered-by user;
                            description "Proxy ARP policy name";
                        }

                        container host-route {
                            description "Enter the host-route context";

                            list populate {
                                key "route-type";
                                description "Enter the populate list instance";

                                leaf route-type {
                                    type enumeration {
                                        enum "static"                       { value 1; }
                                        enum "dynamic"                      { value 2; }
                                        enum "evpn"                         { value 3; }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list populate

                        } // container host-route

                        container limit {
                            description "Enter the limit context";

                            leaf max-entries {
                                type types-router:ipv4-neighbor-limit;
                                description "Maximum number of entries learned on an IP interface";
                            }

                            leaf log-only {
                                type boolean;
                                default "false";
                                description "Generate log entries only if limit is reached";
                            }

                            leaf threshold {
                                type uint32 {
                                    range "1..100";
                                }
                                units "percent";
                                default "90";
                                description "Threshold value that triggers a warning message";
                            }

                        } // container limit

                        container static-neighbor-unnumbered {
                            when "../../unnumbered/ip-address or ../../unnumbered/ip-int-name or ../../unnumbered/system";
                            presence "Enable the static-neighbor-unnumbered context";
                            description "Enable the static-neighbor-unnumbered context";

                            leaf mac-address {
                                type yang:mac-address;
                                mandatory true;
                                description "MAC address for the static neighbor";
                            }

                        } // container static-neighbor-unnumbered

                        list static-neighbor {
                            when "not(../../unnumbered/ip-address) and not(../../unnumbered/ip-int-name) and not(../../unnumbered/system)";
                            key "ipv4-address";
                            description "Enter the static-neighbor list instance";

                            leaf ipv4-address {
                                type types-sros:ipv4-address;
                                description "IPv4 address that corresponds to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                    container dhcp {
                        description "Enter the dhcp context";

                        leaf admin-state {
                            type types-sros:admin-state;
                            description "Administrative state of DHCP";
                        }

                        leaf description {
                            type types-sros:description;
                            description "Text description";
                        }

                        leaf python-policy {
                            when "../../../tunnel = 'false'";
                            type leafref {
                                path "../../../../../../python/python-policy/name";
                            }
                            description "Python policy";
                        }

                        leaf-list server {
                            type types-sros:ipv4-unicast-address;
                            max-elements 8;
                            ordered-by user;
                            description "IP addresses for DHCP server requests";
                        }

                        leaf trusted {
                            type boolean;
                            default "false";
                            description "Relay untrusted packets";
                        }

                        leaf gi-address {
                            type types-sros:ipv4-unicast-address;
                            description "GI address for the DHCP relay";
                        }

                        leaf release-include-gi-address {
                            type boolean;
                            default "false";
                            description "Include gateway IP address in DHCP Release messages";
                        }

                        leaf src-ip-addr {
                            type enumeration {
                                enum "auto"                         { value 0; }
                                enum "gi-address"                   { value 1; }
                            }
                            default "auto";
                            description "Type of source address to use for DHCP relay";
                        }

                        leaf relay-plain-bootp {
                            when "../../../tunnel = 'false'";
                            type boolean;
                            default "false";
                            description "Enable relaying of plain BOOTP packets";
                        }

                        leaf use-arp {
                            when "../../../tunnel = 'false'";
                            type boolean;
                            default "false";
                            description "Use ARP to determine the destination hardware address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container proxy-server {
                            description "Enter the proxy-server context";

                            leaf admin-state {
                                type types-sros:admin-state;
                                default "disable";
                                description "Administrative state of the DHCP proxy server";
                            }

                            leaf emulated-server {
                                type types-sros:ipv4-unicast-address;
                                description "IP address used as the DHCP server address for the SAP";
                            }

                            container lease-time {
                                description "Enter the lease-time context";

                                leaf value {
                                    type types-sros:time-duration {
                                        range "300..315446399";
                                    }
                                    units "seconds";
                                    description "DHCP lease time";
                                }

                                leaf radius-override {
                                    type boolean;
                                    default "false";
                                    description "Use lease time information provided by RADIUS server";
                                }

                            } // container lease-time

                        } // container proxy-server

                        container option-82 {
                            description "Enter the option-82 context";

                            leaf action {
                                type enumeration {
                                    enum "replace"                      { value 1; }
                                    enum "drop"                         { value 2; }
                                    enum "keep"                         { value 3; }
                                }
                                default "keep";
                                description "Action to take with received DHCP Option 82";
                            }

                            container circuit-id {
                                description "Enter the circuit-id context";

                                choice circuit-id {
                                    default "ascii-tuple";
                                    case none {

                                        leaf none {
                                            type empty;
                                            description "Do not include the circuit ID";
                                        }

                                    }
                                    case ifindex {

                                        leaf ifindex {
                                            type empty;
                                            description "Use the interface index for the circuit ID";
                                        }

                                    }
                                    case ascii-tuple {

                                        leaf ascii-tuple {
                                            type empty;
                                            description "Use the ASCII-encoded tuple for the circuit ID";
                                        }

                                    }
                                    case sap-id {

                                        leaf sap-id {
                                            type empty;
                                            description "Use the SAP ID";
                                        }

                                    }
                                    case vlan-ascii-tuple {

                                        leaf vlan-ascii-tuple {
                                            type empty;
                                            description "Include the VLAN ID and dot1p bits in the ASCII tuple";
                                        }

                                    }
                                }
                            } // container circuit-id

                            container remote-id {
                                description "Enter the remote-id context";

                                choice remote-id {
                                    default "none";
                                    case none {

                                        leaf none {
                                            type empty;
                                            description "Do not include the remote ID";
                                        }

                                    }
                                    case mac {

                                        leaf mac {
                                            type empty;
                                            description "Use the MAC address for the remote ID";
                                        }

                                    }
                                    case ascii-string {

                                        leaf ascii-string {
                                            type types-sros:string-not-all-spaces {
                                                length "1..32";
                                            }
                                            description "User-defined ASCII string for the remote ID";
                                        }

                                    }
                                }
                            } // container remote-id

                            container vendor-specific-option {
                                description "Enter the vendor-specific-option context";

                                leaf system-id {
                                    type boolean;
                                    default "false";
                                    description "Send the system ID in the VSO";
                                }

                                leaf client-mac-address {
                                    type boolean;
                                    default "false";
                                    description "Send the MAC address in the VSO";
                                }

                                leaf pool-name {
                                    type boolean;
                                    default "false";
                                    description "Send the pool name in the VSO";
                                }

                                leaf service-id {
                                    type boolean;
                                    default "false";
                                    description "Send the service ID in the Vendor Specific Option";
                                }

                                leaf sap-id {
                                    type boolean;
                                    default "false";
                                    description "Send SAP ID in the sub-option of the DHCP relay packet";
                                }

                                leaf string {
                                    type types-sros:string-not-all-spaces {
                                        length "1..32";
                                    }
                                    description "User-defined ASCII string for the VSO";
                                }

                            } // container vendor-specific-option

                        } // container option-82

                        container lease-populate {
                            description "Enter the lease-populate context";

                            leaf max-leases {
                                type uint32 {
                                    range "0..511999";
                                }
                                description "Maximum number of DHCPv4 leases allowed";
                            }

                        } // container lease-populate

                        container relay-proxy {
                            presence "Enable the relay-proxy context";
                            description "Enter the relay-proxy context";

                            leaf release-update-src-ip {
                                type boolean;
                                default "false";
                                description "Update the source IP address of a DHCP RELEASE message";
                            }

                            leaf siaddr-override {
                                type types-sros:ipv4-unicast-address;
                                description "DHCP server IP address for address hiding function";
                            }

                        } // container relay-proxy

                    } // container dhcp

                    list vrrp {
                        key "virtual-router-id";
                        description "Enter the vrrp list instance";

                        leaf virtual-router-id {
                            type int32 {
                                range "1..255";
                            }
                            description "Virtual Router Identifier (VRID) for the IP interface";
                        }

                        leaf authentication-key {
                            type types-sros:encrypted-leaf {
                                length "1..38";
                            }
                            description "Password for simple text authentication";
                        }

                        leaf-list backup {
                            type types-sros:ipv4-unicast-address;
                            max-elements 16;
                            description "Virtual router IP addresses for the interface";
                        }

                        leaf message-interval {
                            type uint32 {
                                range "1..2559";
                            }
                            units "deciseconds";
                            default "10";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ssh-reply {
                            type boolean;
                            default "false";
                            description "Allow the non-owner master to reply to SSH requests";
                        }

                        leaf ntp-reply {
                            type boolean;
                            default "false";
                            description "Allow processing of NTP requests";
                        }

                        leaf oper-group {
                            type leafref {
                                path "../../../../../oper-group/name";
                            }
                            description "Operational group name associated with the VRRP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ipv4-address;
                                sros-ext:immutable;
                                mandatory true;
                                description "Destination IP address to use for BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container bfd-liveness

                    } // list vrrp

                } // container ipv4

                container ipv6 {
                    presence "Enable the ipv6 context";
                    description "Enable the ipv6 context";

                    leaf qos-route-lookup {
                        type types-router:qos-route-lookup;
                        description "IP address for QoS route lookup for ingress IP packets";
                    }

                    leaf forward-ipv4-packets {
                        type boolean;
                        default "false";
                        description "Forward unencapsulated IPv4 packets";
                    }

                    leaf tcp-mss {
                        type types-router:ipv6-tcp-mss-ext;
                        description "TCP maximum segment size for the interface";
                    }

                    leaf duplicate-address-detection {
                        type boolean;
                        default "true";
                        description "Enable Duplicate Address Detection per interface";
                    }

                    leaf local-dhcp-server {
                        when "../../tunnel = 'false'";
                        type leafref {
                            path "../../../../../router/dhcp-server/dhcpv6/name";
                        }
                        description "DHCP server for the interface";
                    }

                    container urpf-check {
                        presence "Enable the urpf-check context";
                        description "Enable the urpf-check context";

                        leaf ignore-default {
                            type boolean;
                            default "false";
                            description "Ignore default route when performing a uRPF check";
                        }

                        leaf mode {
                            type types-router:urpf-check-mode;
                            default "strict";
                            description "Unicast RPF check mode";
                        }

                    } // container urpf-check

                    container icmp6 {
                        description "Enter the icmp6 context";

                        container packet-too-big {
                            description "Enter the packet-too-big context";

                            leaf admin-state {
                                type types-sros:admin-state;
                                default "enable";
                                description "Administrative state of Packet Too Big message sends";
                            }

                            leaf number {
                                type uint16 {
                                    range "10..1000";
                                }
                                default "100";
                                description "Number of Packet Too big Messages issued per time frame";
                            }

                            leaf seconds {
                                type uint16 {
                                    range "1..60";
                                }
                                default "10";
                                description "Time used to limit Packet Too Big messages";
                            }

                        } // container packet-too-big

                        container param-problem {
                            description "Enter the param-problem context";

                            leaf admin-state {
                                type types-sros:admin-state;
                                default "enable";
                                description "Administrative state of Parameter Problem message sends";
                            }

                            leaf number {
                                type uint16 {
                                    range "10..1000";
                                }
                                default "100";
                                description "Number used to limit ICMPv6 Parameter Problem messages";
                            }

                            leaf seconds {
                                type uint16 {
                                    range "1..60";
                                }
                                default "10";
                                description "Time used to limit ICMPv6 Parameter Problem messages";
                            }

                        } // container param-problem

                        container redirects {
                            description "Enter the redirects context";

                            leaf admin-state {
                                type types-sros:admin-state;
                                default "enable";
                                description "Administrative state of Redirect message sends";
                            }

                            leaf number {
                                type uint16 {
                                    range "10..1000";
                                }
                                default "100";
                                description "Number to limit ICMPv6 Redirect messages per time frame";
                            }

                            leaf seconds {
                                type uint16 {
                                    range "1..60";
                                }
                                default "10";
                                description "Time used to limit ICMPv6 Redirect messages";
                            }

                        } // container redirects

                        container time-exceeded {
                            description "Enter the time-exceeded context";

                            leaf admin-state {
                                type types-sros:admin-state;
                                default "enable";
                                description "Administrative state of Time Exceeded message sends";
                            }

                            leaf number {
                                type uint16 {
                                    range "10..2000";
                                }
                                default "100";
                                description "Number to limit Time Exceeded messages per time frame";
                            }

                            leaf seconds {
                                type uint16 {
                                    range "1..60";
                                }
                                default "10";
                                description "Time used to limit ICMPv6 Time Exceeded messages";
                            }

                        } // container time-exceeded

                        container unreachables {
                            description "Enter the unreachables context";

                            leaf admin-state {
                                type types-sros:admin-state;
                                default "enable";
                                description "Administrative state of Unreachable message sends";
                            }

                            leaf number {
                                type uint16 {
                                    range "10..2000";
                                }
                                default "100";
                                description "Number to limit Unreachable messages per time frame";
                            }

                            leaf seconds {
                                type uint16 {
                                    range "1..60";
                                }
                                default "10";
                                description "Time used to limit ICMPv6 Unreachable messages";
                            }

                        } // container unreachables

                    } // container icmp6

                    container link-local-address {
                        description "Enter the link-local-address context";

                        leaf address {
                            type types-sros:ipv6-address;
                            description "IPv6 link-local address";
                        }

                        leaf duplicate-address-detection {
                            type boolean;
                            default "true";
                            description "Enable Duplicate Address Detection";
                        }

                    } // container link-local-address

                    container bfd {
                        description "Enter the bfd context";

                        leaf admin-state {
                            type types-sros:admin-state;
                            default "disable";
                            description "Administrative state of BFD sessions";
                        }

                        leaf transmit-interval {
                            type uint32 {
                                range "10..100000";
                            }
                            units "milliseconds";
                            default "100";
                            description "BFD transmit interval over this interface";
                        }

                        leaf receive {
                            type uint32 {
                                range "10..100000";
                            }
                            units "milliseconds";
                            default "100";
                            description "BFD receive interval over this interface";
                        }

                        leaf multiplier {
                            type uint32 {
                                range "1..20";
                            }
                            default "3";
                            description "Number of consecutive BFD messages missed from the peer";
                        }

                        leaf echo-receive {
                            type uint32 {
                                range "100..100000";
                            }
                            units "milliseconds";
                            description "Minimum echo interval over this interface";
                        }

                        leaf type {
                            type enumeration {
                                enum "cpm-np"                       { value 1; }
                                enum "auto"                         { value 2; }
                                enum "fp"                           { value 3; }
                            }
                            default "auto";
                            description "Local termination point for the BFD session";
                        }

                    } // container bfd

                    list address {
                        key "ipv6-address";
                        description "Enter the address list instance";

                        leaf ipv6-address {
                            type types-sros:ipv6-address;
                            description "IPv6 address assigned to the interface";
                        }

                        leaf prefix-length {
                            type uint32 {
                                range "4..128";
                            }
                            mandatory true;
                            description "IPv6 address prefix length";
                        }

                        leaf eui-64 {
                            type boolean;
                            sros-ext:immutable;
                            default "false";
                            description "Form IPv6 address from prefix and 64-bit interface ID";
                        }

                        leaf duplicate-address-detection {
                            type boolean;
                            sros-ext:immutable;
                            default "true";
                            description "Enable Duplicate Address Detection";
                        }

                        leaf primary-preference {
                            type uint32 {
                                range "1..4294967295";
                            }
                            description "Index assigned to the IPv6 address of the interface";
                        }

                        leaf track-srrp {
                            type uint32 {
                                range "1..4294967295";
                            }
                            description "SRRP ID whose state is tracked on this IP address";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list address

                    container dhcp6 {
                        when "../../tunnel = 'false'";
                        description "Enter the dhcp6 context";

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container relay {
                            description "Enter the relay context";

                            leaf description {
                                type types-sros:description;
                                description "Text description";
                            }

                            leaf admin-state {
                                type types-sros:admin-state;
                                default "disable";
                                description "Administrative state of DHCPv6 Relay";
                            }

                            leaf link-address {
                                type types-sros:ipv6-address;
                                description "Link address of the DHCPv6 relay messages";
                            }

                            leaf neighbor-resolution {
                                type boolean;
                                default "false";
                                description "Enable neighbor resolution via DHCPv6 relay";
                            }

                            leaf python-policy {
                                type leafref {
                                    path "../../../../../../../python/python-policy/name";
                                }
                                description "Python policy name";
                            }

                            leaf source-address {
                                type types-sros:ipv6-unicast-or-linklocal-address;
                                description "Source IPv6 address of the DHCPv6 relay messages";
                            }

                            leaf user-db {
                                type leafref {
                                    path "../../../../../../../subscriber-mgmt/local-user-db/name";
                                }
                                description "Local user database for authentication";
                            }

                            leaf-list server {
                                type types-sros:ipv6-address-with-zone;
                                max-elements 8;
                                ordered-by user;
                                description "DHCPv6 server to which the DHCPv6 requests are forwarded";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container lease-populate {
                                description "Enter the lease-populate context";

                                leaf max-nbr-of-leases {
                                    type int32 {
                                        range "0..32767";
                                    }
                                    default "0";
                                    description "Maximum lease state entries allowed for the interface";
                                }

                                container route-populate {
                                    description "Enter the route-populate context";

                                    leaf na {
                                        type boolean;
                                        default "false";
                                        description "Create route based on IA_NA prefix option in relay-reply message";
                                    }

                                    leaf ta {
                                        type boolean;
                                        default "false";
                                        description "Create route based on IA_TA prefix option in relay-reply message";
                                    }

                                    container pd {
                                        presence "Enable the pd context";
                                        description "Enable the pd context";

                                        leaf exclude {
                                            type boolean;
                                            default "false";
                                            description "Create back hole route based on prefix exclude option in relay-reply message";
                                        }

                                    } // container pd

                                } // container route-populate

                            } // container lease-populate

                            container option {
                                description "Enter the option context";

                                leaf remote-id {
                                    type boolean;
                                    default "false";
                                    description "Send remote ID option in the DHCPv6 relay packet";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container interface-id {
                                    description "Enter the interface-id context";

                                    choice interface-id {
                                        case ascii-tuple {

                                            leaf ascii-tuple {
                                                type empty;
                                                description "Use ASCII-encoded concatenated tuple";
                                            }

                                        }
                                        case sap-id {

                                            leaf sap-id {
                                                type empty;
                                                description "Use SAP ID in interface ID option in relay packet";
                                            }

                                        }
                                        case if-index {

                                            leaf if-index {
                                                type empty;
                                                description "Use interface index in the DHCPv6 relay packet";
                                            }

                                        }
                                        case string {

                                            leaf string {
                                                type types-sros:string-not-all-spaces {
                                                    length "1..80";
                                                }
                                                description "String for interface ID option in DHCPv6 relay packet";
                                            }

                                        }
                                    }
                                } // container interface-id

                            } // container option

                        } // container relay

                        container server {
                            description "Enter the server context";

                            leaf max-nbr-of-leases {
                                type int32 {
                                    range "0..8000";
                                }
                                default "8000";
                                description "DHCPv6 leases allowed";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container prefix-delegation {
                                description "Enter the prefix-delegation context";

                                leaf admin-state {
                                    type types-sros:admin-state;
                                    default "disable";
                                    description "Administrative state of the prefix delegation";
                                }

                                list prefix {
                                    key "ipv6-prefix";
                                    description "Enter the prefix list instance";

                                    leaf ipv6-prefix {
                                        type types-sros:ipv6-prefix;
                                        description "IPv6 address and prefix";
                                    }

                                    leaf preferred-lifetime {
                                        type types-services:ipv6-prefix-lifetime;
                                        units "seconds";
                                        default "604800";
                                        description "Preferred lifetime of the prefix";
                                    }

                                    leaf valid-lifetime {
                                        type types-services:ipv6-prefix-lifetime;
                                        units "seconds";
                                        default "2592000";
                                        description "Valid lifetime of the prefix";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container client-id {
                                        description "Enter the client-id context";

                                        leaf duid {
                                            type string {
                                                length "1..130";
                                            }
                                            description "Requesting router ID";
                                        }

                                        leaf iaid {
                                            type uint32 {
                                                range "1..4294967295";
                                            }
                                            description "IAID from the requesting router to match";
                                        }

                                    } // container client-id

                                } // list prefix

                            } // container prefix-delegation

                        } // container server

                    } // container dhcp6

                    container neighbor-discovery {
                        when "../../tunnel = 'false'";
                        description "Enter the neighbor-discovery context";

                        leaf reachable-time {
                            type types-router:neighbor-discovery-reachable-time;
                            description "Neighbor reachability detection timer";
                        }

                        leaf stale-time {
                            type types-router:neighbor-discovery-stale-time;
                            description "Time a Neighbor Discovery cache entry remains stale";
                        }

                        leaf learn-unsolicited {
                            type types-router:ipv6-address-type-selection;
                            description "Type of entries learned from unsolicited NA messages";
                        }

                        leaf proactive-refresh {
                            type types-router:ipv6-address-type-selection;
                            description "Proactive refresh of neighbor entries";
                        }

                        leaf populate-host {
                            status obsolete;
                            type boolean;
                            default "false";
                            description "Allow addition or deletion of host routes in route table derived from ARP entries in ARP cache";
                        }

                        leaf route-tag {
                            status obsolete;
                            type types-router:route-tag;
                            description "ARP route tag";
                        }

                        leaf local-proxy-nd {
                            type boolean;
                            default "false";
                            description "Enable local proxy neighbor discovery on the interface";
                        }

                        leaf-list proxy-nd-policy {
                            type leafref {
                                path "../../../../../../policy-options/policy-statement/name";
                            }
                            max-elements 5;
                            ordered-by user;
                            description "Proxy Neighbor Discovery policy name for the interface";
                        }

                        container host-route {
                            description "Enter the host-route context";

                            list populate {
                                key "route-type";
                                description "Enter the populate list instance";

                                leaf route-type {
                                    type enumeration {
                                        enum "static"                       { value 1; }
                                        enum "dynamic"                      { value 2; }
                                        enum "evpn"                         { value 3; }
                                    }
                                    description "Type of ARP or ND entries that generate host routes";
                                }

                                leaf route-tag {
                                    type uint32 {
                                        range "1..255";
                                    }
                                    sros-ext:immutable;
                                    description "Tag value used with the host route from an ARP/ND entry";
                                }

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                            } // list populate

                        } // container host-route

                        container secure-nd {
                            description "Enter the secure-nd context";

                            leaf allow-unsecured-msgs {
                                type boolean;
                                default "true";
                                description "Accept unsecured messages";
                            }

                            leaf public-key-min-bits {
                                type uint32 {
                                    range "512..1024";
                                }
                                default "1024";
                                description "Minimum acceptable key length for public keys in CGA";
                            }

                            leaf security-parameter {
                                type uint32 {
                                    range "0..1";
                                }
                                default "1";
                                description "Security parameter used in the generation of a CGA";
                            }

                            leaf admin-state {
                                type types-sros:admin-state;
                                default "disable";
                                description "Administrative state of Secure Neighbor Discovery";
                            }

                        } // container secure-nd

                        container limit {
                            description "Enter the limit context";

                            leaf max-entries {
                                type types-router:ipv6-neighbor-limit;
                                description "Maximum number of entries learned on an IP interface";
                            }

                            leaf log-only {
                                type boolean;
                                default "false";
                                description "Generate log entries when limit is reached";
                            }

                            leaf threshold {
                                type uint32 {
                                    range "1..100";
                                }
                                units "percent";
                                default "90";
                                description "Threshold percentage that triggers a warning message";
                            }

                        } // container limit

                        list static-neighbor {
                            key "ipv6-address";
                            description "Enter the static-neighbor list instance";

                            leaf ipv6-address {
                                type types-sros:ipv6-address;
                                description "IPv6 address corresponding to the physical address";
                            }

                            leaf mac-address {
                                type yang:mac-address;
                                mandatory true;
                                description "MAC address for the static neighbor";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list static-neighbor

                    } // container neighbor-discovery

                    list vrrp {
                        key "virtual-router-id";
                        max-elements 4;
                        description "Enter the vrrp list instance";

                        leaf virtual-router-id {
                            type int32 {
                                range "1..255";
                            }
                            description "Virtual Router Identifier (VRID) for the IP interface";
                        }

                        leaf-list backup {
                            type types-sros:ipv6-address;
                            max-elements 4;
                            description "Virtual router IP addresses for the interface";
                        }

                        leaf message-interval {
                            type uint32 {
                                range "10..4095";
                            }
                            units "centiseconds";
                            default "100";
                            description "Interval for sending VRRP advertisement messages";
                        }

                        leaf owner {
                            type boolean;
                            sros-ext:immutable;
                            default "false";
                            description "Designate the virtual router instance as owner";
                        }

                        leaf passive {
                            type boolean;
                            sros-ext:immutable;
                            default "false";
                            description "Suppress the processing of VRRP advertisement messages";
                        }

                        leaf init-delay {
                            type uint32 {
                                range "1..65535";
                            }
                            units "seconds";
                            description "VRRP initialization delay timer";
                        }

                        leaf mac {
                            type types-sros:mac-unicast-address;
                            description "Virtual MAC address to use in ARP responses";
                        }

                        leaf priority {
                            type uint32 {
                                range "1..255";
                            }
                            description "Base priority for the VRRP";
                        }

                        leaf admin-state {
                            type types-sros:admin-state;
                            default "enable";
                            description "Administrative state of VRRP";
                        }

                        leaf master-int-inherit {
                            type boolean;
                            description "Allow master instance to dictate the master down timer";
                        }

                        leaf ping-reply {
                            type boolean;
                            default "false";
                            description "Allow non-owner master to reply to ICMP echo requests";
                        }

                        leaf policy {
                            type leafref {
                                path "../../../../../../vrrp/policy/policy-id";
                            }
                            description "VRRP priority control policy";
                        }

                        leaf preempt {
                            type boolean;
                            default "true";
                            description "Allow the VRRP to override an existing non-owner master";
                        }

                        leaf telnet-reply {
                            type boolean;
                            default "false";
                            description "Allow non-owner master to reply to Telnet requests";
                        }

                        leaf traceroute-reply {
                            type boolean;
                            default "false";
                            description "Allow non-owner master to reply to traceroute requests";
                        }

                        leaf standby-forwarding {
                            type boolean;
                            default "false";
                            description "Allow standby router to forward traffic";
                        }

                        leaf ntp-reply {
                            type boolean;
                            default "false";
                            description "Allow processing of NTP requests";
                        }

                        leaf oper-group {
                            type leafref {
                                path "../../../../../oper-group/name";
                            }
                            description "Operational group name associated with the VRRP";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container bfd-liveness {
                            presence "Enable the bfd-liveness context";
                            description "Enable the bfd-liveness context";

                            leaf dest-ip {
                                type types-sros:ip-address;
                                sros-ext:immutable;
                                mandatory true;
                                description "Destination address for the BFD session";
                            }

                            leaf service-name {
                                type types-services:service-name;
                                sros-ext:immutable;
                                description "Administrative service name";
                            }

                            leaf interface-name {
                                type types-sros:interface-name;
                                sros-ext:immutable;
                                mandatory true;
                                description "Name of the interface running BFD";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // container bfd-liveness

                    } // list vrrp

                } // container ipv6

                container if-attribute {
                    description "Enter the if-attribute context";

                    leaf-list admin-group {
                        type leafref {
                            path "../../../../../routing-options/if-attribute/admin-group/group-name";
                        }
                        max-elements 32;
                        description "Administrative group name for the interface";
                    }

                    list srlg-group {
                        key "name";
                        description "Add a list entry for srlg-group";

                        leaf name {
                            type leafref {
                                path "../../../../../../routing-options/if-attribute/srlg-group/name";
                            }
                            description "SRLG name";
                        }

                    } // list srlg-group

                } // container if-attribute

            } // list interface

            list redundant-interface {
                key "interface-name";
                description "Enter the redundant-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    container ipv4 {
                        description "Enter the ipv4 context";

                        container up {
                            description "Enter the up context";

                            leaf seconds {
                                type types-router:hold-time-seconds;
                                units "seconds";
                                description "Up hold time for the IP interface";
                            }

                        } // container up

                        container down {
                            description "Enter the down context";

                            leaf seconds {
                                type types-router:hold-time-seconds;
                                units "seconds";
                                description "Down hold time for the IP interface";
                            }

                            leaf init-only {
                                type boolean;
                                default "false";
                                description "Apply delay only at interface configuration or reboot";
                            }

                        } // container down

                    } // container ipv4

                } // container hold-time

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of the SDP binding to the service";
                    }

                    leaf control-word {
                        type boolean;
                        default "false";
                        description "Use the control word as preferred";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "Ingress MPLS VC label to send packets to the far end";
                        }

                        container filter {
                            description "Enter the filter context";

                            leaf ip {
                                type leafref {
                                    path "../../../../../../../filter/ip-filter/filter-name";
                                }
                                description "IPv4 filter policy name";
                            }

                        } // container filter

                    } // container ingress

                    container egress {
                        description "Enter the egress context";

                        leaf vc-label {
                            type types-services:egress-vc-label;
                            sros-ext:auto-restart-to-modify;
                            description "Egress MPLS VC label to send packets to the far end";
                        }

                        container filter {
                            description "Enter the filter context";

                            leaf ip {
                                type leafref {
                                    path "../../../../../../../filter/ip-filter/filter-name";
                                }
                                description "IPv4 filter policy name";
                            }

                        } // container filter

                    } // container egress

                } // list spoke-sdp

                container ipv4 {
                    description "Enter the ipv4 context";

                    container primary {
                        presence "Enable the primary context";
                        description "Enter the primary context";

                        leaf address {
                            type types-sros:ipv4-unicast-address;
                            mandatory true;
                            description "IPv4 address to be assigned to the interface";
                        }

                        leaf prefix-length {
                            type uint32 {
                                range "0..32";
                            }
                            mandatory true;
                            description "IPv4 address prefix length";
                        }

                        leaf remote-ip {
                            type types-sros:ipv4-unicast-address;
                            description "Remote IP address for the interface";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container primary

                } // container ipv4

            } // list redundant-interface

            list aarp-interface {
                key "interface-name";
                description "Enter the aarp-interface list instance";

                leaf interface-name {
                    type types-sros:interface-name;
                    description "Interface name";
                }

                leaf description {
                    type types-sros:very-long-description;
                    description "Text description";
                }

                leaf admin-state {
                    type types-sros:admin-state;
                    default "enable";
                    description "Administrative state of the interface";
                }

                leaf ip-mtu {
                    type types-router:ip-mtu-ext;
                    units "bytes";
                    description "IP MTU applied to outgoing packets";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list spoke-sdp {
                    key "sdp-bind-id";
                    max-elements 1;
                    description "Enter the spoke-sdp list instance";

                    leaf sdp-bind-id {
                        type types-services:sdp-bind-id;
                        description "SDP binding ID";
                    }

                    leaf description {
                        type types-sros:description;
                        description "Text description";
                    }

                    leaf admin-state {
                        type types-sros:admin-state;
                        default "enable";
                        description "Administrative state of this service SDP binding";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "VC ingress value that indicates a specific connection";
                        }

                        container filter {
                            description "Enter the filter context";

                            leaf ip {
                                type leafref {
                                    path "../../../../../../../filter/ip-filter/filter-name";
                                }
                                description "IP filter name";
                            }

                        } // container filter

                    } // container ingress

                    container egress {
                        description "Enter the egress context";

                        leaf vc-label {
                            type types-services:egress-vc-label;
                            sros-ext:auto-restart-to-modify;
                            description "VC egress value that indicates a specific connection";
                        }

                        container filter {
                            description "Enter the filter context";

                            leaf ip {
                                type leafref {
                                    path "../../../../../../../filter/ip-filter/filter-name";
                                }
                                description "IP filter ID";
                            }

                        } // container filter

                    } // container egress

                    container aarp {
                        presence "Enable the aarp context";
                        description "Enter the aarp context";

                        leaf id {
                            type leafref {
                                path "../../../../../../application-assurance/aarp/aarp-id";
                            }
                            sros-ext:immutable;
                            mandatory true;
                            description "AARP instance ID";
                        }

                        leaf type {
                            type types-services:l3-bsx-aarp-service-ref-type;
                            sros-ext:immutable;
                            mandatory true;
                            description "Role of the spoke SDP referenced by the AARP";
                        }

                    } // container aarp

                } // list spoke-sdp

            } // list aarp-interface

            container igmp-host-tracking {
                description "Enter the igmp-host-tracking context";

                leaf admin-state {
                    type types-sros:admin-state;
                    default "disable";
                    description "Administrative state of IGMP host tracking";
                }

                leaf expiry-time {
                    type types-sros:time-duration {
                        range "1..65535";
                    }
                    units "seconds";
                    default "260";
                    description "Time that the system continues to track inactive hosts";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container igmp-host-tracking

            uses conf-svc-ies-sub-if-subscriber-interface;
            uses conf-svc-ies-vdo-if-video-interface;
        } // list ies

    } // grouping conf-svc-ies

}
