module nokia-bof-state {

    yang-version "1.1";

    namespace "urn:nokia.com:sros:ns:yang:sr:bof-state";

    prefix "bof-state";

    import nokia-sros-yang-extensions     { prefix "sros-ext"; }
    import nokia-state                    { prefix "state"; }
    import nokia-types-port               { prefix "types-port"; }
    import nokia-types-router             { prefix "types-router"; }
    import nokia-types-sros               { prefix "types-sros"; }

    sros-ext:sros-major-release "rel26";
    organization "Nokia";
    contact
        "Nokia SR OS Support
         Web: <http://www.nokia.com>";
    description
        "Nokia YANG Data model to show state data on SR OS based routers.

         Copyright 2016 Nokia. All rights reserved. Reproduction of this document
         is authorized on the condition that the foregoing copyright notice is included.

         This nokia-bof-state YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    augment /state:state {

        container bof {
            config false;
            description "Enter the bof context";

            container booted {
                description "Enter the booted context";

                container auto-boot {
                    description "Enter the auto-boot context";

                    leaf port-mtu {
                        type uint32 {
                            range "512..9800";
                        }
                        units "bytes";
                        description "Port MTU setting";
                    }

                    leaf timeout {
                        type uint32 {
                            range "30..1440";
                        }
                        units "minutes";
                        description "Timeout of Auto-Boot";
                    }

                    choice auto-boot-mode {
                        case dhcp {

                            container dhcp {
                                description "Enter the dhcp context";

                                leaf client-id {
                                    type union {
                                        type enumeration {
                                            enum use-chassis-mac-address        { value 0; }
                                        }
                                        type types-sros:hex-string {
                                            length "3..118";
                                        }
                                        type string {
                                            length "1..58";
                                        }
                                    }
                                    description "DHCP client ID";
                                }

                                leaf management-port {
                                    type boolean;
                                    description "Use auto boot on the management port";
                                }

                                leaf ipv4 {
                                    type boolean;
                                    description "Use auto boot with IPv4";
                                }

                                leaf ipv6 {
                                    type boolean;
                                    description "Use auto boot with IPv6";
                                }

                                leaf include-user-class {
                                    type boolean;
                                    description "Include user class in auto boot provisioning";
                                }

                                container inband {
                                    description "Enter the inband context";

                                    choice inband-options {
                                        case specific-vlan {

                                            leaf vlan {
                                                type types-sros:vlan-id;
                                                description "Inband VLAN ID";
                                            }

                                        }
                                        case discovery-mode {

                                            leaf vlan-discovery {
                                                type boolean;
                                                description "Use VLAN discovery";
                                            }

                                        }
                                        case null-encapsulation {

                                            leaf null-encapsulation {
                                                type boolean;
                                                description "Use null encapsulation";
                                            }

                                        }
                                        case disabled {

                                            leaf disabled {
                                                type boolean;
                                                description "Do not use inband ports";
                                            }

                                        }
                                    }
                                } // container inband

                            } // container dhcp

                        }
                        case ospf {

                            container ospf {
                                description "Enter the ospf context";

                                leaf neid {
                                    type types-sros:hex-string {
                                        length "3";
                                    }
                                    description "Network Element ID";
                                }

                                leaf neip-ipv4 {
                                    type types-sros:ipv4-unicast-address;
                                    description "Network Element IPV4 Address";
                                }

                                leaf neip-ipv6 {
                                    type types-sros:ipv6-address;
                                    description "Network Element IPV6 Address";
                                }

                                leaf mtu {
                                    type types-router:ip-mtu;
                                    units "bytes";
                                    description "OSPF Mtu";
                                }

                                leaf vendor-id {
                                    type uint32 {
                                        range "1..254";
                                    }
                                    description "Vendor Id";
                                }

                            } // container ospf

                        }
                    }
                } // container auto-boot

                container auto-configure {
                    description "Enter the auto-configure context";

                    container ipv4 {
                        description "Enter the ipv4 context";

                        container dhcp {
                            description "Enter the dhcp context";

                            leaf client-id {
                                type union {
                                    type types-sros:hex-string {
                                        length "3..514";
                                    }
                                    type string {
                                        length "1..256";
                                    }
                                }
                                description "DHCP client ID";
                            }

                            leaf include-user-class {
                                type boolean;
                                description "Include user class information";
                            }

                            leaf timeout {
                                type uint32 {
                                    range "1..65535";
                                }
                                description "DHCP timeout";
                            }

                        } // container dhcp

                    } // container ipv4

                    container ipv6 {
                        description "Enter the ipv6 context";

                        container dhcp {
                            description "Enter the dhcp context";

                            leaf client-type {
                                type enumeration {
                                    enum duid-enterprise                { value 2; }
                                    enum duid-link-local                { value 3; }
                                }
                                description "DHCP client type";
                            }

                            leaf client-id {
                                type union {
                                    type types-sros:hex-string {
                                        length "3..514";
                                    }
                                    type string {
                                        length "1..256";
                                    }
                                }
                                description "DHCP client ID";
                            }

                            leaf include-user-class {
                                type boolean;
                                description "Include user class information";
                            }

                            leaf timeout {
                                type uint32 {
                                    range "1..65535";
                                }
                                description "DHCP timeout";
                            }

                        } // container dhcp

                    } // container ipv6

                } // container auto-configure

                container configuration {
                    description "Enter the configuration context";

                    leaf primary-location {
                        type types-sros:bof-cflash-and-url;
                        description "Primary configuration location";
                    }

                    leaf secondary-location {
                        type types-sros:bof-cflash-and-url;
                        description "Secondary configuration location";
                    }

                    leaf tertiary-location {
                        type types-sros:bof-cflash-and-url;
                        description "Tertiary configuration location";
                    }

                    leaf encrypt {
                        type boolean;
                        description "Whether BOF configuration files are encrypted.";
                    }

                    leaf password {
                        type types-sros:encrypted-leaf {
                            length "1..71";
                        }
                        description "Password for encrypted BOF configuration files.";
                    }

                    leaf encryption-key {
                        type types-sros:encrypted-leaf {
                            length "1..71";
                        }
                        description "Key for encrypted BOF configuration files.";
                    }

                } // container configuration

                container console {
                    description "Enter the console context";

                    leaf speed {
                        type uint32 {
                            range "9600|19200|38400|57600|115200";
                        }
                        units "bps";
                        description "Console port speed";
                    }

                    leaf wait-time {
                        type uint32 {
                            range "1..10";
                        }
                        units "seconds";
                        description "Wait time for interrupt to change boot parameters";
                    }

                } // container console

                container dns {
                    description "Enter the dns context";

                    leaf domain {
                        type string {
                            length "1..178";
                        }
                        description "System DNS domain name for DNS address resolution";
                    }

                    leaf primary-server {
                        type types-sros:ip-address;
                        description "Primary DNS server";
                    }

                    leaf secondary-server {
                        type types-sros:ip-address;
                        description "Secondary DNS server";
                    }

                    leaf tertiary-server {
                        type types-sros:ip-address;
                        description "Tertiary DNS server";
                    }

                } // container dns

                container image {
                    description "Enter the image context";

                    leaf primary-location {
                        type types-sros:bof-cflash-and-url;
                        description "Primary image location";
                    }

                    leaf secondary-location {
                        type types-sros:bof-cflash-and-url;
                        description "Secondary image location";
                    }

                    leaf tertiary-location {
                        type types-sros:bof-cflash-and-url;
                        description "Tertiary image location";
                    }

                } // container image

                container li {
                    description "Enter the li context";

                    leaf local-save {
                        type boolean;
                        description "Save the LI configuration locally";
                    }

                    leaf separate {
                        type boolean;
                        description "Separate access to the LI information";
                    }

                } // container li

                container license {
                    description "Enter the license context";

                    leaf primary-location {
                        type types-sros:bof-cflash-and-url;
                        description "Primary license file location";
                    }

                } // container license

                list port {
                    key "router-name";
                    description "Enter the port list instance";

                    leaf router-name {
                        type types-sros:named-item-64;
                        description "Administrative name for the virtual router";
                    }

                    leaf autonegotiate {
                        type enumeration {
                            enum false                          { value 0; }
                            enum true                           { value 1; }
                        }
                        description "Autonegotiate speed and duplex type on Ethernet port";
                    }

                    leaf duplex {
                        type types-port:duplex-mode;
                        description "Duplex type for the Ethernet port";
                    }

                    leaf speed {
                        type uint32 {
                            range "10|100|1000";
                        }
                        units "megabps";
                        description "Speed of the Ethernet port";
                    }

                } // list port

                list router {
                    key "router-name";
                    description "Enter the router list instance";

                    leaf router-name {
                        type types-sros:named-item-64;
                        description "Administrative name of the virtual router";
                    }

                    list interface {
                        key "interface-name";
                        description "Enter the interface list instance";

                        leaf interface-name {
                            type types-sros:interface-name;
                            description "Router interface name";
                        }

                        leaf ip-mtu {
                            type types-router:ip-mtu-ext;
                            units "bytes";
                            description "Interface IP MTU";
                        }

                        list cpm {
                            key "cpm-type";
                            description "Enter the cpm list instance";

                            leaf cpm-type {
                                type enumeration {
                                    enum active                         { value 0; }
                                    enum standby                        { value 1; }
                                    enum a                              { value 2; }
                                    enum b                              { value 3; }
                                    enum c                              { value 4; }
                                    enum d                              { value 5; }
                                }
                                description "CPM type";
                            }

                            container ipv4 {
                                description "Enter the ipv4 context";

                                leaf ip-address {
                                    type types-sros:ipv4-unicast-address;
                                    description "IPv4 address assigned to the interface";
                                }

                                leaf prefix-length {
                                    type uint32 {
                                        range "0..32";
                                    }
                                    description "IPv4 address prefix length";
                                }

                            } // container ipv4

                            container ipv6 {
                                description "Enter the ipv6 context";

                                leaf ipv6-address {
                                    type types-sros:ipv6-address;
                                    description "IPv6 address assigned to the interface";
                                }

                                leaf prefix-length {
                                    type uint32 {
                                        range "0..128";
                                    }
                                    description "IPv6 address prefix length";
                                }

                            } // container ipv6

                        } // list cpm

                    } // list interface

                    container static-routes {
                        description "Enter the static-routes context";

                        list route {
                            key "ip-prefix";
                            description "Enter the route list instance";

                            leaf ip-prefix {
                                type types-sros:ip-prefix;
                                description "IP prefix for the static route";
                            }

                            leaf next-hop {
                                type types-sros:ip-address;
                                description "Next-hop IP address";
                            }

                        } // list route

                    } // container static-routes

                } // list router

                container system {
                    description "Enter the system context";

                    leaf base-mac-address {
                        type types-sros:mac-unicast-address;
                        description "Base system MAC address";
                    }

                    leaf fips-140 {
                        type boolean;
                        description "Operate in FIP-140 mode";
                    }

                    leaf persistent-indices {
                        type boolean;
                        description "Classic and mixed management mode persistent indicies";
                    }

                    leaf profile {
                        type enumeration {
                            enum profile-a                      { value 1; }
                            enum profile-b                      { value 2; }
                        }
                        description "System capabilities profile";
                    }

                } // container system

            } // container booted

        } // container bof

    }
}
