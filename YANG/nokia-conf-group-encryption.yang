submodule nokia-conf-group-encryption {

    yang-version "1.1";

    belongs-to nokia-conf { prefix "conf"; }

    import nokia-sros-yang-extensions     { prefix "sros-ext"; }
    import nokia-types-sros               { prefix "types-sros"; }

    include nokia-conf-groups;

    sros-ext:sros-major-release "rel20";

    organization "Nokia";

    contact
        "Nokia SR OS Support
         Web: <http://www.nokia.com>";

    description
        "Nokia YANG Data model to configure Group encryption on SR OS based routers.

         Copyright 2016 Nokia. All rights reserved. Reproduction of this document
         is authorized on the condition that the foregoing copyright notice is included.

         This nokia-conf-group-encryption YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-03-25";

    grouping conf-group-encryption {
        container group-encryption {
            description "Enter the group-encryption context";

            leaf group-encryption-label {
                type uint32 {
                    range "32..2047";
                }
                description "The network-wide unique label to be used by group encryption. It is used as an identifier for encrypted packets and is a mandatory configuration for group encryption to be functional. Once a label value is used, it will be reserved and will not be available for any MPLS interface label-map pop operation.";
            }

            leaf-list apply-groups {
                type leafref {
                    path "../../groups/group/name";
                }
                max-elements 8;
                ordered-by user;
                description "Apply a configuration group at this level";
            }

            list encryption-keygroup {
                key "id";
                description "Enter the encryption-keygroup list instance";

                leaf id {
                    type uint32 {
                        range "1..127";
                    }
                    description "Identification of the encryption keygroup";
                }

                leaf description {
                    type types-sros:description;
                    description "Text description";
                }

                leaf authentication-algorithm {
                    type enumeration {
                        enum "sha256"                       { value 1; }
                        enum "sha512"                       { value 2; }
                    }
                    default "sha256";
                    description "The hashing algorithm used for the Authentication Header (AH) protocol's authentication function";
                }

                leaf encryption-algorithm {
                    type enumeration {
                        enum "aes128"                       { value 1; }
                        enum "aes256"                       { value 2; }
                    }
                    default "aes128";
                    description "The encryption algorithm to be used. Encryption only applies to ESP (Encapsulating Security Payload) configurations.";
                }

                leaf active-outbound-security-association {
                    type uint32 {
                        range "1..1023";
                    }
                    description "The Security Parameter Index (SPI) to be used when performing encryption and authentication on egressing packets using this keygroup";
                }

                leaf keygroup-name {
                    type types-sros:named-item-64-or-empty;
                    default "";
                    description "The name to associate with this keygroup";
                }

                leaf-list apply-groups {
                    type leafref {
                        path "../../../groups/group/name";
                    }
                    max-elements 8;
                    ordered-by user;
                    description "Apply a configuration group at this level";
                }

            } // list encryption-keygroup

        } // container group-encryption

    } // grouping conf-group-encryption

}
