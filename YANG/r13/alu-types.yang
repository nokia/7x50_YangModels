module alu-types {
    yang-version 1;

    namespace "urn:alcatel-lucent.com:sros:ns:yang:types";

    prefix "alu";

    alu:alu-major-release "rel19";

    organization "Alcatel-Lucent";

    contact
        "Alcatel-Lucent SR OS Support 
         Web: <http://www.alcatel-lucent.com>";

    description
        "Alcatel-Lucent YANG Data model defining data-types for SR OS based routers. 
         
         Copyright 2014-2015 Alcatel-Lucent, 2016 Nokia. All rights reserved. 
         Reproduction of this document is authorized on the condition that the 
         foregoing copyright notice is included. 
         
         This alu-types YANG module embodies Alcatel-Lucent's proprietary intellectual 
         property. Alcatel-Lucent retains all title and ownership in the Specification, 
         including any revisions. 
         
         Alcatel-Lucent grants all interested parties a non-exclusive license to use 
         and distribute an unmodified copy of this Specification in connection with 
         management of Alcatel-Lucent products, and without fee, provided this 
         copyright notice and license appear on all copies. 
         
         This Specification is supplied `as is', and Alcatel-Lucent makes no warranty, 
         either express or implied, as to the use, operation, condition, or performance 
         of the Specification.";

    revision "2015-06-10";

    typedef ieee-address {
      type string {
        pattern '([0-9a-fA-F]{2}(:[0-9a-fA-F]{2}){5})|([0-9a-fA-F]{2}(-[0-9a-fA-F]{2}){5})';
      }
      description
          "The ieee-address type represents an IEEE 802 MAC address.";
    } //typedef ieee-address

    extension alu-major-release {
      argument 'major-release';
      description
          "The SR OS Major Release to which this particular instance of this YANG module 
           belongs.";
    } //extension alu-major-release

  } //module  alu-types
