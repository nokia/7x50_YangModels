module alu-conf-port-network-r13 {
  yang-version "1";

  namespace "urn:alcatel-lucent.com:sros:ns:yang:conf-port-network-r13";

  prefix "conf-port-network-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure the network parameters for a port 
       on SR OS based routers. 
       
       Copyright 2014-2015 Alcatel-Lucent, 2016 Nokia. All rights reserved. 
       Reproduction of this document is authorized on the condition that the 
       foregoing copyright notice is included. 
       
       This alu-conf-port-network-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-port-network-r13 {
    container network {
      description
          "Configure the network parameters for a port";
      container egress {
        description
            "Configure network egress port parameters";
        list pool {
          key "name";
          description
              "Configure the egress pool policy for the port";
          leaf name {
            type string {
              length "1..32";
            }
          } //name

          container amber-alarm-threshold {
            description
                "Configure amber alarm threshold";
            leaf percentage {
              type uint32 {
                range "1..1000";
              }
            } //percentage

          } //container amber-alarm-threshold

          container red-alarm-threshold {
            description
                "Configure red alarm threshold";
            leaf percentage {
              type uint32 {
                range "1..1000";
              }
            } //percentage

          } //container red-alarm-threshold

          container resv-cbs {
            description
                "Configure the reserved CBS for the port";
            leaf percent-or-default {
              type string;
              description
                  "[0..100|default]";
            } //percent-or-default

            leaf amber-alarm-action {
              type boolean;
            } //amber-alarm-action

            leaf step {
              type uint32 {
                range "1..100";
              }
            } //step

            leaf max {
              type uint32 {
                range "1..100";
              }
            } //max

          } //container resv-cbs

          container slope-policy {
            description
                "Configure the slope policy";
            leaf name {
              type string {
                length "1..32";
              }
              default "default";
            } //name

          } //container slope-policy

        } //list pool

      } //container egress

    } //container network

  } //grouping alu-conf-port-network-r13

} //module  alu-conf-port-network-r13
