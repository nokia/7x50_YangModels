module alu-conf-sfm-r13 {
  yang-version "1";

  namespace "urn:alcatel-lucent.com:sros:ns:yang:conf-sfm-r13";

  prefix "conf-sfm-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure switch fabric modules on SR OS 
       based routers. 
       
       Copyright 2014-2015 Alcatel-Lucent, 2016 Nokia. All rights reserved. 
       Reproduction of this document is authorized on the condition that the 
       foregoing copyright notice is included. 
       
       This alu-conf-sfm-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-sfm-r13 {
    list sfm {
      key "sfm-name";
      description
          "Configure switch fabric modules";
      leaf sfm-name {
        type string {
          length "1..32";
        }
        description
            "Attribute sfm-name for sfm";
      } //sfm-name

      container sfm-type {
        description
            "Provisions/de-provisions the SFM type";
        leaf sfm-type {
          type string {
            length "1..32";
          }
          description
              "Attribute sfm-type for sfm-type";
        } //sfm-type

      } //container sfm-type

      leaf shutdown {
        type boolean;
        description
            "Administratively shut down an SFM";
      }

    } //list sfm

  } //grouping alu-conf-sfm-r13

} //module  alu-conf-sfm-r13
