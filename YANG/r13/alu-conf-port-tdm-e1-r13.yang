module alu-conf-port-tdm-e1-r13 {
  yang-version "1";

  namespace "urn:alcatel-lucent.com:sros:ns:yang:conf-port-tdm-e1-r13";

  prefix "conf-port-tdm-e1-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure E1 channels on a physical port on 
       SR OS based routers. 
       
       Copyright 2014-2015 Alcatel-Lucent, 2016 Nokia. All rights reserved. 
       Reproduction of this document is authorized on the condition that the 
       foregoing copyright notice is included. 
       
       This alu-conf-port-tdm-e1-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-30";

  grouping alu-conf-port-tdm-e1-r13 {
    list e1 {
      key "e1-id";
      description
          "Configure E1 channels on a physical port";
      leaf e1-id {
        type string {
        }
        description
            "e1-number(1-21)|e1-sonet-sdh-index";
      } //e1-id

      container bert {
        description
            "Start/Stop a Bit Error Rate Test (BERT)";
        leaf t2e3-2e9-2e11-2e15-2e20-2e20q-2e23-ones-zeros-alternating {
          type enumeration {
            enum 2e3;
            enum 2e9;
            enum 2e11;
            enum 2e15;
            enum 2e20;
            enum 2e20q;
            enum 2e23;
            enum ones;
            enum zeros;
            enum alternating;
          }
          description
              "keywords";
        } //t2e3-2e9-2e11-2e15-2e20-2e20q-2e23-ones-zeros-alternating

        leaf duration {
          type string;
          description
              "sec|hh:mm[:sec] 24 hour max";
        } //duration

      } //container bert

      container bit-error-insertion {
        description
            "Configure the bit error insertion rate for the BERT test";
        leaf rate {
          type int32 {
            range "2..7";
          }
        } //rate

      } //container bit-error-insertion

      container clock-source {
        description
            "Configure the clock for transmitted data";
        leaf clock-source-id {
          type enumeration {
            enum loop-timed;
            enum node-timed;
            enum adaptive;
            enum differential;
          }
        } //clock-source-id

      } //container clock-source

      container framing {
        description
            "Configure the framing for the channel";
        leaf no-crc-g704-g704-e1-unframed {
          type enumeration {
            enum no-crc-g704;
            enum g704;
            enum e1-unframed;
          }
          description
              "keywords";
        } //no-crc-g704-g704-e1-unframed

      } //container framing

      container hold-time {
        description
            "Configure the line dampening timers";
        leaf up {
          type uint32 {
            range "0..100";
          }
          description
              "[0..100] in 100s of milliseconds";
        } //up

        leaf down {
          type uint32 {
            range "0..100";
          }
          description
              "[0..100] in 100s of milliseconds";
        } //down

      } //container hold-time

      leaf insert-single-bit-error {
        type boolean;
        description
            "Insert a single bit error for the BERT test";
      }

      leaf invert-data {
        type boolean;
        description
            "Enable/disable inverting of data bits";
      }

      container loopback {
        description
            "Activate a loopback on the channel";
        leaf line-internal {
          type enumeration {
            enum line;
            enum internal;
          }
          description
              "keywords";
        } //line-internal

      } //container loopback

      container national-bits {
        description
            "Configure the National Use Bits";
        leaf-list sa-bits {
          type int32 {
            range "0..1";
          }
          max-elements 5;
          description
              "[0|1] - Disable or enable sa-bit.";
        } //sa-bits

      } //container national-bits

      container report-alarm {
        description
            "Enable/disable logging of alarms";
        leaf ais {
          type boolean;
        } //ais

        leaf los {
          type boolean;
        } //los

        leaf oof {
          type boolean;
        } //oof

        leaf rai {
          type boolean;
        } //rai

        leaf looped {
          type boolean;
        } //looped

        leaf ber-sd {
          type boolean;
        } //ber-sd

        leaf ber-sf {
          type boolean;
        } //ber-sf

      } //container report-alarm

      leaf shutdown {
        type boolean;
        description
            "Administratively enable/disable the channel";
      }

      container signal-mode {
        description
            "Activate the signal-mode on the channel";
        leaf cas {
          type enumeration {
            enum cas;
          }
        } //cas

      } //container signal-mode

      list threshold {
        key "ber-sd-ber-sf";
        description
            "Configure BER signal degradation failure thresholds";
        leaf ber-sd-ber-sf {
          type enumeration {
            enum ber-sd;
            enum ber-sf;
          }
          description
              "keywords";
        } //ber-sd-ber-sf

        leaf rate {
          type enumeration {
            enum 1;
            enum 5;
            enum 10;
            enum 50;
            enum 100;
          }
          description
              "Number of errors in millions 
               - Default ber-sd: 5 
               ber-sf: 50";
        } //rate

      } //list threshold

      list channel-group {
        key "channel-group-id";
        description
            "Create/delete DS0 channel groups";
        leaf channel-group-id {
          type int32 {
            range "1..32";
          }
        } //channel-group-id

        container crc {
          description
              "Configure the precision of the cyclic redundancy check (CRC)";
          leaf t16-32 {
            type enumeration {
              enum 16;
              enum 32;
            }
            description
                "keywords";
          } //t16-32

        } //container crc

        container description {
          description
              "Add/remove a text description for the channel group";
          leaf long-description-string {
            type string {
              length "1..160";
            }
          } //long-description-string

        } //container description

        container egress-scheduler-policy {
          description
              "Configure an egress scheduler policy";
          leaf port-scheduler-policy-name {
            type string {
              length "1..32";
            }
          } //port-scheduler-policy-name

        } //container egress-scheduler-policy

        container encap-type {
          description
              "Configure an encap method";
          leaf atm-bcp-null-bcp-dot1q-ipcp-ppp-auto-frame-relay-wan-mirror-cisco-hdlc-cem {
            type enumeration {
              enum atm;
              enum bcp-null;
              enum bcp-dot1q;
              enum ipcp;
              enum ppp-auto;
              enum frame-relay;
              enum wan-mirror;
              enum cisco-hdlc;
              enum cem;
            }
          } //atm-bcp-null-bcp-dot1q-ipcp-ppp-auto-frame-relay-wan-mirror-cisco-hdlc-cem

        } //container encap-type

        container idle-cycle-flag {
          description
              "Configure the value that the channel group transmits during idle cycle";
          leaf flags-ones {
            type enumeration {
              enum flags;
              enum ones;
            }
            description
                "keywords";
          } //flags-ones

        } //container idle-cycle-flag

        container idle-payload-fill {
          description
              "Configure the payload the CEM channel transmits during underrun or missing 
               frames";
          leaf idle-payload-fill-id {
            type enumeration {
              enum all-ones;
            }
          } //idle-payload-fill-id

          leaf pattern {
            type string;
            description
                "[0..255] - accepted in decimal, hex or binary";
          } //pattern

        } //container idle-payload-fill

        container idle-signal-fill {
          description
              "Configure the signal the CAS CEM channel transmits during underrun or missing 
               frames";
          leaf idle-signal-fill-id {
            type enumeration {
              enum all-ones;
            }
          } //idle-signal-fill-id

          leaf pattern {
            type string;
            description
                "[0..15] - accepted in decimal, hex or binary";
          } //pattern

        } //container idle-signal-fill

        container load-balancing-algorithm {
          description
              "Configure Load Balancing Algorithm";
          leaf option {
            type enumeration {
              enum include-l4;
              enum exclude-l4;
            }
          } //option

        } //container load-balancing-algorithm

        container mac {
          description
              "Assign a MAC address to the channel group";
          leaf ieee-address {
            type alu:ieee-address;
            description
                "xx:xx:xx:xx:xx:xx or xx-xx-xx-xx-xx-xx";
          } //ieee-address

        } //container mac

        container mode {
          description
              "Configure a channel group for access or network mode";
          leaf access-network {
            type enumeration {
              enum access;
              enum network;
            }
            description
                "keywords";
          } //access-network

        } //container mode

        container mtu {
          description
              "Configure the maximum payload MTU size for the channel group";
          leaf mtu-bytes {
            type uint32 {
              range "512..9208";
            }
          } //mtu-bytes

        } //container mtu

        leaf scramble {
          type boolean;
          description
              "Configure ATM payload scrambling";
        }

        leaf shutdown {
          type boolean;
          description
              "Administratively enable/disable the channel group";
        }

        container speed {
          description
              "Configure the speed of the channels in this channel group";
          leaf t56-64 {
            type enumeration {
              enum 56;
              enum 64;
            }
            description
                "keywords";
          } //t56-64

        } //container speed

        container timeslots {
          description
              "Configure timeslots for this channel group";
          leaf timeslots {
            type string {
              length "1..64";
            }
            description
                "timeslot range [2..32] (e.g. 2-10,21,31)";
          } //timeslots

        } //container timeslots

        container atm {
          description
              "Configure ATM properties";
          container cell-format {
            description
                "Configure the ATM cell-format";
            leaf cell-format {
              type enumeration {
                enum uni;
                enum nni;
              }
              description
                  "keywords - uni|nni";
            } //cell-format

          } //container cell-format

          container min-vp-vpi {
            description
                "Configure the ATM minimum vpi";
            leaf value {
              type uint32 {
                range "0..4095";
              }
              description
                  "[0..4095] (NNI) 
                   [0..255] (UNI)";
            } //value

          } //container min-vp-vpi

        } //container atm

        container cisco-hdlc {
          description
              "Configure the Cisco-HDLC operational parameters";
          container down-count {
            description
                "Number of keep alive intervals that must pass without receiving a keep alive 
                 packet before the link is declared down";
            leaf down-count {
              type uint32 {
                range "3..16";
              }
            } //down-count

          } //container down-count

          container keepalive {
            description
                "Time interval at which keep-alive requests are issued";
            leaf time-interval {
              type uint32 {
                range "0..300";
              }
              description
                  "[0..300] seconds";
            } //time-interval

          } //container keepalive

          container up-count {
            description
                "Number of continual keepalive packets to be received to declare the link up";
            leaf up-count {
              type uint32 {
                range "1..3";
              }
            } //up-count

          } //container up-count

        } //container cisco-hdlc

        container egress-scheduler-override {
          description
              "Apply egress scheduler overrides";
          list level {
            key "priority-level";
            description
                "Configure priority level parameters";
            leaf priority-level {
              type uint32 {
                range "1..8";
              }
            } //priority-level

            leaf rate {
              type string;
              description
                  "[1..3200000000|max] Kbps";
            } //rate

            leaf percent-rate {
              type string;
              description
                  "[0.01..100.00]";
            } //percent-rate

            leaf cir {
              type string;
              description
                  "[0..3200000000|max] Kbps";
            } //cir

            leaf percent-cir {
              type string;
              description
                  "[0.00..100.00]";
            } //percent-cir

          } //list level

          container max-rate {
            description
                "Configure the maximum rate";
            leaf rate {
              type string;
              description
                  "[1..3200000000|max] Kbps";
            } //rate

            leaf percent {
              type string;
              description
                  "[0.01..100.00]";
            } //percent

          } //container max-rate

        } //container egress-scheduler-override

        container frame-relay {
          description
              "Configure the Frame Relay parameters";
          container identifier {
            description
                "Configure FRF.16 link identifier";
            leaf frf16-identifier {
              type string {
                length "1..49";
              }
            } //frf16-identifier

          } //container identifier

          container lmi-type {
            description
                "Configure the LMI type";
            leaf lmi-type-id {
              type enumeration {
                enum ansi;
                enum itu;
                enum none;
                enum rev1;
              }
            } //lmi-type-id

          } //container lmi-type

          container mode {
            description
                "Configure the DCE/DTE mode of the Frame Relay interface";
            leaf dce-dte-bidir {
              type enumeration {
                enum dce;
                enum dte;
                enum bidir;
              }
              description
                  "keywords";
            } //dce-dte-bidir

          } //container mode

          container n391dte {
            description
                "Configure the number of DTE full status polling intervals for the LMI";
            leaf intervals {
              type int32 {
                range "1..255";
              }
            } //intervals

          } //container n391dte

          container n392dce {
            description
                "Configure the DCE error threshold for the LMI";
            leaf threshold {
              type int32 {
                range "1..10";
              }
            } //threshold

          } //container n392dce

          container n392dte {
            description
                "Configure the DTE error threshold for the LMI";
            leaf threshold {
              type int32 {
                range "1..10";
              }
            } //threshold

          } //container n392dte

          container n393dce {
            description
                "Configure the DCE monitored event count for the LMI";
            leaf count {
              type int32 {
                range "1..10";
              }
            } //count

          } //container n393dce

          container n393dte {
            description
                "Configure the DTE monitored event count for the LMI";
            leaf count {
              type int32 {
                range "1..10";
              }
            } //count

          } //container n393dte

          container t391dte {
            description
                "Configure the DTE keepalive timer value for the LMI";
            leaf keepalive {
              type int32 {
                range "5..30";
              }
              description
                  "[5..30 seconds]";
            } //keepalive

          } //container t391dte

          container t392dce {
            description
                "Configure the DCE keepalive timer value for the LMI";
            leaf keepalive {
              type int32 {
                range "5..30";
              }
              description
                  "[5..30 seconds]";
            } //keepalive

          } //container t392dce

          container frf-12 {
            presence
                "Enable/Disable FRF.12 Headers";
            container fragment-threshold {
              description
                  "Configure FRF.12 fragmentation threshold";
              leaf threshold {
                type uint32 {
                  range "128..512";
                }
              } //threshold

            } //container fragment-threshold

            container egress {
              description
                  "Configure egress FRF.12 parameters";
              container qos-profile {
                description
                    "Configure egress FRF.12 qos-profile";
                leaf profile-id {
                  type int32;
                  description
                      "Attribute profile-id for qos-profile";
                } //profile-id

              } //container qos-profile

            } //container egress

          } //container frf-12

        } //container frame-relay

        container network {
          description
              "Configure network port parameters";
          container accounting-policy {
            description
                "Configure the accounting policy which applies to the network port";
            leaf policy-id {
              type uint32 {
                range "1..99";
              }
            } //policy-id

          } //container accounting-policy

          leaf collect-stats {
            type boolean;
            description
                "Enable/disable the collection of statistical data";
          }

          container queue-policy {
            description
                "Configure the network policy";
            leaf name {
              type string {
                length "1..32";
              }
              default "default";
            } //name

          } //container queue-policy

        } //container network

        container ppp {
          description
              "Configure the LCP operational parameters";
          leaf ber-sf-link-down {
            type boolean;
            description
                "Enable/Disable port down on BER-SF alarm";
          }

          container compress {
            description
                "Enable/Disable PPP field compression";
            leaf acfc {
              type boolean;
              description
                  "keyword - address and control field compression";
            } //acfc

            leaf pfc {
              type boolean;
              description
                  "keyword - protocol field compression";
            } //pfc

          } //container compress

          container keepalive {
            description
                "Configure the time interval at which keepalive requests are issued";
            leaf time-period {
              type int32 {
                range "1..60";
              }
            } //time-period

            leaf dropcount {
              type uint64 {
                range "1..255";
              }
            } //dropcount

          } //container keepalive

        } //container ppp

      } //list channel-group

    } //list e1

  } //grouping alu-conf-port-tdm-e1-r13

} //module  alu-conf-port-tdm-e1-r13
