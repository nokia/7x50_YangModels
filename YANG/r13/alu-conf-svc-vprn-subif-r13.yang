module alu-conf-svc-vprn-subif-r13 {
  yang-version "1";

  namespace "urn:alcatel-lucent.com:sros:ns:yang:conf-svc-vprn-subif-r13";

  prefix "conf-svc-vprn-subif-r13";

  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure subscriber interfaces for VPRN 
       services on SR OS based routers. 
       
       Copyright 2014-2015 Alcatel-Lucent, 2016 Nokia. All rights reserved. 
       Reproduction of this document is authorized on the condition that the 
       foregoing copyright notice is included. 
       
       This alu-conf-svc-vprn-subif-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-01-13";

  grouping alu-conf-svc-vprn-subif-r13 {
    list subscriber-interface {
      key "ip-int-name";
      description
          "Configure subscriber interfaces for VPRN services";
      leaf ip-int-name {
        type string {
          length "1..32";
        }
        description
            "[32 chars max] (must start with a letter)";
      } //ip-int-name

      leaf fwd-service {
        type string;
        description
            "Attribute service-id for subscriber-interface";
      } //fwd-service

      leaf fwd-subscriber-interface {
        type string {
          length "1..32";
        }
      } //fwd-subscriber-interface

      leaf wan-mode {
        type enumeration {
          enum mode64;
          enum mode128;
        }
      } //wan-mode

      list address {
        key "ip-address-mask netmask";
        description
            "Assigns an IP address/IP subnet to the interface";
        leaf ip-address-mask {
          type string;
          description
              "ip-address a.b.c.d (no multicast address) 
               mask [0..32]";
        } //ip-address-mask

        leaf netmask {
          type string;
          description
              "a.b.c.d (network bits all 1 and host bits all 0)";
        } //netmask

        leaf gw-ip-address {
          type inet:ip-address;
        } //gw-ip-address

        leaf populate-host-routes {
          type boolean;
        } //populate-host-routes

        leaf track-srrp {
          type uint32 {
            range "1..4294967295";
          }
        } //track-srrp

        leaf holdup-time {
          type uint32 {
            range "100..5000";
          }
        } //holdup-time

      } //list address

      leaf allow-unmatching-subnets {
        type boolean;
        description
            "Allow subscriber hosts without a matching subnet";
      }

      container default-dns {
        description
            "Configure the default DNS server address";
        leaf ip-address {
          type inet:ip-address;
          description
              "a.b.c.d";
        } //ip-address

        leaf secondary {
          type inet:ip-address;
          description
              "a.b.c.d";
        } //secondary

      } //container default-dns

      container delayed-enable {
        status "obsolete";
        description
            "Delays making interface operational by the specified number of seconds";
        leaf seconds {
          type uint32 {
            range "1..65535";
          }
        } //seconds

        leaf init-only {
          type boolean;
        } //init-only

      } //container delayed-enable

      list description {
        key "long-description-string";
        description
            "Description for Subscriber interface";
        leaf long-description-string {
          type string {
            length "1..255";
          }
        } //long-description-string

      } //list description

      leaf export-host-routes {
        type boolean;
        description
            "Allow export of IPv4 host routes";
      }

      leaf private-retail-subnets {
        type boolean;
        description
            "Controls the export of subnets to the forwarding service";
      }

      leaf shutdown {
        type boolean;
        description
            "Administratively enable/disable the interface";
      }

      container unnumbered {
        description
            "Configure the interface as an unnumbered interface";
        leaf ip-int-name-ip-address {
          type string;
          description
              "Attribute ip-int-name|ip-address for unnumbered";
        } //ip-int-name-ip-address

      } //container unnumbered

      container arp-host {
        description
            "Configure ARP host parameters";
        container host-limit {
          description
              "Configure the maximum number of ARP hosts";
          leaf max-num-hosts {
            type int32 {
              range "1..524287";
            }
            description
                "Attribute max-num-hosts for host-limit";
          } //max-num-hosts

        } //container host-limit

        leaf shutdown {
          type boolean;
          description
              "Enable/disable ARP hosts";
        }

      } //container arp-host

      container dhcp {
        description
            "Configure DHCP parameters";
        container client-applications {
          description
              "Configure the set of DHCP Relay client applications";
          leaf dhcp {
            type boolean;
          } //dhcp

          leaf ppp {
            type boolean;
          } //ppp

        } //container client-applications

        container description {
          description
              "Add/remove a text description for DHCP";
          leaf description-string {
            type string {
              length "1..80";
            }
          } //description-string

        } //container description

        container gi-address {
          description
              "Configure the gateway interface address for the DHCP relay";
          leaf ip-address {
            type inet:ip-address;
          } //ip-address

          leaf src-ip-addr {
            type boolean;
            description
                "keyword - use the gi-address as src-ip";
          } //src-ip-addr

        } //container gi-address

        container lease-populate {
          description
              "Configure the maximum number of DHCPv4 leases";
          leaf nbr-of-leases {
            type int32 {
              range "1..524287";
            }
            description
                "Attribute nbr-of-leases for lease-populate";
          } //nbr-of-leases

        } //container lease-populate

        container python-policy {
          description
              "Configure the Python policy";
          leaf name {
            type string {
              length "1..32";
            }
          } //name

        } //container python-policy

        container relay-proxy {
          description
              "Enable/disable relaying of unicast DHCP client messages and optional DHCP 
               server ip address hiding";
          leaf release-update-src-ip {
            type boolean;
          } //release-update-src-ip

          leaf siaddr-override {
            type inet:ip-address;
          } //siaddr-override

        } //container relay-proxy

        container server {
          description
              "Configure the DHCP server IP address";
          leaf-list server-ip-address {
            type inet:ip-address;
            max-elements 8;
            description
                "DHCP server IP address";
          } //server-ip-address

        } //container server

        leaf shutdown {
          type boolean;
          description
              "Administratively enable/disable DHCP on this interface";
        }

        leaf virtual-subnet {
          type boolean;
          description
              "Enable/disable virtual subnetting";
        }

        container offer-selection {
          description
              "Configure the DHCP offer selection attributes";
          container discover-delay {
            description
                "Configure the DHCP discovery delay";
            leaf deci-seconds {
              type uint32 {
                range "1..100";
              }
            } //deci-seconds

          } //container discover-delay

          container client-mac {
            description
                "Configure the DHCP client-mac";
            leaf client-mac-id {
              type enumeration {
                enum odd;
                enum even;
              }
            } //client-mac-id

            container discover-delay {
              description
                  "Configure the DHCP client-mac discovery delay";
              leaf deci-seconds {
                type uint32 {
                  range "1..100";
                }
              } //deci-seconds

            } //container discover-delay

          } //container client-mac

          list server {
            key "ip-address";
            description
                "Configure the DHCP server";
            leaf ip-address {
              type inet:ip-address;
            } //ip-address

            container discover-delay {
              description
                  "Configure the DHCP discovery delay";
              leaf deci-seconds {
                type uint32 {
                  range "1..100";
                }
              } //deci-seconds

            } //container discover-delay

          } //list server

        } //container offer-selection

        container option {
          presence
              "Configure the DHCP Relay information options";
          container vendor-specific-option {
            presence
                "Configure the Nokia vendor specific suboption of the DHCP Relay packet";
            leaf client-mac-address {
              type boolean;
              description
                  "Enable/disable sending of the MAC address in the Nokia vendor specific 
                   suboption of the DHCP Relay packet";
            }

            leaf sap-id {
              type boolean;
              description
                  "Enable/disable sending of the SAP-id in the Nokia vendor specific suboption of 
                   the DHCP Relay packet";
            }

            leaf service-id {
              type boolean;
              description
                  "Enable/disable sending of the service-id in the Nokia vendor specific 
                   suboption of the DHCP Relay packet";
            }

            container string {
              description
                  "Specifies the string in the Nokia vendor specific suboption of the DHCP Relay 
                   packet";
              leaf text {
                type string {
                  length "1..32";
                }
              } //text

            } //container string

            leaf system-id {
              type boolean;
              description
                  "Enable/disable sending of the system-id in the Nokia vendor specific suboption 
                   of the DHCP Relay packet";
            }

          } //container vendor-specific-option

        } //container option

        container proxy-server {
          description
              "Configure the DHCP proxy server";
          container emulated-server {
            description
                "Specify the emulated server address";
            leaf ip-address {
              type inet:ip-address;
            } //ip-address

          } //container emulated-server

          container lease-time {
            description
                "Configure the DHCP lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

            leaf override {
              type boolean;
            } //override

          } //container lease-time

          leaf shutdown {
            type boolean;
            description
                "Administratively enable/disable DHCP proxy on this interface";
          }

        } //container proxy-server

      } //container dhcp

      list group-interface {
        key "ip-int-name";
        description
            "Create/delete or configure a group interface";
        leaf ip-int-name {
          type string {
            length "1..32";
          }
          description
              "[32 chars max] (must start with a letter)";
        } //ip-int-name

        leaf type {
          type enumeration {
            enum lns;
            enum wlangw;
            enum gtp;
            enum bonding;
          }
        } //type

        leaf do-not-delete {
          type boolean;
        } //do-not-delete

        leaf arp-populate {
          type boolean;
          description
              "Configures the ARP populate option";
        }

        list arp-timeout {
          key "seconds";
          description
              "Configures timeout for an ARP entry learned on the interface";
          leaf seconds {
            type uint32 {
              range "0..65535";
            }
          } //seconds

        } //list arp-timeout

        container authentication-policy {
          description
              "Configures the authentication policy for this interface";
          leaf-list name {
            type string {
              length "1..32";
            }
            max-elements 1;
            description
                "[32 chars max]";
          } //name

        } //container authentication-policy

        list description {
          key "long-description-string";
          description
              "Description for Group interface";
          leaf long-description-string {
            type string {
              length "1..255";
            }
          } //long-description-string

        } //list description

        container diameter-application-policy {
          description
              "Configure the Diameter application policy";
          leaf policy-name {
            type string;
          } //policy-name

        } //container diameter-application-policy

        container diameter-auth-policy {
          description
              "Configure the Diameter NASREQ application policy to use for authentication";
          leaf name {
            type string;
          } //name

        } //container diameter-auth-policy

        leaf enable-ingress-stats {
          type boolean;
          description
              "Enable/disable the gathering of ingress interface statistics";
        }

        container host-connectivity-verify {
          description
              "Enable/disable host connectivity verification for all hosts on this interface";
          leaf interval {
            type uint64 {
              range "1..6000";
            }
            description
                "[1..6000] minutes";
          } //interval

          leaf action {
            type enumeration {
              enum remove;
              enum alarm;
            }
            description
                "keywords";
          } //action

          leaf timeout {
            type uint8 {
              range "10..60";
            }
            description
                "[10..60] seconds";
          } //timeout

          leaf retry-count {
            type uint8 {
              range "2..29";
            }
            description
                "[2..29]";
          } //retry-count

          leaf family {
            type enumeration {
              enum ipv4;
              enum ipv6;
              enum both;
            }
          } //family

        } //container host-connectivity-verify

        leaf ignore-df-bit {
          type boolean;
          description
              "Configure ignore-df-bit";
        }

        container ip-mtu {
          description
              "Configure the interface IP MTU";
          leaf octets {
            type string;
            description
                "Attribute octets for ip-mtu";
          } //octets

        } //container ip-mtu

        leaf local-proxy-arp {
          type boolean;
          description
              "Enable/disable local proxy ARP on the interface";
        }

        list mac {
          key "ieee-address";
          description
              "Assign a MAC address to the interface";
          leaf ieee-address {
            type string;
            description
                "xx:xx:xx:xx:xx:xx or xx-xx-xx-xx-xx-xx (cannot be all zeros)";
          } //ieee-address

        } //list mac

        leaf oper-up-while-empty {
          type boolean;
          description
              "Allow the subscriber interface to treat this group interface to be 
               operationally enabled without any active SAPs";
        }

        container policy-control {
          status "obsolete";
          description
              "Configure a policy-control policy for the interface";
          leaf diameter-policy-name {
            type string {
              length "1..32";
            }
          } //diameter-policy-name

        } //container policy-control

        container proxy-arp-policy {
          description
              "Configure a proxy ARP policy for the interface";
          leaf-list policy-name {
            type string {
              length "1..32";
            }
            max-elements 5;
            description
                "[32 chars max]";
          } //policy-name

        } //container proxy-arp-policy

        leaf qos-route-lookup {
          type boolean;
          description
              "Configure Qos route lookup for the interface";
        }

        container redundant-interface {
          description
              "Configure the redundant interface";
          leaf red-ip-int-name {
            type string {
              length "1..32";
            }
          } //red-ip-int-name

        } //container redundant-interface

        leaf remote-proxy-arp {
          type boolean;
          description
              "Enable/disable remote proxy ARP on the interface";
        }

        container shcv-policy {
          description
              "Configure the Subscriber Host Connectivity Verification policy for IPv4 and 
               IPv6";
          leaf policy-name {
            type string;
          } //policy-name

        } //container shcv-policy

        container shcv-policy-ipv4 {
          description
              "Configure the Subscriber Host Connectivity Verification policy for IPv4";
          leaf policy-name {
            type string;
          } //policy-name

        } //container shcv-policy-ipv4

        container shcv-policy-ipv6 {
          description
              "Configure the Subscriber Host Connectivity Verification policy for IPv6";
          leaf policy-name {
            type string;
          } //policy-name

        } //container shcv-policy-ipv6

        leaf shutdown {
          type boolean;
          description
              "Administratively enable/disable the interface";
        }

        container srrp-enabled-routing {
          description
              "Configure SRRP enabled routing";
          leaf hold-time {
            type uint32 {
              range "1..50";
            }
            description
                "[1..50] deci-seconds";
          } //hold-time

        } //container srrp-enabled-routing

        leaf suppress-aa-sub {
          type boolean;
          description
              "Enable/Disable Application Assurance suppression for ESM subscribers for this 
               interface";
        }

        container tos-marking-state {
          description
              "Specify TOS marking state";
          leaf trusted-untrusted {
            type enumeration {
              enum trusted;
              enum untrusted;
            }
            description
                "keywords";
          } //trusted-untrusted

        } //container tos-marking-state

        container arp-host {
          description
              "Configure ARP host parameters";
          container host-limit {
            description
                "Configure the maximum number of ARP hosts";
            leaf max-num-hosts {
              type int32 {
                range "1..131071";
              }
              description
                  "Attribute max-num-hosts for host-limit";
            } //max-num-hosts

          } //container host-limit

          container min-auth-interval {
            description
                "Configure the minimum authentication interval";
            leaf min-auth-interval {
              type uint32 {
                range "1..6000";
              }
              description
                  "[1..6000] minutes";
            } //min-auth-interval

          } //container min-auth-interval

          container sap-host-limit {
            description
                "Configure the maximum number of ARP hosts per SAP";
            leaf max-num-hosts-sap {
              type int32 {
                range "1..131071";
              }
              description
                  "Attribute max-num-hosts-sap for sap-host-limit";
            } //max-num-hosts-sap

          } //container sap-host-limit

          leaf shutdown {
            type boolean;
            description
                "Enable/disable ARP hosts";
          }

        } //container arp-host

        container bonding-parameters {
          description
              "Configure the ESM connection bonding";
          container fpe {
            description
                "Configure the FPE to be used to provision bonding functionality";
            leaf fpe-id {
              type uint32 {
                range "1..64";
              }
              description
                  "[1..64]";
            } //fpe-id

          } //container fpe

          leaf shutdown {
            type boolean;
            description
                "Enable/disable ESM bonding";
          }

          list connection {
            key "connection-id";
            description
                "Configure an ESM bonding connection";
            leaf connection-id {
              type uint32 {
                range "1..2";
              }
              description
                  "[1,2]";
            } //connection-id

            container service {
              description
                  "Configure the service for the connection";
              leaf service-id {
                type string;
                description
                    "Attribute service-id for service";
              } //service-id

            } //container service

          } //list connection

          container multicast {
            description
                "Configure the bonding parameters for multicast";
            container connection {
              description
                  "Configure the multicast connection";
              leaf connection-id {
                type uint32 {
                  range "1..2";
                }
                description
                    "[1,2]";
              } //connection-id

              leaf use-incoming {
                type boolean;
                description
                    "keyword";
              } //use-incoming

            } //container connection

          } //container multicast

        } //container bonding-parameters

        container brg {
          description
              "Configure for Bridged Residential Gateways";
          leaf authenticated-brg-only {
            type boolean;
            description
                "Configure if this system allows only hosts from authenticated Bridged 
                 Residential Gateways";
          }

          container default-brg-profile {
            description
                "Configure the BRG profile in case the AAA server does not specify it";
            leaf profile-name {
              type string;
            } //profile-name

          } //container default-brg-profile

          leaf shutdown {
            type boolean;
            description
                "Administratively disable or enable BRG";
          }

        } //container brg

        container cflowd-parameters {
          description
              "Configure Cflowd parameters on the interface";
          list sampling {
            key "sampling-id";
            description
                "Configure the Cflowd sampling parameters";
            leaf sampling-id {
              type enumeration {
                enum unicast;
                enum multicast;
                enum both;
              }
            } //sampling-id

            leaf type {
              type enumeration {
                enum acl;
                enum interface;
              }
            } //type

            leaf direction {
              type enumeration {
                enum ingress-only;
                enum egress-only;
                enum both;
              }
              default "ingress-only";
              description
                  "keywords - Default: ingress-only";
            } //direction

            leaf sample-profile {
              type uint32 {
                range "1..5";
              }
              default 1;
            } //sample-profile

          } //list sampling

        } //container cflowd-parameters

        container data-trigger {
          description
              "Configure data triggered subscriber host creation";
          leaf shutdown {
            type boolean;
            description
                "Disable data triggered subscriber host creation";
          }

        } //container data-trigger

        container dhcp {
          description
              "Configure DHCP parameters";
          container client-applications {
            description
                "Configure the set of DHCP Relay client applications";
            leaf dhcp {
              type boolean;
            } //dhcp

            leaf ppp {
              type boolean;
            } //ppp

          } //container client-applications

          container description {
            description
                "Add/remove a text description for DHCP";
            leaf description-string {
              type string {
                length "1..80";
              }
            } //description-string

          } //container description

          container filter {
            description
                "Configure the DHCP filter for this interface";
            leaf filter-id {
              type uint32 {
                range "1..65535";
              }
            } //filter-id

          } //container filter

          container gi-address {
            description
                "Configure the gateway interface address for the DHCP relay";
            leaf ip-address {
              type inet:ip-address;
            } //ip-address

            leaf src-ip-addr {
              type boolean;
              description
                  "keyword - use the gi-address as src-ip";
            } //src-ip-addr

          } //container gi-address

          container lease-populate {
            description
                "Configure the maximum number of DHCPv4 leases per SAP";
            leaf nbr-of-leases {
              type int32 {
                range "1..131071";
              }
              description
                  "Attribute nbr-of-leases for lease-populate";
            } //nbr-of-leases

            leaf l2-header {
              type boolean;
            } //l2-header

            leaf mac {
              type string;
              description
                  "xx:xx:xx:xx:xx:xx or xx-xx-xx-xx-xx-xx (cannot be all zeros)";
            } //mac

          } //container lease-populate

          leaf match-circuit-id {
            type boolean;
            description
                "Match Opt82 circuit ID on relayed DHCP packets";
          }

          container python-policy {
            description
                "Configure the Python policy";
            leaf name {
              type string {
                length "1..32";
              }
            } //name

          } //container python-policy

          container relay-proxy {
            description
                "Enable/disable relaying of unicast DHCP client messages and optional DHCP 
                 server ip address hiding";
            leaf release-update-src-ip {
              type boolean;
            } //release-update-src-ip

            leaf siaddr-override {
              type inet:ip-address;
            } //siaddr-override

          } //container relay-proxy

          container server {
            description
                "Configure the DHCP server IP address";
            leaf-list server-ip-address {
              type inet:ip-address;
              max-elements 8;
              description
                  "DHCP server IP address";
            } //server-ip-address

          } //container server

          leaf shutdown {
            type boolean;
            description
                "Administratively enable/disable DHCP on this interface";
          }

          leaf trusted {
            type boolean;
            description
                "Enable/disable relaying of untrusted packets";
          }

          container user-db {
            description
                "Configure the local user database to use for authentication";
            leaf local-user-db-name {
              type string {
                length "1..32";
              }
            } //local-user-db-name

          } //container user-db

          container offer-selection {
            description
                "Configure the DHCP offer selection attributes";
            container discover-delay {
              description
                  "Configure the DHCP discovery delay";
              leaf deci-seconds {
                type uint32 {
                  range "1..100";
                }
              } //deci-seconds

            } //container discover-delay

            container client-mac {
              description
                  "Configure the DHCP client-mac";
              leaf client-mac-id {
                type enumeration {
                  enum odd;
                  enum even;
                }
              } //client-mac-id

              container discover-delay {
                description
                    "Configure the DHCP client-mac discovery delay";
                leaf deci-seconds {
                  type uint32 {
                    range "1..100";
                  }
                } //deci-seconds

              } //container discover-delay

            } //container client-mac

            list server {
              key "ip-address";
              description
                  "Configure the DHCP server";
              leaf ip-address {
                type inet:ip-address;
              } //ip-address

              container discover-delay {
                description
                    "Configure the DHCP discovery delay";
                leaf deci-seconds {
                  type uint32 {
                    range "1..100";
                  }
                } //deci-seconds

              } //container discover-delay

            } //list server

          } //container offer-selection

          container option {
            presence
                "Configure the DHCP Relay information options";
            container action {
              description
                  "Configure the DHCP Relay reforwarding policy action";
              leaf replace-drop-keep {
                type enumeration {
                  enum replace;
                  enum drop;
                  enum keep;
                }
                description
                    "keywords";
              } //replace-drop-keep

            } //container action

            container circuit-id {
              description
                  "Configure the circuit-id suboption of the DHCP Relay packet";
              leaf ifindex {
                type boolean;
              } //ifindex

              leaf ascii-tuple {
                type boolean;
              } //ascii-tuple

              leaf sap-id {
                type boolean;
              } //sap-id

              leaf vlan-ascii-tuple {
                type boolean;
              } //vlan-ascii-tuple

            } //container circuit-id

            container remote-id {
              description
                  "Configure the remote-id suboption of the DHCP Relay packet";
              leaf mac {
                type boolean;
              } //mac

              leaf string {
                type string {
                  length "1..32";
                }
                description
                    "Max 32 chars";
              } //string

            } //container remote-id

            container vendor-specific-option {
              presence
                  "Configure the Nokia vendor specific suboption of the DHCP Relay packet";
              leaf client-mac-address {
                type boolean;
                description
                    "Enable/disable sending of the MAC address in the Nokia vendor specific 
                     suboption of the DHCP Relay packet";
              }

              leaf pool-name {
                type boolean;
                description
                    "Enable/disable sending of the pool name in the Nokia vendor specific suboption 
                     of the DHCP Relay packet";
              }

              leaf sap-id {
                type boolean;
                description
                    "Enable/disable sending of the SAP-id in the Nokia vendor specific suboption of 
                     the DHCP Relay packet";
              }

              leaf service-id {
                type boolean;
                description
                    "Enable/disable sending of the service-id in the Nokia vendor specific 
                     suboption of the DHCP Relay packet";
              }

              container string {
                description
                    "Specifies the string in the Nokia vendor specific suboption of the DHCP Relay 
                     packet";
                leaf text {
                  type string {
                    length "1..32";
                  }
                } //text

              } //container string

              leaf system-id {
                type boolean;
                description
                    "Enable/disable sending of the system-id in the Nokia vendor specific suboption 
                     of the DHCP Relay packet";
              }

            } //container vendor-specific-option

          } //container option

          container proxy-server {
            description
                "Configure the DHCP proxy server";
            container emulated-server {
              description
                  "Specify the emulated server address";
              leaf ip-address {
                type inet:ip-address;
              } //ip-address

            } //container emulated-server

            container lease-time {
              description
                  "Configure the DHCP lease time";
              leaf days {
                type int32 {
                  range "0..3650";
                }
              } //days

              leaf hrs {
                type int32 {
                  range "0..23";
                }
              } //hrs

              leaf min {
                type int32 {
                  range "0..59";
                }
              } //min

              leaf sec {
                type int32 {
                  range "0..59";
                }
              } //sec

              leaf override {
                type boolean;
              } //override

            } //container lease-time

            leaf shutdown {
              type boolean;
              description
                  "Administratively enable/disable DHCP proxy on this interface";
            }

          } //container proxy-server

        } //container dhcp

        container gtp-parameters {
          description
              "Configure the GTP user interface";
          container fpe {
            description
                "Configure the FPE to be used to provision the GTP user interface";
            leaf fpe-id {
              type uint32 {
                range "1..64";
              }
              description
                  "[1..64]";
            } //fpe-id

          } //container fpe

          leaf shutdown {
            type boolean;
            description
                "Enable/disable GTP Access";
          }

        } //container gtp-parameters

        container icmp {
          description
              "Configure ICMP parameters for the interface";
          leaf mask-reply {
            type boolean;
            description
                "Enable/disable responses to ICMP mask requests";
          }

          container param-problem {
            description
                "Configures rate for ICMP param-problem messages";
            leaf-list number-seconds {
              type uint16 {
                range "1..1000";
              }
              max-elements 2;
              description
                  "number [10..1000] 
                   seconds [1..60]";
            } //number-seconds

          } //container param-problem

          container redirects {
            description
                "Configures rate for ICMP redirect messages";
            leaf-list number-seconds {
              type uint16 {
                range "1..1000";
              }
              max-elements 2;
              description
                  "number [10..1000] 
                   seconds [1..60]";
            } //number-seconds

          } //container redirects

          container ttl-expired {
            description
                "Configures rate for ICMP TTL expired messages";
            leaf-list number-seconds {
              type uint16 {
                range "1..2000";
              }
              max-elements 2;
              description
                  "number [10..2000] 
                   seconds [1..60]";
            } //number-seconds

          } //container ttl-expired

          container unreachables {
            description
                "Configures rate for ICMP unreachable messages";
            leaf-list number-seconds {
              type uint16 {
                range "1..2000";
              }
              max-elements 2;
              description
                  "number [10..2000] 
                   seconds [1..60]";
            } //number-seconds

          } //container unreachables

        } //container icmp

        container ingress {
          description
              "Configure ingress network filter policies for the interface.";
          container policy-accounting {
            description
                "Enable/Disable policy accounting template";
            leaf template-name {
              type string {
                length "1..32";
              }
            } //template-name

          } //container policy-accounting

        } //container ingress

        container ipoe-linking {
          description
              "Configures IPoE host linking";
          leaf gratuitous-rtr-adv {
            type boolean;
            description
                "Enable/disable unsolicited router advertisements";
          }

          leaf shared-circuit-id {
            type boolean;
            description
                "Enable/disable sharing of circuit-id";
          }

          leaf shutdown {
            type boolean;
            description
                "Administratively enable/disable IPoE host linking";
          }

        } //container ipoe-linking

        container ipoe-session {
          presence
              "Configure IPoE session parameters";
          container description {
            description
                "Description for the IPoE session";
            leaf description-string {
              type string {
                length "1..80";
              }
            } //description-string

          } //container description

          container force-auth {
            description
                "Configure when authentication must be forced";
            leaf cid-change {
              type boolean;
              description
                  "keyword - ignore min-auth-interval when cid changed";
            } //cid-change

            leaf rid-change {
              type boolean;
              description
                  "keyword - ignore min-auth-interval when rid changed";
            } //rid-change

            leaf disabled {
              type boolean;
              description
                  "keyword - never ignore min-auth-interval";
            } //disabled

          } //container force-auth

          container ipoe-session-policy {
            description
                "Assign an IPoE session policy";
            leaf policy-name {
              type string {
                length "1..32";
              }
            } //policy-name

          } //container ipoe-session-policy

          container min-auth-interval {
            description
                "Configure the minimum interval between two authentication attempts";
            leaf days {
              type uint32 {
                range "0..365";
              }
            } //days

            leaf hrs {
              type uint32 {
                range "0..23";
              }
            } //hrs

            leaf min {
              type uint32 {
                range "0..59";
              }
            } //min

            leaf sec {
              type uint32 {
                range "0..59";
              }
            } //sec

            leaf infinite {
              type boolean;
              description
                  "keyword";
            } //infinite

          } //container min-auth-interval

          container radius-session-timeout {
            description
                "Configure how to interpret the session timeout VSA from RADIUS";
            leaf backwards-compatible-ignore-absolute {
              type enumeration {
                enum backwards-compatible;
                enum ignore;
                enum absolute;
              }
              description
                  "keywords";
            } //backwards-compatible-ignore-absolute

          } //container radius-session-timeout

          container sap-session-limit {
            description
                "Configure the session limit per SAP";
            leaf sap-session-limit {
              type uint32 {
                range "1..131071";
              }
              description
                  "Attribute sap-session-limit for sap-session-limit";
            } //sap-session-limit

          } //container sap-session-limit

          container session-limit {
            description
                "Configure the session limit per group interface";
            leaf session-limit {
              type uint32 {
                range "1..131071";
              }
              description
                  "Attribute session-limit for session-limit";
            } //session-limit

          } //container session-limit

          leaf shutdown {
            type boolean;
            description
                "Administratively enable/disable IPoE Session";
          }

          leaf stateless-redundancy {
            type boolean;
            description
                "Enable or disable stateless multi-chassis redundancy (remove IPoE sessions 
                 when the system becomes stand-by)";
          }

          container user-db {
            description
                "Assign a local user database";
            leaf local-user-db-name {
              type string {
                length "1..32";
              }
            } //local-user-db-name

          } //container user-db

        } //container ipoe-session

        container ipv6 {
          presence
              "Configure IPv6 for a group interface";
          leaf allow-multiple-wan-addresses {
            type boolean;
            description
                "Configure if the group interface will accept multiple WAN addresses";
          }

          leaf ipoe-bridged-mode {
            type boolean;
            description
                "Enable/Disable IPv6 IPoE Bridged Mode";
          }

          leaf qos-route-lookup {
            type boolean;
            description
                "Enable/Disable Qos route lookup for the interface";
          }

          container auto-reply {
            presence
                "Configure static IPv6 hosts auto-reply for RS/NS";
            leaf neighbor-solicitation {
              type boolean;
              description
                  "Configure auto-reply for NS";
            }

            leaf router-solicitation {
              type boolean;
              description
                  "Configure auto-reply for RS";
            }

          } //container auto-reply

          container dhcp6 {
            presence
                "Configure DHCPv6 parameters";
            container filter {
              description
                  "Configure the DHCP6 filter for this interface";
              leaf filter-id {
                type uint32 {
                  range "1..65535";
                }
              } //filter-id

            } //container filter

            leaf override-slaac {
              type boolean;
              description
                  "Configure if the WAN address offered by dhcp should overwrite the WAN address 
                   acquired from SLAAC";
            }

            container pd-managed-route {
              description
                  "Enable installation of dhcp6 delegated prefixes as managed routes";
              leaf next-hop {
                type enumeration {
                  enum ipv4;
                  enum ipv6;
                }
              } //next-hop

            } //container pd-managed-route

            container python-policy {
              description
                  "Configure the Python policy";
              leaf name {
                type string {
                  length "1..32";
                }
              } //name

            } //container python-policy

            container user-db {
              description
                  "Configure the local user database to use for authentication";
              leaf local-user-db-name {
                type string {
                  length "1..32";
                }
              } //local-user-db-name

            } //container user-db

            container user-ident {
              description
                  "Configure the DHCP6 user-identification for this interface";
              leaf user-ident {
                type enumeration {
                  enum mac;
                  enum mac-interface-id;
                }
              } //user-ident

            } //container user-ident

            container option {
              presence
                  "Configure the DHCPv6 Relay information options";
              container interface-id {
                description
                    "Enable/disable sending of interface-id option in the DHCPv6 Relay packet";
                leaf ifindex {
                  type boolean;
                } //ifindex

                leaf ascii-tuple {
                  type boolean;
                } //ascii-tuple

                leaf sap-id {
                  type boolean;
                } //sap-id

                leaf string {
                  type string {
                    length "1..80";
                  }
                } //string

              } //container interface-id

              leaf remote-id {
                type boolean;
                description
                    "Enable/disable sending of remote-id option in the DHCPv6 Relay packet";
              }

            } //container option

            container proxy-server {
              presence
                  "Configure IPv6 DHCP proxy server for this group-interface";
              container client-applications {
                description
                    "Configure the set of DHCP6 proxy server client application on this 
                     group-interface";
                leaf dhcp {
                  type boolean;
                } //dhcp

                leaf ppp {
                  type boolean;
                } //ppp

              } //container client-applications

              container preferred-lifetime {
                description
                    "Time for prefix to remain preferred on this group-interface";
                leaf days {
                  type uint32 {
                    range "0..49710";
                  }
                } //days

                leaf hrs {
                  type uint32 {
                    range "0..23";
                  }
                } //hrs

                leaf min {
                  type uint32 {
                    range "0..59";
                  }
                } //min

                leaf sec {
                  type uint32 {
                    range "0..59";
                  }
                } //sec

                leaf infinite {
                  type boolean;
                  description
                      "keyword";
                } //infinite

              } //container preferred-lifetime

              container rebind-timer {
                description
                    "Set the rebind timer (T2) for this group-interface";
                leaf days {
                  type uint32 {
                    range "0..14";
                  }
                } //days

                leaf hrs {
                  type uint32 {
                    range "0..23";
                  }
                } //hrs

                leaf min {
                  type uint32 {
                    range "0..59";
                  }
                } //min

                leaf sec {
                  type uint32 {
                    range "0..59";
                  }
                } //sec

              } //container rebind-timer

              container renew-timer {
                description
                    "Set the renew timer (T1) for this group-interface";
                leaf days {
                  type uint32 {
                    range "0..7";
                  }
                } //days

                leaf hrs {
                  type uint32 {
                    range "0..23";
                  }
                } //hrs

                leaf min {
                  type uint32 {
                    range "0..59";
                  }
                } //min

                leaf sec {
                  type uint32 {
                    range "0..59";
                  }
                } //sec

              } //container renew-timer

              container server-id {
                description
                    "Configure the DUID";
                leaf duid-ll {
                  type boolean;
                  description
                      "keyword";
                } //duid-ll

                leaf duid-en {
                  type boolean;
                  description
                      "keyword";
                } //duid-en

                leaf string {
                  type string {
                    length "1..58";
                  }
                } //string

                leaf hex {
                  type string {
                    length "1..118";
                  }
                  description
                      "[0x0..0xFFFFFFFF...(max 116 hex nibbles)]";
                } //hex

              } //container server-id

              leaf shutdown {
                type boolean;
                description
                    "Administratively enable/disable DHCPv6 Proxy Server on this group-interface";
              }

              container valid-lifetime {
                description
                    "Time for prefix to remain valid on this group-interface";
                leaf days {
                  type uint32 {
                    range "0..49710";
                  }
                } //days

                leaf hrs {
                  type uint32 {
                    range "0..23";
                  }
                } //hrs

                leaf min {
                  type uint32 {
                    range "0..59";
                  }
                } //min

                leaf sec {
                  type uint32 {
                    range "0..59";
                  }
                } //sec

                leaf infinite {
                  type boolean;
                  description
                      "keyword";
                } //infinite

              } //container valid-lifetime

            } //container proxy-server

            container relay {
              presence
                  "Configure DHCPv6 relay parameters for this interface";
              container client-applications {
                description
                    "Configure the set of DHCP6 relay server client application on this 
                     group-interface";
                leaf dhcp {
                  type boolean;
                } //dhcp

                leaf ppp {
                  type boolean;
                } //ppp

              } //container client-applications

              container description {
                description
                    "Description for DHCPv6 relay";
                leaf description-string {
                  type string {
                    length "1..80";
                  }
                } //description-string

              } //container description

              container link-address {
                description
                    "Configure the link address of the DHCPv6 relay messages";
                leaf ipv6-address {
                  type inet:ipv6-address;
                  description
                      "ipv6-address x:x:x:x:x:x:x:x (eight 16-bit pieces) 
                       x:x:x:x:x:x:d.d.d.d 
                       x [0..FFFF]H 
                       d [0..255]D";
                } //ipv6-address

              } //container link-address

              container server {
                description
                    "Configure the DHCPv6 server IPv6 address";
                leaf-list ipv6-address {
                  type string;
                  max-elements 8;
                  description
                      "Attribute ipv6-address for server";
                } //ipv6-address

              } //container server

              leaf shutdown {
                type boolean;
                description
                    "Administratively enable/disable DHCPv6 relay on this interface";
              }

              container source-address {
                description
                    "Configure the source IPv6 address of the DHCPv6 relay messages";
                leaf ipv6-address {
                  type inet:ipv6-address;
                  description
                      "ipv6-address x:x:x:x:x:x:x:x (eight 16-bit pieces) 
                       x:x:x:x:x:x:d.d.d.d 
                       x [0..FFFF]H 
                       d [0..255]D";
                } //ipv6-address

              } //container source-address

              container advertise-selection {
                description
                    "Configure the DHCP6 advertise selection attributes";
                container solicit-delay {
                  description
                      "Configure the DHCP6 solicit delay";
                  leaf deci-seconds {
                    type uint32 {
                      range "1..100";
                    }
                  } //deci-seconds

                } //container solicit-delay

                container client-mac {
                  description
                      "Configure the DHCP6 client-mac";
                  leaf client-mac-id {
                    type enumeration {
                      enum even;
                      enum odd;
                    }
                  } //client-mac-id

                  container solicit-delay {
                    description
                        "Configure the DHCP6 client-mac solicit delay";
                    leaf deci-seconds {
                      type uint32 {
                        range "1..100";
                      }
                    } //deci-seconds

                  } //container solicit-delay

                  container preference-option {
                    presence
                        "Configure the DHCP6 client-mac preference option";
                    container value {
                      description
                          "Configure the DHCP6 client-mac preference option";
                      leaf value-id {
                        type uint32 {
                          range "0..255";
                        }
                      } //value-id

                    } //container value

                  } //container preference-option

                } //container client-mac

                container preference-option {
                  presence
                      "Configure the DHCP6 preference option";
                  container value {
                    description
                        "Configure the DHCP6 preference option";
                    leaf value-id {
                      type uint32 {
                        range "0..255";
                      }
                    } //value-id

                  } //container value

                } //container preference-option

                list server {
                  key "ipv6-address";
                  description
                      "Configure the DHCP6 server";
                  leaf ipv6-address {
                    type inet:ipv6-address;
                  } //ipv6-address

                  container solicit-delay {
                    description
                        "Configure the DHCP6 server solicit delay";
                    leaf deci-seconds {
                      type uint32 {
                        range "1..100";
                      }
                    } //deci-seconds

                  } //container solicit-delay

                  container preference-option {
                    presence
                        "Configure the DHCP6 server preference option";
                    container value {
                      description
                          "Configure the DHCP6 server preference option";
                      leaf value-id {
                        type uint32 {
                          range "0..255";
                        }
                      } //value-id

                    } //container value

                  } //container preference-option

                } //list server

              } //container advertise-selection

            } //container relay

            container snooping {
              presence
                  "Configure DHCPv6 Snooping options";
              leaf shutdown {
                type boolean;
              }

            } //container snooping

          } //container dhcp6

          container nd {
            description
                "Configure neighbor discovery parameters";
            leaf dad-snooping {
              type boolean;
              description
                  "Enable/Disable snooping of duplicate address packets to populate new 
                   neighbors.";
            }

            container neighbor-limit {
              description
                  "Configure the maximum number of neighbors learned";
              leaf neighbor-limit-id {
                type uint32 {
                  range "1..8";
                }
              } //neighbor-limit-id

            } //container neighbor-limit

          } //container nd

          container router-advertisements {
            presence
                "Configure IPv6 router advertisements for this group-interface";
            container current-hop-limit {
              description
                  "Set the hop-limit advertised for this group-interface";
              leaf limit {
                type uint16 {
                  range "0..255";
                }
                default 64;
              } //limit

            } //container current-hop-limit

            container force-mcast {
              description
                  "Configure multicast router advertisements on this interface";
              leaf ip {
                type boolean;
              } //ip

              leaf mac {
                type boolean;
              } //mac

            } //container force-mcast

            leaf managed-configuration {
              type boolean;
              description
                  "Set/reset managed address configuration flag for this group-interface";
            }

            container max-advertisement {
              description
                  "Set the maximum advertisement interval for this group-interface";
              leaf seconds {
                type uint32 {
                  range "900..1800";
                }
                default 1800;
              } //seconds

            } //container max-advertisement

            container min-advertisement {
              description
                  "Set the minimum advertisement interval for this group-interface";
              leaf seconds {
                type uint32 {
                  range "900..1350";
                }
                default 900;
              } //seconds

            } //container min-advertisement

            container mtu {
              description
                  "Set the advertised MTU value for this group-interface";
              leaf bytes {
                type uint32 {
                  range "1280..9212";
                }
                default 1280;
              } //bytes

            } //container mtu

            leaf other-stateful-configuration {
              type boolean;
              description
                  "Set/reset other-stateful-configuration flag for this group-interface";
            }

            container reachable-time {
              description
                  "Set the reachable time for advertisements from this group-interface";
              leaf milli-seconds {
                type uint32 {
                  range "0..3600000";
                }
                default 0;
              } //milli-seconds

            } //container reachable-time

            container retransmit-time {
              description
                  "Set the retransmit time for advertisement from this group-interface";
              leaf milli-seconds {
                type uint32 {
                  range "0..1800000";
                }
                default 0;
              } //milli-seconds

            } //container retransmit-time

            container router-lifetime {
              description
                  "Set the router lifetime for this group-interface";
              leaf seconds {
                type uint32 {
                  range "2700..9000";
                }
                default 4500;
              } //seconds

              leaf no-default-router {
                type boolean;
              } //no-default-router

            } //container router-lifetime

            leaf shutdown {
              type boolean;
              description
                  "Administratively enable/disable router advertisements on this group-interface";
            }

            container dns-options {
              presence
                  "Set/reset DNS options for this group-interface";
              leaf include-dns {
                type boolean;
                description
                    "Set/reset inclusion of the RDNSS server option 25 on this group-interface";
              }

              container rdnss-lifetime {
                description
                    "Maximum time the RDNSS address is valid in this group-interface";
                leaf seconds {
                  type uint32 {
                    range "900..3600";
                  }
                } //seconds

                leaf infinite {
                  type boolean;
                } //infinite

              } //container rdnss-lifetime

            } //container dns-options

            container prefix-options {
              presence
                  "Set/reset prefix options for this group-interface";
              leaf autonomous {
                type boolean;
                description
                    "Enable/disable prefix for stateless address autoconfiguration on this 
                     group-interface";
              }

              leaf on-link {
                type boolean;
                description
                    "Enable/disable assigning of the prefix to an interface on the specified link";
              }

              container preferred-lifetime {
                description
                    "Time for prefix to remain preferred on this group-interface";
                leaf seconds {
                  type uint32;
                } //seconds

                leaf infinite {
                  type boolean;
                } //infinite

              } //container preferred-lifetime

              container valid-lifetime {
                description
                    "Time for prefix to remain valid on this group-interface";
                leaf seconds {
                  type uint32;
                } //seconds

                leaf infinite {
                  type boolean;
                } //infinite

              } //container valid-lifetime

            } //container prefix-options

          } //container router-advertisements

          container router-solicit {
            description
                "Configure parameters used for router-solicit based authentication";
            container inactivity-timer {
              description
                  "Configure the time before an inactive host is removed";
              leaf infinite {
                type boolean;
              } //infinite

              leaf days {
                type uint32 {
                  range "0..365";
                }
              } //days

              leaf hrs {
                type uint32 {
                  range "0..23";
                }
              } //hrs

              leaf min {
                type uint32 {
                  range "0..59";
                }
              } //min

              leaf sec {
                type uint32 {
                  range "0..59";
                }
              } //sec

            } //container inactivity-timer

            container min-auth-interval {
              description
                  "Configure the minimum interval between two consecutive authentication attempts 
                   for the same host";
              leaf days {
                type uint32 {
                  range "0..4";
                }
              } //days

              leaf hrs {
                type uint32 {
                  range "0..23";
                }
              } //hrs

              leaf min {
                type uint32 {
                  range "0..59";
                }
              } //min

              leaf sec {
                type uint32 {
                  range "0..59";
                }
              } //sec

            } //container min-auth-interval

            leaf shutdown {
              type boolean;
              description
                  "Administratively enable/disable router-solicit based authentication";
            }

            container user-db {
              description
                  "Configure the local-user-database used for router solicit based authentication";
              leaf local-user-db-name {
                type string {
                  length "1..32";
                }
              } //local-user-db-name

            } //container user-db

          } //container router-solicit

          container urpf-check {
            presence
                "Enables/Configures unicast RPF check for Ipv6 on this interface";
            container mode {
              description
                  "Configure unicast RPF check mode";
              leaf strict-loose-strict-no-ecmp {
                type enumeration {
                  enum strict;
                  enum loose;
                  enum strict-no-ecmp;
                }
              } //strict-loose-strict-no-ecmp

            } //container mode

          } //container urpf-check

        } //container ipv6

        container local-address-assignment {
          description
              "Configures local address assignment";
          container client-application {
            description
                "Configure the client applications";
            leaf ppp-v4 {
              type boolean;
            } //ppp-v4

            leaf ipoe-v4 {
              type boolean;
            } //ipoe-v4

          } //container client-application

          container default-pool {
            description
                "Configure the default pool";
            leaf pool-name {
              type string {
                length "1..32";
              }
            } //pool-name

            leaf secondary {
              type string {
                length "1..32";
              }
            } //secondary

          } //container default-pool

          container server {
            description
                "Configure the DHCP server";
            leaf server-name {
              type string;
            } //server-name

          } //container server

          leaf shutdown {
            type boolean;
            description
                "Administratively enable/disable local address assignment";
          }

          container ipv6 {
            description
                "Configures IPv6 local address assignment";
            container client-application {
              description
                  "Configure the IPv6 client applications";
              leaf ppp-slaac {
                type boolean;
                description
                    "enable PPP hosts to request addresses from a local address server";
              } //ppp-slaac

              leaf ipoe-wan {
                type boolean;
                description
                    "enable DHCP_NA requests to request addresses from a local address server";
              } //ipoe-wan

              leaf ipoe-slaac {
                type boolean;
                description
                    "enable IPoE hosts to request SLAAC prefixes from a local address server";
              } //ipoe-slaac

            } //container client-application

            container server {
              description
                  "Configure the DHCPv6 server";
              leaf server-name {
                type string;
              } //server-name

            } //container server

          } //container ipv6

        } //container local-address-assignment

        container ppp {
          presence
              "Configure PPP parameters";
          container description {
            description
                "Configure the PPP description";
            leaf description-string {
              type string {
                length "1..80";
              }
            } //description-string

          } //container description

          container policy {
            description
                "Configure the PPP policy for this interface";
            leaf ppp-policy-name {
              type string {
                length "1..32";
              }
            } //ppp-policy-name

          } //container policy

          container session-limit {
            description
                "Configure the maximum number of PPP sessions";
            leaf session-limit {
              type int32 {
                range "1..131071";
              }
              description
                  "Attribute session-limit for session-limit";
            } //session-limit

          } //container session-limit

          leaf shutdown {
            type boolean;
            description
                "Administratively enable/disable PPP";
          }

          container user-db {
            description
                "Configure the local user database to use for authentication";
            leaf local-user-db-name {
              type string {
                length "1..32";
              }
            } //local-user-db-name

          } //container user-db

        } //container ppp

        container pppoe {
          presence
              "Configure PPPoE parameters";
          container anti-spoof {
            description
                "Configure the PPPoE anti-spoof filtering";
            leaf pppoe-anti-spoofing-type {
              type enumeration {
                enum mac-sid;
                enum mac-sid-ip;
              }
              description
                  "Attribute pppoe-anti-spoofing-type for anti-spoof";
            } //pppoe-anti-spoofing-type

          } //container anti-spoof

          container description {
            description
                "Description for PPPoE";
            leaf description-string {
              type string {
                length "1..80";
              }
            } //description-string

          } //container description

          container policy {
            description
                "Configure the PPPoE policy on this interface";
            leaf ppp-policy-name {
              type string {
                length "1..32";
              }
            } //ppp-policy-name

          } //container policy

          container python-policy {
            description
                "Configure the Python policy used to modify PPPoE packets on this interface";
            leaf policy-name {
              type string;
            } //policy-name

          } //container python-policy

          container sap-session-limit {
            description
                "Configure the maximum number of PPPoE sessions per SAP";
            leaf sap-session-limit {
              type int32 {
                range "1..131071";
              }
              description
                  "Attribute sap-session-limit for sap-session-limit";
            } //sap-session-limit

          } //container sap-session-limit

          container session-limit {
            description
                "Configure the maximum number of PPPoE sessions";
            leaf session-limit {
              type int32 {
                range "1..131071";
              }
              description
                  "Attribute session-limit for session-limit";
            } //session-limit

          } //container session-limit

          leaf shutdown {
            type boolean;
            description
                "Administratively enable/disable PPPoE";
          }

          container user-db {
            description
                "Configure the local user database to use for PPP PAP/CHAP authentication";
            leaf local-user-db-name {
              type string {
                length "1..32";
              }
            } //local-user-db-name

          } //container user-db

          container dhcp-client {
            description
                "Configure the PPPoE-to-DHCP options";
            leaf ccag-use-origin-sap {
              type boolean;
              status "obsolete";
              description
                  "Include the original VPLS SAP in the circuit-id option to send to the DHCP 
                   server (in case this interface is connected to a VPLS via a CCA MDA)";
            }

            container client-id {
              description
                  "Configure the format of the Nokia vendor specific client-id suboption";
              leaf client-id-id {
                type enumeration {
                  enum mac-pppoe-session-id;
                }
              } //client-id-id

            } //container client-id

          } //container dhcp-client

        } //container pppoe

        list sap {
          key "sap-id";
          description
              "Provision a SAP";
          leaf sap-id {
            type string;
            description
                "Attribute sap-id for sap";
          } //sap-id

          list accounting-policy {
            key "acct-policy-id";
            description
                "Configure accounting-policy to be used";
            leaf acct-policy-id {
              type uint64 {
                range "1..99";
              }
            } //acct-policy-id

          } //list accounting-policy

          container anti-spoof {
            description
                "Configures anti-spoof filtering for this SAP";
            leaf type {
              type enumeration {
                enum ip;
                enum ip-mac;
                enum mac;
                enum nh-mac;
              }
              description
                  "Attribute type for anti-spoof";
            } //type

          } //container anti-spoof

          container app-profile {
            description
                "Configure the application profile name";
            leaf app-profile-name {
              type string {
                length "1..32";
              }
            } //app-profile-name

          } //container app-profile

          container calling-station-id {
            description
                "Configure the RADIUS calling-station-id to include in auth/acct requests";
            leaf calling-station-id {
              type string {
                length "1..64";
              }
            } //calling-station-id

          } //container calling-station-id

          leaf collect-stats {
            type boolean;
            description
                "Enable/disable statistics collection";
          }

          container cpu-protection {
            description
                "Configure CPU protection";
            leaf policy-id {
              type uint32 {
                range "1..255";
              }
              default 254;
              description
                  "[1..255] - Default: 254";
            } //policy-id

            leaf mac-monitoring {
              type boolean;
              description
                  "keyword - enable MAC monitoring";
            } //mac-monitoring

            leaf eth-cfm-monitoring {
              type boolean;
              description
                  "keyword - enable Ethernet Connectivity Fault Management monitoring";
            } //eth-cfm-monitoring

            leaf aggregate {
              type boolean;
              description
                  "keyword - apply the rate limit to the sum of the per peer packet rates";
            } //aggregate

            leaf car {
              type boolean;
              description
                  "keyword - Committed Access Rate - ignore Eth-CFM packets when enforcing 
                   overall-rate";
            } //car

            leaf ip-src-monitoring {
              type boolean;
              description
                  "keyword - enable monitoring per IP source address";
            } //ip-src-monitoring

          } //container cpu-protection

          list default-host {
            key "ip-address-mask";
            description
                "Configure default-host to be used";
            leaf ip-address-mask {
              type string;
              description
                  "Attribute ipv4-prefix/mask | ipv6-prefix/prefix-length for default-host";
            } //ip-address-mask

            leaf next-hop {
              type string;
              description
                  "Attribute ipv4-address | ipv6-address for default-host";
            } //next-hop

          } //list default-host

          list description {
            key "long-description-string";
            description
                "Description for the SAP";
            leaf long-description-string {
              type string {
                length "1..160";
              }
            } //long-description-string

          } //list description

          container dist-cpu-protection {
            description
                "Assign Distributed CPU protection policy for the SAP";
            leaf policy-name {
              type string;
            } //policy-name

          } //container dist-cpu-protection

          container host-lockout-policy {
            description
                "Configure host lockout policy";
            leaf policy-name {
              type string {
                length "1..32";
              }
            } //policy-name

          } //container host-lockout-policy

          leaf host-shutdown {
            type boolean;
            description
                "Administratively enable/disable host creation on this SAP";
          }

          container lag-link-map-profile {
            description
                "Configure lag link profile";
            leaf link-map-profile-id {
              type string;
              description
                  "Attribute link-map-profile-id for lag-link-map-profile";
            } //link-map-profile-id

          } //container lag-link-map-profile

          container lag-per-link-hash {
            description
                "Configure per-link-hash information";
            leaf class {
              type enumeration {
                enum 1;
                enum 2;
                enum 3;
              }
            } //class

            leaf weight {
              type uint32 {
                range "1..1024";
              }
            } //weight

          } //container lag-per-link-hash

          container monitor-oper-group {
            description
                "Configure an Operational-Group to monitor";
            leaf group-name {
              type string {
                length "1..32";
              }
            } //group-name

          } //container monitor-oper-group

          container multi-service-site {
            description
                "Specify the multi-service-site to which this SAP belongs";
            leaf customer-site-name {
              type string {
                length "1..32";
              }
            } //customer-site-name

          } //container multi-service-site

          container oper-group {
            description
                "Configure operational-group";
            leaf group-name {
              type string {
                length "1..32";
              }
            } //group-name

          } //container oper-group

          leaf shutdown {
            type boolean;
            description
                "Administratively enable/disable the SAP";
          }

          container atm {
            description
                "Configure ATM properties";
            container encapsulation {
              description
                  "Configure the ATM encap-type";
              leaf atm-encap-type {
                type enumeration {
                  enum aal5auto;
                  enum aal5mux-bridged-eth-nofcs;
                  enum aal5mux-ppp;
                  enum aal5nlpid-ppp;
                  enum aal5snap-bridged;
                }
              } //atm-encap-type

            } //container encapsulation

            container egress {
              description
                  "Configure egress parameters";
              container traffic-desc {
                description
                    "Assign ATM traffic descriptor profile";
                leaf traffic-desc-profile-id {
                  type int32 {
                    range "1..1000";
                  }
                } //traffic-desc-profile-id

              } //container traffic-desc

            } //container egress

            container ingress {
              description
                  "Configure ingress parameters";
              container traffic-desc {
                description
                    "Assign ATM traffic descriptor profile";
                leaf traffic-desc-profile-id {
                  type int32 {
                    range "1..1000";
                  }
                } //traffic-desc-profile-id

              } //container traffic-desc

            } //container ingress

            container oam {
              description
                  "Configure OAM propertvprn";
              leaf alarm-cells {
                type boolean;
                description
                    "Disable/enable handling and generation of AIS/RDI";
              }

              leaf periodic-loopback {
                type boolean;
                description
                    "Disable/enable periodic loopback cells";
              }

            } //container oam

          } //container atm

          container egress {
            description
                "Configure egress policies";
            container filter {
              description
                  "Apply egress filter";
              leaf ip {
                type string;
                description
                    "[1..65535]|<name:64 char max>";
              } //ip

              leaf ipv6 {
                type string;
                description
                    "[1..65535]|<name:64 char max>";
              } //ipv6

            } //container filter

            container policer-control-policy {
              description
                  "Specify policer control policy";
              leaf policy-name {
                type string {
                  length "1..32";
                }
              } //policy-name

            } //container policer-control-policy

            leaf qinq-mark-top-only {
              type boolean;
              description
                  "Mark p-bits on top q-tag only";
            }

            list qos {
              key "policy-id";
              description
                  "Apply egress qos policy";
              leaf policy-id {
                type string;
                description
                    "[1..65535]|<name:64 char max>";
              } //policy-id

            } //list qos

            container scheduler-policy {
              description
                  "Specify a scheduler-policy";
              leaf scheduler-policy-name {
                type string {
                  length "1..32";
                }
              } //scheduler-policy-name

            } //container scheduler-policy

            container agg-rate {
              presence
                  "Configure aggregate rate limit";
              leaf limit-unused-bandwidth {
                type boolean;
                description
                    "Specify whether to enable limit unused bandwidth";
              }

              leaf queue-frame-based-accounting {
                type boolean;
                description
                    "Specify whether to enable queue frame based accounting";
              }

              container rate {
                description
                    "Specify rate limit for agg-rate";
                leaf kilobits-per-second {
                  type string;
                  description
                      "[1..6400000000|max] Kbps";
                } //kilobits-per-second

              } //container rate

            } //container agg-rate

          } //container egress

          container eth-cfm {
            description
                "Configure CFM parameters";
            leaf collect-lmm-stats {
              type boolean;
              description
                  "Enable/Disable the collection of statistics for OAM-PM Loss Measurement 
                   Message (LMM) tests";
            }

            container squelch-ingress-levels {
              description
                  "Configure the level(s) of the ETH-CFM PDUs that will be silently discarded";
              leaf t0 {
                type boolean;
                description
                    "[0..7]";
              } //t0

              leaf t1 {
                type boolean;
              } //t1

              leaf t2 {
                type boolean;
              } //t2

              leaf t3 {
                type boolean;
              } //t3

              leaf t4 {
                type boolean;
              } //t4

              leaf t5 {
                type boolean;
              } //t5

              leaf t6 {
                type boolean;
              } //t6

              leaf t7 {
                type boolean;
              } //t7

            } //container squelch-ingress-levels

            container tunnel-fault {
              description
                  "Accept/Ignore tunnel fault notification";
              leaf tunnel-fault-id {
                type enumeration {
                  enum accept;
                  enum ignore;
                }
              } //tunnel-fault-id

            } //container tunnel-fault

            container collect-lmm-fc-stats {
              description
                  "Configure the collection of Forwarding Class (FC) aware statistics for OAM-PM 
                   Loss Measurement Message (LMM) tests";
              container fc {
                description
                    "Configure Forwarding Class (FC) counters without regard for profile";
                leaf-list fc-name {
                  type enumeration {
                    enum be;
                    enum l2;
                    enum af;
                    enum l1;
                    enum h2;
                    enum ef;
                    enum h1;
                    enum nc;
                  }
                  max-elements 8;
                } //fc-name

              } //container fc

              container fc-in-profile {
                description
                    "Configure only in profile Forwarding Class (FC) counters";
                leaf-list fc-name {
                  type enumeration {
                    enum be;
                    enum l2;
                    enum af;
                    enum l1;
                    enum h2;
                    enum ef;
                    enum h1;
                    enum nc;
                  }
                  max-elements 8;
                } //fc-name

              } //container fc-in-profile

            } //container collect-lmm-fc-stats

            list mep {
              key "mep-id domain association";
              description
                  "Configure a CFM Maintenance Endpoint";
              leaf mep-id {
                type int16 {
                  range "1..8191";
                }
              } //mep-id

              leaf domain {
                type uint32 {
                  range "1..4294967295";
                }
              } //domain

              leaf association {
                type uint32 {
                  range "1..4294967295";
                }
              } //association

              leaf direction {
                type enumeration {
                  enum up;
                  enum down;
                }
                description
                    "keywords";
              } //direction

              leaf ccm-enable {
                type boolean;
                description
                    "Enable/Disable Generation of CCM messages";
              }

              container ccm-ltm-priority {
                description
                    "Configure the priority of CCM and LTM messages";
                leaf priority {
                  type uint16 {
                    range "0..7";
                  }
                  description
                      "[0..7] - Default highest priority on bridge-port";
                } //priority

              } //container ccm-ltm-priority

              container ccm-padding-size {
                description
                    "Insert additional padding in the CCM packets";
                leaf ccm-padding {
                  type uint32 {
                    range "3..1500";
                  }
                  description
                      "3..1500 octets";
                } //ccm-padding

              } //container ccm-padding-size

              container description {
                description
                    "Add/remove a text description for the MEP";
                leaf description-string {
                  type string {
                  }
                  description
                      "[80 chars max]";
                } //description-string

              } //container description

              container fault-propagation-enable {
                description
                    "Configure the Fault Propagation for the MEP";
                leaf use-if-tlv-suspend-ccm {
                  type enumeration {
                    enum use-if-tlv;
                    enum suspend-ccm;
                  }
                  description
                      "keywords - use interface TLV, or suspend Continuity Check Messages";
                } //use-if-tlv-suspend-ccm

              } //container fault-propagation-enable

              container low-priority-defect {
                description
                    "Configure the Lowest Priority Defect for the MEP";
                leaf allDef-macRemErrXcon-remErrXcon-errXcon-xcon-noXcon {
                  type enumeration {
                    enum allDef;
                    enum macRemErrXcon;
                    enum remErrXcon;
                    enum errXcon;
                    enum xcon;
                    enum noXcon;
                  }
                  description
                      "keywords";
                } //allDef-macRemErrXcon-remErrXcon-errXcon-xcon-noXcon

              } //container low-priority-defect

              container mac-address {
                description
                    "Configure the MAC Address for the MEP";
                leaf mac-address {
                  type yang:mac-address;
                } //mac-address

              } //container mac-address

              container one-way-delay-threshold {
                description
                    "Configure the one-way-delay test threshold";
                leaf seconds {
                  type uint32 {
                    range "0..600";
                  }
                  default 3;
                  description
                      "[0..600] Default: 3";
                } //seconds

              } //container one-way-delay-threshold

              leaf shutdown {
                type boolean;
                description
                    "Administratively enable/disable the MEP";
              }

              container ais-enable {
                presence
                    "Configure the generation and reception of Alarm Indication Signal (AIS) 
                     message parameters";
                leaf interface-support-enable {
                  type boolean;
                  description
                      "Enable/disable the generation of AIS PDUs based on the associated endpoint 
                       state";
                }

                container interval {
                  description
                      "Configure the transmission interval of AIS messages";
                  leaf t1-60 {
                    type enumeration {
                      enum 1;
                      enum 60;
                    }
                    default 1;
                    description
                        "seconds - Default: 1";
                  } //t1-60

                } //container interval

                container priority {
                  description
                      "Configure the priority of AIS messages originated by the node";
                  leaf priority-value {
                    type uint32 {
                      range "0..7";
                    }
                    default 7;
                    description
                        "[0..7] - Default: 7";
                  } //priority-value

                } //container priority

              } //container ais-enable

              container alarm-notification {
                description
                    "Configure the MEP alarm notification parameters";
                container fng-alarm-time {
                  description
                      "Configure the Fault Notification Generation (FNG) alarm time";
                  leaf time {
                    type enumeration {
                      enum 0;
                      enum 250;
                      enum 500;
                      enum 1000;
                    }
                    default 0;
                    description
                        "[0,250,500,1000] centi-seconds - Default: 0";
                  } //time

                } //container fng-alarm-time

                container fng-reset-time {
                  description
                      "Configure the Fault Notification Generation (FNG) reset time";
                  leaf time {
                    type enumeration {
                      enum 0;
                      enum 250;
                      enum 500;
                      enum 1000;
                    }
                    default 0;
                    description
                        "[0,250,500,1000] centi-seconds - Default: 0";
                  } //time

                } //container fng-reset-time

              } //container alarm-notification

              container csf-enable {
                presence
                    "Configure the reception of Client Signal Fail (CSF) message parameters";
                container multiplier {
                  description
                      "Configure the multiplier used for timing out CSF";
                  leaf multiplier-value {
                    type string;
                    description
                        "[0.0|2.0 .. 30.0] - Default: 3.5";
                  } //multiplier-value

                } //container multiplier

              } //container csf-enable

              container eth-test-enable {
                presence
                    "Enable/Disable eth-test functionality on MEP";
                container bit-error-threshold {
                  description
                      "Configure the bit error trap threshold";
                  leaf bit-errors {
                    type uint32 {
                      range "0..11840";
                    }
                    default 1;
                    description
                        "[0..11840] Default: 1";
                  } //bit-errors

                } //container bit-error-threshold

                container test-pattern {
                  description
                      "Configure the test pattern for eth-test frames";
                  leaf all-zeros-all-ones {
                    type enumeration {
                      enum all-zeros;
                      enum all-ones;
                    }
                    default "all-zeros";
                    description
                        "keywords - Test pattern - default: all-zeros";
                  } //all-zeros-all-ones

                  leaf crc-enable {
                    type boolean;
                    description
                        "keyword - Generate CRC checksum";
                  } //crc-enable

                } //container test-pattern

              } //container eth-test-enable

              container grace {
                description
                    "Configure the generation and reception of grace period parameters";
                container eth-ed {
                  description
                      "Configure the generation and reception of eth-ed grace period parameters";
                  container max-rx-defect-window {
                    description
                        "Configure/Disable an upper maximum defect window length; when disabled the 
                         advertised value from the peer will be used; when enabled the lower of the 
                         configured value or the advertised value from the peer will be used";
                    leaf seconds {
                      type uint32 {
                        range "1..86400";
                      }
                      description
                          "[1..86400] - Default: no max-rx-defect-window";
                    } //seconds

                  } //container max-rx-defect-window

                  container priority {
                    description
                        "Configure/Disable the transmission priority value for ETH-ED PDUs; when 
                         disabled the priority value of ccm-ltm-priority associated with this MEP will 
                         be used";
                    leaf priority {
                      type int32 {
                        range "0..7";
                      }
                      default 0;
                      description
                          "[0..7] - Default: no priority";
                    } //priority

                  } //container priority

                  leaf rx-eth-ed {
                    type boolean;
                    description
                        "Enable/Disable the receiving and processing of ETH-ED PDUs";
                  }

                  leaf tx-eth-ed {
                    type boolean;
                    description
                        "Enable/Disable the transmission of ETH-ED PDUs";
                  }

                } //container eth-ed

                container eth-vsm-grace {
                  description
                      "Configure the generation and reception of sros vendor specific message (vsm) 
                       grace period parameters";
                  leaf rx-eth-vsm-grace {
                    type boolean;
                    description
                        "Enable/Disable the receiving and processing of vendor specific message (vsm) 
                         grace period notifications";
                  }

                  leaf tx-eth-vsm-grace {
                    type boolean;
                    description
                        "Enable/Disable the transmission of vsm grace period notifications";
                  }

                } //container eth-vsm-grace

              } //container grace

            } //list mep

          } //container eth-cfm

          container fwd-wholesale {
            description
                "Configure Foward wholesale information";
            container pppoe {
              description
                  "Configure EPIPE service id";
              leaf service-id {
                type string;
                description
                    "Attribute service-id for pppoe";
              } //service-id

            } //container pppoe

          } //container fwd-wholesale

          container igmp-host-tracking {
            description
                "Configure IGMP host tracking parameters";
            leaf disable-router-alert-check {
              type boolean;
              description
                  "Enable/disable the IGMP router alert check option";
            }

            container expiry-time {
              description
                  "Configure the time that the system continues to track inactive hosts";
              leaf expiry-time {
                type uint32 {
                  range "1..65535";
                }
                description
                    "[1..65535] seconds";
              } //expiry-time

            } //container expiry-time

            container import {
              description
                  "Specify the import policy to filter IGMP packets";
              leaf policy-name {
                type string {
                  length "1..32";
                }
              } //policy-name

            } //container import

            container max-num-groups {
              description
                  "Configure the max number of multicast groups allowed to be tracked";
              leaf max-num-groups-id {
                type uint32 {
                  range "1..16000";
                }
              } //max-num-groups-id

            } //container max-num-groups

            container max-num-grp-sources {
              description
                  "Configure the max number of multicast group sources allowed to be tracked per 
                   group";
              leaf max-num-grp-sources-id {
                type uint16 {
                  range "1..32000";
                }
              } //max-num-grp-sources-id

            } //container max-num-grp-sources

            container max-num-sources {
              description
                  "Configure the max number of multicast sources allowed to be tracked per group";
              leaf max-num-sources-id {
                type uint32 {
                  range "1..1000";
                }
              } //max-num-sources-id

            } //container max-num-sources

          } //container igmp-host-tracking

          container ingress {
            description
                "Configure ingress policies";
            container filter {
              description
                  "Apply ingress filter";
              leaf ip {
                type string;
                description
                    "[1..65535]|<name:64 char max>";
              } //ip

              leaf ipv6 {
                type string;
                description
                    "[1..65535]|<name:64 char max>";
              } //ipv6

            } //container filter

            container match-qinq-dot1p {
              description
                  "Define 802.1P bits to match in QinQ SAP's";
              leaf top-bottom {
                type enumeration {
                  enum top;
                  enum bottom;
                }
              } //top-bottom

            } //container match-qinq-dot1p

            container policer-control-policy {
              description
                  "Specify policer control policy";
              leaf policy-name {
                type string {
                  length "1..32";
                }
              } //policy-name

            } //container policer-control-policy

            list qos {
              key "policy-id";
              description
                  "Apply ingress qos policy";
              leaf policy-id {
                type string;
                description
                    "[1..65535]|<name:64 char max>";
              } //policy-id

              leaf shared-queuing {
                type enumeration {
                  enum shared-queuing;
                }
                description
                    "enables shared-queuing";
              } //shared-queuing

            } //list qos

            container scheduler-policy {
              description
                  "Specify a scheduler-policy";
              leaf scheduler-policy-name {
                type string {
                  length "1..32";
                }
              } //scheduler-policy-name

            } //container scheduler-policy

          } //container ingress

          container static-host {
            description
                "Configure a static host on this SAP";
            leaf ip {
              type string;
              description
                  "Attribute ip-prefix[/prefix-length] for static-host";
            } //ip

            leaf mac {
              type string;
              description
                  "xx:xx:xx:xx:xx:xx or xx-xx-xx-xx-xx-xx (cannot be all zeros)";
            } //mac

            leaf all {
              type boolean;
            } //all

            leaf force {
              type boolean;
              description
                  "keyword - force removal";
            } //force

            container ancp-string {
              description
                  "Configure the ANCP string";
              leaf ancp-string {
                type string {
                  length "1..63";
                }
              } //ancp-string

            } //container ancp-string

            container app-profile {
              description
                  "Configure the application profile name";
              leaf app-profile-name {
                type string {
                  length "1..32";
                }
              } //app-profile-name

              leaf scope {
                type enumeration {
                  enum subscriber;
                  enum mac;
                }
                default "subscriber";
                description
                    "subscriber|mac - default:subscriber";
              } //scope

            } //container app-profile

            container inter-dest-id {
              description
                  "Configure the intermediate destination id";
              leaf intermediate-destination-id {
                type string {
                  length "1..32";
                }
              } //intermediate-destination-id

            } //container inter-dest-id

            container mac-linking {
              description
                  "Associate this IPv6 host to the specified IPv4 host through the learned MAC 
                   address";
              leaf ip-address {
                type inet:ip-address;
              } //ip-address

            } //container mac-linking

            container retail-svc-id {
              description
                  "Configure the retail service id";
              leaf service-id {
                type string;
                description
                    "Attribute service-id for retail-svc-id";
              } //service-id

            } //container retail-svc-id

            container rip-policy {
              description
                  "Configure the RIP policy name";
              leaf policy-name {
                type string {
                  length "1..32";
                }
              } //policy-name

            } //container rip-policy

            leaf shutdown {
              type boolean;
              description
                  "Enable/disable the static host";
            }

            container sla-profile {
              description
                  "Configure the SLA profile name";
              leaf sla-profile-name {
                type string {
                  length "1..32";
                }
              } //sla-profile-name

            } //container sla-profile

            container sub-profile {
              description
                  "Configure the sub-profile name";
              leaf sub-profile-name {
                type string {
                  length "1..32";
                }
              } //sub-profile-name

            } //container sub-profile

            container subscriber {
              description
                  "Configure the subscriber identification";
              leaf sub-ident-string {
                type string;
                description
                    "Attribute sub-ident-string for subscriber";
              } //sub-ident-string

            } //container subscriber

            leaf subscriber-sap-id {
              type boolean;
              description
                  "Enable/disable using the SAP id as subscriber id";
            }

            container managed-routes {
              description
                  "Configure managed routes";
              container route {
                description
                    "Configure a managed route";
                leaf ip-prefix-length {
                  type inet:ip-prefix;
                  description
                      "ip-prefix - a.b.c.d 
                       host bits must be 0 
                       length [1..32]";
                } //ip-prefix-length

                leaf netmask {
                  type string;
                  description
                      "a.b.c.d any mask expressed as dotted quad 
                       0.0.0.0 not allowed";
                } //netmask

                leaf ipv6-prefix-prefix-length {
                  type string;
                  description
                      "Attribute ipv6-prefix/prefix-length for route";
                } //ipv6-prefix-prefix-length

                leaf metric {
                  type uint32;
                } //metric

              } //container route

            } //container managed-routes

          } //container static-host

          container static-host-mgmt {
            description
                "Configure common parameters for static hosts";
            container mac-learning-options {
              presence
                  "Configure behavior options related to learning of subscriber host MAC 
                   addresses";
              leaf data-triggered {
                type boolean;
                description
                    "Enable learning of MAC addresses from data packets";
              }

              leaf single-mac {
                type boolean;
                description
                    "Enforce the limit of a single MAC address per SAP, learned by means of ICMPv6";
              }

            } //container mac-learning-options

          } //container static-host-mgmt

          container sub-sla-mgmt {
            presence
                "Configure subscriber management for this SAP";
            container def-app-profile {
              description
                  "Configure a default application profile for this SAP";
              leaf default-app-profile-name {
                type string {
                  length "1..32";
                }
              } //default-app-profile-name

            } //container def-app-profile

            container def-inter-dest-id {
              description
                  "Configure default inter-dest-id";
              leaf string {
                type string {
                  length "1..32";
                }
              } //string

              leaf def-inter-dest-id-id {
                type enumeration {
                  enum use-top-q;
                  enum use-vpi;
                }
              } //def-inter-dest-id-id

            } //container def-inter-dest-id

            container def-sla-profile {
              description
                  "Configure a default SLA profile for this SAP";
              leaf default-sla-profile-name {
                type string {
                  length "1..32";
                }
              } //default-sla-profile-name

            } //container def-sla-profile

            container def-sub-id {
              description
                  "Configure a default subscriber identification string for this SAP";
              leaf use-sap-id {
                type boolean;
                description
                    "keyword - use sap-id as subscriber-id";
              } //use-sap-id

              leaf string {
                type string;
                description
                    "Attribute sub-ident-string for def-sub-id";
              } //string

              leaf use-auto-id {
                type boolean;
                description
                    "keyword - use auto-generated subscriber-id";
              } //use-auto-id

            } //container def-sub-id

            container def-sub-profile {
              description
                  "Configure a default subscriber profile for this SAP";
              leaf default-subscriber-profile-name {
                type string {
                  length "1..32";
                }
              } //default-subscriber-profile-name

            } //container def-sub-profile

            container multi-sub-sap {
              description
                  "Configure maximum number of subscribers for this SAP";
              leaf subscriber-limit {
                type uint32 {
                  range "2..131071";
                }
                description
                    "Attribute subscriber-limit for multi-sub-sap";
              } //subscriber-limit

            } //container multi-sub-sap

            leaf shutdown {
              type boolean;
              description
                  "Enable/disable subscriber management on this SAP";
            }

            container sub-ident-policy {
              description
                  "Apply a subscriber identification policy on this SAP";
              leaf sub-ident-policy-name {
                type string {
                  length "1..32";
                }
              } //sub-ident-policy-name

            } //container sub-ident-policy

            container single-sub-parameters {
              description
                  "Configure the single-sub-parameters for this SAP";
              container non-sub-traffic {
                description
                    "Configure non-subscriber-traffic profiles";
                leaf sub-profile {
                  type string {
                    length "1..32";
                  }
                } //sub-profile

                leaf sla-profile {
                  type string {
                    length "1..32";
                  }
                } //sla-profile

                leaf subscriber {
                  type string;
                  description
                      "Attribute sub-ident-string for non-sub-traffic";
                } //subscriber

                leaf app-profile {
                  type string {
                    length "1..32";
                  }
                } //app-profile

              } //container non-sub-traffic

              leaf profiled-traffic-only {
                type boolean;
                description
                    "Enable/disable profiled-traffic-only for this SAP";
              }

            } //container single-sub-parameters

          } //container sub-sla-mgmt

        } //list sap

        container sap-parameters {
          description
              "Configure (internal) SAP parameters";
          container anti-spoof {
            description
                "Configure the anti-spoofing type";
            leaf anti-spoof-id {
              type enumeration {
                enum ip-mac;
                enum nh-mac;
              }
            } //anti-spoof-id

          } //container anti-spoof

          container description {
            description
                "Configure the description";
            leaf description-string {
              type string {
                length "1..80";
              }
            } //description-string

          } //container description

          container sub-sla-mgmt {
            description
                "Configure subscriber policies and profiles";
            container def-app-profile {
              description
                  "Configure default application profile";
              leaf app-profile-name {
                type string {
                  length "1..32";
                }
              } //app-profile-name

            } //container def-app-profile

            container def-sla-profile {
              description
                  "Configure default SLA profile";
              leaf sla-profile-name {
                type string {
                  length "1..32";
                }
              } //sla-profile-name

            } //container def-sla-profile

            container def-sub-id {
              description
                  "Configure default subscriber id";
              leaf string {
                type string;
                description
                    "Attribute sub-ident-string for def-sub-id";
              } //string

              leaf use-auto-id {
                type boolean;
                description
                    "keyword - use auto-generated subscriber-id";
              } //use-auto-id

            } //container def-sub-id

            container def-sub-profile {
              description
                  "Configure default subscriber profile";
              leaf sub-profile-name {
                type string {
                  length "1..32";
                }
              } //sub-profile-name

            } //container def-sub-profile

            container sub-ident-policy {
              description
                  "Configure subscriber identification policy";
              leaf policy-name {
                type string {
                  length "1..32";
                }
              } //policy-name

            } //container sub-ident-policy

          } //container sub-sla-mgmt

        } //container sap-parameters

        list srrp {
          key "srrp-id";
          description
              "Configure an SRRP instance on this interface";
          leaf srrp-id {
            type uint32 {
              range "1..4294967295";
            }
          } //srrp-id

          list bfd-enable {
            key "interface dst-ip";
            description
                "Configure a BFD interface";
            leaf service-id {
              type string;
              description
                  "Attribute service-id for bfd-enable";
            } //service-id

            leaf interface {
              type string {
                length "1..32";
              }
              description
                  "[32 chars max] (must start with a letter)";
            } //interface

            leaf dst-ip {
              type inet:ip-address;
              description
                  "ip-address";
            } //dst-ip

            leaf name {
              type string;
              description
                  "64-char max (ies/vprn service-name)";
            } //name

          } //list bfd-enable

          container description {
            description
                "Configure the description for the SRRP instance";
            leaf description {
              type string {
                length "1..80";
              }
            } //description

          } //container description

          container gw-mac {
            description
                "Configure the gateway MAC address";
            leaf mac-address {
              type string;
              description
                  "xx:xx:xx:xx:xx:xx or xx-xx-xx-xx-xx-xx";
            } //mac-address

          } //container gw-mac

          container keep-alive-interval {
            description
                "Configure the interval between SRRP advertisements";
            leaf interval {
              type uint32 {
                range "1..100";
              }
              description
                  "[1..100] tenths of a second";
            } //interval

          } //container keep-alive-interval

          container message-path {
            description
                "Configure the SAP to use as the SRRP message path";
            leaf sap-id {
              type string;
              description
                  "Attribute sap-id for message-path";
            } //sap-id

          } //container message-path

          container monitor-oper-group {
            description
                "Configure an Operational-Group to monitor";
            leaf group-name {
              type string {
                length "1..32";
              }
            } //group-name

            leaf priority-step {
              type int32 {
                range "1..10";
              }
            } //priority-step

          } //container monitor-oper-group

          leaf one-garp-per-sap {
            type boolean;
            description
                "Configure to send one gratuitous ARP to each SAP";
          }

          list policy {
            key "vrrp-policy-id";
            description
                "Associate a VRRP Priority Control Policy with this SRRP instance";
            leaf vrrp-policy-id {
              type uint32 {
                range "1..9999";
              }
            } //vrrp-policy-id

          } //list policy

          leaf preempt {
            type boolean;
            description
                "Allow/disallow the srrp instance to override an existing master";
          }

          container priority {
            description
                "Configure the base priority";
            leaf priority {
              type uint16 {
                range "1..254";
              }
            } //priority

          } //container priority

          container send-fib-population-packets {
            description
                "Configure Mode used to send Fib population packets";
            leaf mode {
              type enumeration {
                enum all;
                enum outer-tag-only;
              }
            } //mode

          } //container send-fib-population-packets

          leaf shutdown {
            type boolean;
            description
                "Administratively enable/disable SRRP";
          }

        } //list srrp

        container urpf-check {
          presence
              "Enables/Configures unicast RPF check for an interface";
          container mode {
            description
                "Configure unicast RPF check mode";
            leaf strict-loose-strict-no-ecmp {
              type enumeration {
                enum strict;
                enum loose;
                enum strict-no-ecmp;
              }
              description
                  "keywords";
            } //strict-loose-strict-no-ecmp

          } //container mode

        } //container urpf-check

        container wlan-gw {
          description
              "Configure WLAN Gateway";
          container gw-address {
            status "obsolete";
            description
                "Configure the IP address of the WLAN Gateway on this interface";
            leaf ip-address {
              type inet:ip-address;
              description
                  "a.b.c.d";
            } //ip-address

          } //container gw-address

          container gw-ipv6-address {
            status "obsolete";
            description
                "Configure the IPv6 address of the WLAN Gateway on this interface";
            leaf ipv6-address {
              type inet:ipv6-address;
              description
                  "Attribute ipv6-address for gw-ipv6-address";
            } //ipv6-address

          } //container gw-ipv6-address

          container l2-ap-auto-sub-id-fmt {
            description
                "Configure the auto-generated subscriber id format";
            leaf l2-ap-auto-sub-id-fmt-id {
              type enumeration {
                enum include-ap-tags;
                enum sap-only;
              }
            } //l2-ap-auto-sub-id-fmt-id

          } //container l2-ap-auto-sub-id-fmt

          container l2-ap-encap-type {
            description
                "Configure the default encapsulation type for layer 2 access points";
            leaf l2-ap-encap-type-id {
              type enumeration {
                enum null;
                enum dot1q;
                enum qinq;
              }
            } //l2-ap-encap-type-id

          } //container l2-ap-encap-type

          container learn-ap-mac {
            description
                "Enable/disable ARP or ND packets on wlan-gw GRE tunnel";
            leaf delay-auth {
              type boolean;
            } //delay-auth

          } //container learn-ap-mac

          container max-lanext-bd {
            description
                "Configure maximum number of Bridged Domains for this interface";
            leaf max-lanext-bd-id {
              type uint32 {
                range "1..131071";
              }
            } //max-lanext-bd-id

          } //container max-lanext-bd

          leaf oper-down-on-group-degrade {
            type boolean;
            description
                "Configure if this interface will go down when its wlan-gw-group is degraded";
          }

          container router {
            description
                "Configure the router for the tunneled User Equipment traffic";
            leaf router-instance {
              type string {
                length "1..32";
              }
              default "Base";
              description
                  "Attribute router-instance for router";
            } //router-instance

          } //container router

          leaf shutdown {
            type boolean;
            description
                "Enable/disable Soft-GRE";
          }

          container tcp-mss-adjust {
            description
                "Configure the value to adjust the TCP Maximum Segment Size (MSS) option";
            leaf segment-size {
              type uint32 {
                range "160..10240";
              }
            } //segment-size

          } //container tcp-mss-adjust

          container wlan-gw-group {
            description
                "Configure the ISA WLAN-GW Group";
            leaf group-id {
              type uint32 {
                range "1..4";
              }
            } //group-id

          } //container wlan-gw-group

          container egress {
            description
                "Egress QoS configuration for WLAN Gateway tunnels";
            container agg-rate-limit {
              description
                  "Configure the aggregate rate limit";
              leaf kilobits-per-second {
                type string;
                description
                    "[1..100000000|max]";
              } //kilobits-per-second

            } //container agg-rate-limit

            container hold-time {
              description
                  "Configure the hold time for the egress resources";
              leaf hold-time-id {
                type uint32 {
                  range "1..86400";
                }
              } //hold-time-id

              leaf infinite {
                type boolean;
              } //infinite

            } //container hold-time

            container qos {
              description
                  "Apply a QoS policy";
              leaf policy-id {
                type string;
                description
                    "[1..65535]|<name:64 char max>";
              } //policy-id

            } //container qos

            container scheduler-policy {
              description
                  "Apply a scheduler policy";
              leaf scheduler-policy-name {
                type string {
                  length "1..32";
                }
              } //scheduler-policy-name

            } //container scheduler-policy

            leaf shape-multi-client-only {
              type boolean;
              description
                  "Shape a tunnel's traffic only if multiple UE are using it";
            }

            container shaping {
              description
                  "Configure shaping";
              leaf shaping-id {
                type enumeration {
                  enum per-retailer;
                  enum per-tunnel;
                }
              } //shaping-id

            } //container shaping

          } //container egress

          container group-encryption {
            description
                "Configure group encryption";
            list encryption-keygroup {
              key "direction";
              description
                  "Configure the encryption-keygroup";
              leaf keygroup-id {
                type string;
                description
                    "Attribute keygroup-id for encryption-keygroup";
              } //keygroup-id

              leaf direction {
                type enumeration {
                  enum inbound;
                  enum outbound;
                }
              } //direction

            } //list encryption-keygroup

          } //container group-encryption

          container gw-addresses {
            description
                "Configure the IP address of the WLAN Gateway(s) on this interface";
            list address {
              key "ip-address-ipv6-address";
              description
                  "Configure an IPv4 or IPv6 address of a WLAN Gateway (max 4 IPv4 and 6 IPv6 
                   addresses)";
              leaf ip-address-ipv6-address {
                type string;
                description
                    "Attribute ip-address|ipv6-address for address";
              } //ip-address-ipv6-address

              leaf xconnect {
                type boolean;
              } //xconnect

            } //list address

          } //container gw-addresses

          container l2-access-points {
            description
                "Configure layer 2 access points";
            list l2-ap {
              key "sap-id";
              description
                  "Configure a layer 2 access point";
              leaf sap-id {
                type string;
              } //sap-id

              container encap-type {
                description
                    "Configure the encapsulation type of the traffic received through this access 
                     point";
                leaf encap-type-id {
                  type enumeration {
                    enum default;
                    enum null;
                    enum dot1q;
                    enum qinq;
                  }
                } //encap-type-id

              } //container encap-type

              container epipe-sap-template {
                description
                    "Configure the Ether-Pipe SAP template for the internal connections to the 
                     tunnel ISA cards";
                leaf name {
                  type string;
                } //name

              } //container epipe-sap-template

              leaf shutdown {
                type boolean;
                description
                    "Administratively disable/enable this access point";
              }

            } //list l2-ap

          } //container l2-access-points

          container mobility {
            description
                "Configure mobility";
            leaf arp-ap {
              type boolean;
              status "obsolete";
              description
                  "Enable/disable ARP to Access Point";
            }

            container hold-time {
              description
                  "Configure the minimum time a UE is held with its AP";
              leaf time-in-s {
                type uint8;
              } //time-in-s

            } //container hold-time

            leaf inter-vlan {
              type boolean;
              description
                  "Enable mobility within different VLAN's of the same range";
            }

            leaf multi-tunnel-type {
              type boolean;
              description
                  "Enable/disable terminating multiple types of tunnels";
            }

            container trigger {
              description
                  "Configure the mobility triggers";
              leaf data {
                type boolean;
              } //data

              leaf iapp {
                type boolean;
              } //iapp

              leaf control {
                type boolean;
              } //control

            } //container trigger

          } //container mobility

          container tunnel-encaps {
            description
                "Configure tunnel encapsulation";
            container learn-l2tp-cookie {
              description
                  "Configure when to learn the L2TP cookie";
              leaf learn-l2tp-cookie-id {
                type enumeration {
                  enum if-match;
                  enum never;
                  enum always;
                }
              } //learn-l2tp-cookie-id

              leaf cookie {
                type string {
                  length "1..6";
                }
                description
                    "[0x0000..0xFFFF...(4 hex nibbles)]";
              } //cookie

            } //container learn-l2tp-cookie

          } //container tunnel-encaps

          container vlan-tag-ranges {
            description
                "Configure IEEE 802.1q VLAN tag ranges";
            container range {
              description
                  "Configure a VLAN tag range";
              leaf start {
                type uint32 {
                  range "0..4096";
                }
                default 4096;
              } //start

              leaf end {
                type uint32 {
                  range "0..4096";
                }
                default 4096;
              } //end

              leaf default {
                type boolean;
                description
                    "keyword - configure defaults for the interface";
              } //default

              leaf authenticate-on-dhcp {
                type boolean;
                description
                    "Authenticate on receiving a DHCP message from a UE";
              }

              container data-triggered-ue-creation {
                description
                    "Enable/disable data-triggered UE creation";
              }

              container http-redirect-policy {
                description
                    "Configure the HTTP redirect policy";
                leaf policy-name {
                  type string;
                } //policy-name

              } //container http-redirect-policy

              container idle-timeout {
                description
                    "Configure the idle-timeout action";
                leaf action {
                  type enumeration {
                    enum remove;
                    enum shcv;
                  }
                } //action

              } //container idle-timeout

              container nat-policy {
                description
                    "Configure the NAT policy";
                leaf policy-name {
                  type string;
                } //policy-name

              } //container nat-policy

              container retail-svc-id {
                description
                    "Configure the retailer service";
                leaf service-id {
                  type string;
                  description
                      "Attribute service-id for retail-svc-id";
                } //service-id

              } //container retail-svc-id

              container authentication {
                description
                    "Configure authentication";
                container authentication-policy {
                  description
                      "Configure the ISA RADIUS policy for authentication";
                  leaf policy-name {
                    type string;
                  } //policy-name

                } //container authentication-policy

                container hold-time {
                  description
                      "Configure the minimum time that a UE is held down after a failed 
                       authentication attempt";
                  leaf hrs {
                    type uint8 {
                    }
                  } //hrs

                  leaf min {
                    type uint8 {
                      range "1..59";
                    }
                  } //min

                  leaf sec {
                    type uint8 {
                      range "0..59";
                    }
                  } //sec

                } //container hold-time

                container vlan-mismatch-timeout {
                  description
                      "Configure the timeout for the radius proxy cache if a packet is received with 
                       a non-matching VLAN tag";
                  leaf seconds {
                    type uint32 {
                      range "5..60";
                    }
                  } //seconds

                } //container vlan-mismatch-timeout

              } //container authentication

              container brg {
                status "obsolete";
                description
                    "Configure Bridged Residential Gateway";
                leaf authenticated-brg-only {
                  type boolean;
                  status "obsolete";
                  description
                      "Configure if this system allows only hosts from authenticated Bridged 
                       Residential Gateways";
                }

                container default-brg-profile {
                  status "obsolete";
                  description
                      "Configure the BRG profile in case the AAA server does not specify it";
                  leaf profile-name {
                    type string;
                  } //profile-name

                } //container default-brg-profile

                leaf shutdown {
                  type boolean;
                  status "obsolete";
                  description
                      "Administratively disable or enable BRG";
                }

              } //container brg

              container dhcp {
                description
                    "Configure ISA DHCP for UE";
                container active-lease-time {
                  description
                      "Configure the DHCP lease time for UE in active state";
                  leaf hrs {
                    type uint8 {
                    }
                  } //hrs

                  leaf min {
                    type uint8 {
                      range "5..59";
                    }
                  } //min

                  leaf sec {
                    type uint8 {
                      range "1..59";
                    }
                  } //sec

                } //container active-lease-time

                container initial-lease-time {
                  description
                      "Configure the DHCP lease time for UE before authentication";
                  leaf hrs {
                    type uint8 {
                    }
                  } //hrs

                  leaf min {
                    type uint8 {
                      range "5..59";
                    }
                  } //min

                  leaf sec {
                    type uint8 {
                      range "1..59";
                    }
                  } //sec

                } //container initial-lease-time

                container l2-aware-ip-address {
                  description
                      "Configure the layer-2-aware yiaddress for the UE to use before authentication";
                  leaf ip-address {
                    type inet:ip-address;
                  } //ip-address

                  leaf from-pool {
                    type boolean;
                    description
                        "Allocate an IP address from a pool";
                  } //from-pool

                } //container l2-aware-ip-address

                container primary-dns {
                  description
                      "Configure the primary DNS server";
                  leaf ip-address {
                    type inet:ip-address;
                  } //ip-address

                } //container primary-dns

                container primary-nbns {
                  description
                      "Configure the primary NetBIOS server";
                  leaf ip-address {
                    type inet:ip-address;
                  } //ip-address

                } //container primary-nbns

                container secondary-dns {
                  description
                      "Configure the secondary DNS server";
                  leaf ip-address {
                    type inet:ip-address;
                  } //ip-address

                } //container secondary-dns

                container secondary-nbns {
                  description
                      "Configure the secondary NetBIOS server";
                  leaf ip-address {
                    type inet:ip-address;
                  } //ip-address

                } //container secondary-nbns

                leaf shutdown {
                  type boolean;
                  description
                      "Enable/disable ISA DHCP";
                }

              } //container dhcp

              container dhcp6 {
                description
                    "Configure ISA DHCPv6 for UE";
                container active-preferred-lifetime {
                  description
                      "Configure the ISA signaled preferred lifetime in DHCPv6 after full 
                       authentication";
                  leaf hrs {
                    type uint8 {
                    }
                  } //hrs

                  leaf min {
                    type uint8 {
                      range "5..59";
                    }
                  } //min

                  leaf sec {
                    type uint8 {
                      range "1..59";
                    }
                  } //sec

                } //container active-preferred-lifetime

                container active-valid-lifetime {
                  description
                      "Configure the ISA signaled valid lifetime in DHCPv6 after full authentication";
                  leaf hrs {
                    type uint8 {
                    }
                  } //hrs

                  leaf min {
                    type uint8 {
                      range "5..59";
                    }
                  } //min

                  leaf sec {
                    type uint8 {
                      range "1..59";
                    }
                  } //sec

                } //container active-valid-lifetime

                container initial-preferred-lifetime {
                  description
                      "Configure the ISA signaled preferred lifetime in DHCPv6 during migrant phase";
                  leaf hrs {
                    type uint8 {
                    }
                  } //hrs

                  leaf min {
                    type uint8 {
                      range "5..59";
                    }
                  } //min

                  leaf sec {
                    type uint8 {
                      range "1..59";
                    }
                  } //sec

                } //container initial-preferred-lifetime

                container initial-valid-lifetime {
                  description
                      "Configure the ISA signaled valid lifetime in DHCPv6 during migrant phase";
                  leaf hrs {
                    type uint8 {
                    }
                  } //hrs

                  leaf min {
                    type uint8 {
                      range "5..59";
                    }
                  } //min

                  leaf sec {
                    type uint8 {
                      range "1..59";
                    }
                  } //sec

                } //container initial-valid-lifetime

                leaf shutdown {
                  type boolean;
                  description
                      "Enable/disable ISA DHCPv6 for UE";
                }

              } //container dhcp6

              container distributed-sub-mgmt {
                description
                    "Configure distributed subscriber management";
                container accounting-policy {
                  description
                      "Configure the ISA RADIUS policy for accounting";
                  leaf policy-name {
                    type string;
                  } //policy-name

                } //container accounting-policy

                container accounting-update-interval {
                  description
                      "Configure the time interval between consecutive Interim Accounting Update 
                       messages (minutes)";
                  leaf accounting-update-interval-id {
                    type uint32 {
                      range "5..259200";
                    }
                  } //accounting-update-interval-id

                } //container accounting-update-interval

                leaf collect-aa-acct-stats {
                  type boolean;
                  description
                      "Enable/disable Application Assurance accounting statistics collection";
                }

                container def-app-profile {
                  description
                      "Configure the default application profile";
                  leaf profile-name {
                    type string;
                  } //profile-name

                } //container def-app-profile

                container dsm-ip-filter {
                  description
                      "Configure an IP filter that is distributed on ISA cards";
                  leaf dsm-ip-filter-name {
                    type string;
                  } //dsm-ip-filter-name

                } //container dsm-ip-filter

                container egress-policer {
                  description
                      "Configure the dsm policer for egress";
                  leaf policer-name {
                    type string;
                  } //policer-name

                } //container egress-policer

                container ingress-policer {
                  description
                      "Configure the dsm policer for ingress";
                  leaf policer-name {
                    type string;
                  } //policer-name

                } //container ingress-policer

                container one-time-redirect {
                  description
                      "Configure the one-time HTTP redirection";
                  leaf url {
                    type string {
                      length "1..255";
                    }
                    description
                        "Attribute rdr-url-string for one-time-redirect";
                  } //url

                  leaf port {
                    type uint16 {
                      range "1..65535";
                    }
                  } //port

                } //container one-time-redirect

                leaf shutdown {
                  type boolean;
                  description
                      "Disable/enable distributed subscriber management";
                }

              } //container distributed-sub-mgmt

              container l2-service {
                description
                    "Configure layer 2 service";
                leaf service-id {
                  type string;
                  description
                      "Attribute service-id for l2-service";
                } //service-id

                container description {
                  description
                      "Description for the layer 2 service";
                  leaf description-string {
                    type string {
                      length "1..80";
                    }
                  } //description-string

                } //container description

                leaf shutdown {
                  type boolean;
                  description
                      "Disable/enable layer 2 service";
                }

              } //container l2-service

              container slaac {
                description
                    "Configure ISA SLAAC for UE";
                container active-preferred-lifetime {
                  description
                      "Configure the ISA signaled preferred lifetime in SLAAC after full 
                       authentication";
                  leaf hrs {
                    type uint8 {
                    }
                  } //hrs

                  leaf min {
                    type uint8 {
                      range "5..59";
                    }
                  } //min

                  leaf sec {
                    type uint8 {
                      range "1..59";
                    }
                  } //sec

                } //container active-preferred-lifetime

                container active-valid-lifetime {
                  description
                      "Configure the ISA signaled valid lifetime in SLAAC after full authentication";
                  leaf hrs {
                    type uint8 {
                    }
                  } //hrs

                  leaf min {
                    type uint8 {
                      range "5..59";
                    }
                  } //min

                  leaf sec {
                    type uint8 {
                      range "1..59";
                    }
                  } //sec

                } //container active-valid-lifetime

                container initial-preferred-lifetime {
                  description
                      "Configure the ISA signaled preferred lifetime in SLAAC during migrant phase";
                  leaf hrs {
                    type uint8 {
                    }
                  } //hrs

                  leaf min {
                    type uint8 {
                      range "5..59";
                    }
                  } //min

                  leaf sec {
                    type uint8 {
                      range "1..59";
                    }
                  } //sec

                } //container initial-preferred-lifetime

                container initial-valid-lifetime {
                  description
                      "Configure the ISA signaled valid lifetime in SLAAC during migrant phase";
                  leaf hrs {
                    type uint8 {
                    }
                  } //hrs

                  leaf min {
                    type uint8 {
                      range "5..59";
                    }
                  } //min

                  leaf sec {
                    type uint8 {
                      range "1..59";
                    }
                  } //sec

                } //container initial-valid-lifetime

                leaf shutdown {
                  type boolean;
                  description
                      "Enable/disable ISA SLAAC for UE";
                }

              } //container slaac

              container track-mobility {
                description
                    "Configure the tracking of mobility";
                container mac-format {
                  description
                      "Configure how a MAC address is represented by the RADIUS proxy server";
                  leaf mac-format {
                    type string {
                      length "1..7";
                    }
                    description
                        "like ab: for 00:0c:f1:99:85:b8 
                         or XY- for 00-0C-F1-99-85-B8 
                         or mmmm. for 0002.03aa.abff 
                         or xx for 000cf19985b8";
                  } //mac-format

                } //container mac-format

                container radius-proxy-cache {
                  description
                      "Configure the RADIUS proxy server";
                  leaf router {
                    type string {
                      length "1..32";
                    }
                    default "Base";
                    description
                        "Attribute router-instance for radius-proxy-cache";
                  } //router

                  leaf server {
                    type string;
                  } //server

                } //container radius-proxy-cache

              } //container track-mobility

              container vrgw {
                description
                    "Configure Virtual Residential Gateway functionality";
                container brg {
                  description
                      "Configure Bridged Residential Gateway";
                  leaf authenticated-brg-only {
                    type boolean;
                    description
                        "Configure if this system allows only hosts from authenticated Bridged 
                         Residential Gateways";
                  }

                  container default-brg-profile {
                    description
                        "Configure the BRG profile in case the AAA server does not specify it";
                    leaf profile-name {
                      type string;
                    } //profile-name

                  } //container default-brg-profile

                  leaf shutdown {
                    type boolean;
                    description
                        "Administratively disable or enable BRG";
                  }

                } //container brg

                container lanext {
                  presence
                      "Configure Home LAN Extension functionality";
                  leaf assistive-address-resolution {
                    type boolean;
                    description
                        "Enable/disable assistive address resolution in bridged domains";
                  }

                  container bd-mac-prefix {
                    description
                        "Configure MAC translation prefix in bridged domains";
                    leaf mac-prefix {
                      type string {
                        length "1..8";
                      }
                      description
                          "[8 chars] format AA:BB:CC";
                    } //mac-prefix

                  } //container bd-mac-prefix

                  leaf mac-translation {
                    type boolean;
                    description
                        "Enable/disable MAC translation in bridged domains";
                  }

                  leaf shutdown {
                    type boolean;
                    description
                        "Enable/disable the Home LAN Extension functionality";
                  }

                  container access {
                    presence
                        "Configure access side attributes";
                    container max-mac {
                      description
                          "Configure maximum number of MAC entries in bridged domain";
                      leaf max-mac-id {
                        type uint32 {
                          range "1..256";
                        }
                      } //max-mac-id

                    } //container max-mac

                    leaf multi-access {
                      type boolean;
                      description
                          "Allow multiple access";
                    }

                    container policer {
                      description
                          "Configure policer for ingress home traffic";
                      leaf policer-name {
                        type string {
                          length "1..32";
                        }
                      } //policer-name

                    } //container policer

                  } //container access

                  container network {
                    presence
                        "Configure network side attributes";
                    container max-mac {
                      description
                          "Configure maximum number of VM MAC entries in bridged domain";
                      leaf max-mac-id {
                        type uint32 {
                          range "1..64";
                        }
                      } //max-mac-id

                    } //container max-mac

                    container policer {
                      description
                          "Configure policer for ingress data center traffic";
                      leaf policer-name {
                        type string {
                          length "1..32";
                        }
                      } //policer-name

                    } //container policer

                    leaf shutdown {
                      type boolean;
                      description
                          "Enable/disable data center connections";
                    }

                  } //container network

                } //container lanext

              } //container vrgw

              container xconnect {
                description
                    "Configure the cross-connect";
                container accounting-policy {
                  description
                      "Configure the ISA Radius accounting policy";
                  leaf isa-radius-policy-name {
                    type string;
                  } //isa-radius-policy-name

                } //container accounting-policy

                container accounting-update-interval {
                  description
                      "Configure the time interval between consecutive Interim Accounting Update 
                       messages (minutes)";
                  leaf accounting-update-interval-id {
                    type uint32 {
                      range "5..259200";
                    }
                  } //accounting-update-interval-id

                } //container accounting-update-interval

                leaf mobility-acct-updates {
                  type boolean;
                  description
                      "Enable/disable the sending of mobility-triggered accounting updates.";
                }

                leaf shutdown {
                  type boolean;
                  description
                      "Enable/disable the cross-connect";
                }

              } //container xconnect

            } //container range

          } //container vlan-tag-ranges

        } //container wlan-gw

        container wpp {
          presence
              "Configure Web Portal Protocol parameters";
          leaf enable-triggered-hosts {
            type boolean;
            description
                "Enable/disable triggered hosts";
          }

          container initial-app-profile {
            description
                "Configure the initial application profile";
            leaf app-profile-name {
              type string {
                length "1..32";
              }
            } //app-profile-name

          } //container initial-app-profile

          container initial-sla-profile {
            description
                "Configure the initial SLA profile";
            leaf sla-profile-name {
              type string {
                length "1..32";
              }
            } //sla-profile-name

          } //container initial-sla-profile

          container initial-sub-profile {
            description
                "Configure the initial subscriber profile";
            leaf sub-profile-name {
              type string {
                length "1..32";
              }
            } //sub-profile-name

          } //container initial-sub-profile

          container lease-time {
            description
                "Configure the lease time";
            leaf days {
              type uint32 {
                range "0..3650";
              }
            } //days

            leaf hrs {
              type uint16 {
                range "1..23";
              }
            } //hrs

            leaf min {
              type uint32 {
                range "1..59";
              }
            } //min

            leaf sec {
              type int32 {
                range "0..59";
              }
            } //sec

          } //container lease-time

          container portal {
            description
                "Configure the WPP portal for this interface";
            leaf router {
              type string {
                length "1..32";
              }
              default "Base";
              description
                  "Attribute router-instance for portal";
            } //router

            leaf name {
              type string {
                length "1..32";
              }
            } //name

          } //container portal

          container portal-group {
            description
                "Configure the WPP portal group for this interface";
            leaf portal-group-name {
              type string;
            } //portal-group-name

          } //container portal-group

          leaf restore-disconnected {
            type boolean;
            description
                "Restore initial profiles after a host has disconnected";
          }

          leaf shutdown {
            type boolean;
            description
                "Enable/disable WPP";
          }

          container user-db {
            description
                "Configure the user database";
            leaf local-user-db-name {
              type string {
                length "1..32";
              }
            } //local-user-db-name

          } //container user-db

        } //container wpp

      } //list group-interface

      container hold-time {
        description
            "Configure the hold times (up/down) for the interface";
        container down {
          description
              "Configure the hold time when the interface is coming up";
          leaf ip {
            type boolean;
          } //ip

          leaf ipv6 {
            type boolean;
          } //ipv6

          leaf seconds {
            type uint32 {
              range "1..1200";
            }
          } //seconds

          leaf init-only {
            type boolean;
          } //init-only

        } //container down

        container up {
          description
              "Configure the hold time when the interface is going down";
          leaf ip {
            type boolean;
          } //ip

          leaf ipv6 {
            type boolean;
          } //ipv6

          leaf seconds {
            type uint32 {
              range "1..1200";
            }
          } //seconds

        } //container up

      } //container hold-time

      container ipoe-linking {
        presence
            "Configures IPoE host linking";
        leaf gratuitous-rtr-adv {
          type boolean;
          description
              "Enable/disable unsolicited router advertisements";
        }

      } //container ipoe-linking

      container ipoe-session {
        presence
            "Configure IPoE session parameters";
        container session-limit {
          description
              "Configure the session limit per interface";
          leaf session-limit {
            type uint32 {
              range "1..500000";
            }
            description
                "Attribute session-limit for session-limit";
          } //session-limit

        } //container session-limit

      } //container ipoe-session

      container ipv6 {
        presence
            "Configure IPv6 parameters";
        list address {
          key "ipv6-address-prefix-length";
          description
              "Configure IPv6 address";
          leaf ipv6-address-prefix-length {
            type string;
            description
                "ipv6-address x:x:x:x:x:x:x:x (eight 16-bit pieces) 
                 x:x:x:x:x:x:d.d.d.d 
                 x [0..FFFF]H 
                 d [0..255]D 
                 prefix-length [32..127]";
          } //ipv6-address-prefix-length

          leaf pd {
            type boolean;
          } //pd

          leaf wan-host {
            type boolean;
          } //wan-host

          leaf track-srrp {
            type uint32 {
              range "1..4294967295";
            }
          } //track-srrp

          leaf holdup-time {
            type uint32 {
              range "100..5000";
            }
          } //holdup-time

        } //list address

        leaf allow-multiple-wan-addresses {
          type boolean;
          description
              "Allow subscriber hosts with multiple WAN addresses";
        }

        leaf allow-unmatching-prefixes {
          type boolean;
          description
              "Allow subscriber hosts without a matching prefix";
        }

        container default-dns {
          description
              "Configure the default DNS server address";
          leaf ipv6-address {
            type inet:ipv6-address;
            description
                "Attribute ipv6-address for default-dns";
          } //ipv6-address

          leaf secondary {
            type inet:ipv6-address;
            description
                "ipv6-address";
          } //secondary

        } //container default-dns

        container delegated-prefix-length {
          description
              "Configure IPv6 delegated prefix length";
          leaf bits {
            type uint32 {
              range "48..64";
            }
          } //bits

          leaf variable {
            type boolean;
          } //variable

        } //container delegated-prefix-length

        leaf ipoe-bridged-mode {
          type boolean;
          description
              "Enable/Disable IPv6 IPoE Bridged Mode";
        }

        container link-local-address {
          description
              "Configure link-local address";
          leaf ipv6-address {
            type string;
            description
                "Attribute ipv6-address for link-local-address";
          } //ipv6-address

        } //container link-local-address

        container dhcp6 {
          presence
              "Configure IPv6 DHCP parameters";
          leaf override-slaac {
            type boolean;
            description
                "Configure if the WAN address offered by dhcp should overwrite the WAN address 
                 acquired from SLAAC";
          }

          container pd-managed-route {
            description
                "Enable installation of dhcp6 delegated prefixes as managed routes";
            leaf next-hop {
              type enumeration {
                enum ipv4;
                enum ipv6;
              }
            } //next-hop

          } //container pd-managed-route

          container python-policy {
            description
                "Configure the Python policy";
            leaf name {
              type string {
                length "1..32";
              }
            } //name

          } //container python-policy

          container proxy-server {
            presence
                "Configure IPv6 DHCP proxy-server parameters";
            container client-applications {
              description
                  "Configure the set of DHCP6 proxy-server client-applications";
              leaf dhcp {
                type boolean;
              } //dhcp

              leaf ppp {
                type boolean;
              } //ppp

            } //container client-applications

            container preferred-lifetime {
              description
                  "Time for prefix to remain preferred on this interface";
              leaf days {
                type uint32 {
                  range "0..49710";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
                description
                    "keyword";
              } //infinite

            } //container preferred-lifetime

            container rebind-timer {
              description
                  "Set the rebind timer (T2) for this interface";
              leaf days {
                type uint32 {
                  range "0..14";
                }
              } //days

              leaf hrs {
                type uint32 {
                  range "0..23";
                }
              } //hrs

              leaf min {
                type uint32 {
                  range "0..59";
                }
              } //min

              leaf sec {
                type uint32 {
                  range "0..59";
                }
              } //sec

            } //container rebind-timer

            container renew-timer {
              description
                  "Set the renew timer (T1) for this interface";
              leaf days {
                type uint32 {
                  range "0..7";
                }
              } //days

              leaf hrs {
                type uint32 {
                  range "0..23";
                }
              } //hrs

              leaf min {
                type uint32 {
                  range "0..59";
                }
              } //min

              leaf sec {
                type uint32 {
                  range "0..59";
                }
              } //sec

            } //container renew-timer

            container server-id {
              description
                  "Configure the DUID";
              leaf duid-ll {
                type boolean;
                description
                    "keyword";
              } //duid-ll

              leaf duid-en {
                type boolean;
                description
                    "keyword";
              } //duid-en

              leaf string {
                type string {
                  length "1..58";
                }
              } //string

              leaf hex {
                type string {
                  length "1..118";
                }
                description
                    "[0x0..0xFFFFFFFF...(max 116 hex nibbles)]";
              } //hex

            } //container server-id

            leaf shutdown {
              type boolean;
              description
                  "Administratively enable/disable DHCPv6 proxy-server";
            }

            container valid-lifetime {
              description
                  "Time for prefix to remain valid on this interface";
              leaf days {
                type uint32 {
                  range "0..49710";
                }
              } //days

              leaf hrs {
                type uint32 {
                  range "0..23";
                }
              } //hrs

              leaf min {
                type uint32 {
                  range "0..59";
                }
              } //min

              leaf sec {
                type uint32 {
                  range "0..59";
                }
              } //sec

              leaf infinite {
                type boolean;
                description
                    "keyword";
              } //infinite

            } //container valid-lifetime

          } //container proxy-server

          container relay {
            presence
                "Configure IPv6 DHCP relay parameters";
            container client-applications {
              description
                  "Configure the set of DHCP6 relay client-applications";
              leaf dhcp {
                type boolean;
              } //dhcp

              leaf ppp {
                type boolean;
              } //ppp

            } //container client-applications

            container description {
              description
                  "Description for DHCPv6 relay";
              leaf description-string {
                type string {
                  length "1..80";
                }
              } //description-string

            } //container description

            container link-address {
              description
                  "Configure the link address of the DHCPv6 relay messages";
              leaf ipv6-address {
                type inet:ipv6-address;
                description
                    "ipv6-address x:x:x:x:x:x:x:x (eight 16-bit pieces) 
                     x:x:x:x:x:x:d.d.d.d 
                     x [0..FFFF]H 
                     d [0..255]D";
              } //ipv6-address

            } //container link-address

            container server {
              description
                  "Configure the DHCPv6 server IPv6 address";
              leaf-list ipv6-address {
                type string;
                max-elements 8;
                description
                    "Attribute ipv6-address for server";
              } //ipv6-address

            } //container server

            leaf shutdown {
              type boolean;
              description
                  "Administratively enable/disable DHCPv6 relay";
            }

            container source-address {
              description
                  "Configure the source IPv6 address of the DHCPv6 relay messages";
              leaf ipv6-address {
                type inet:ipv6-address;
                description
                    "ipv6-address x:x:x:x:x:x:x:x (eight 16-bit pieces) 
                     x:x:x:x:x:x:d.d.d.d 
                     x [0..FFFF]H 
                     d [0..255]D";
              } //ipv6-address

            } //container source-address

            container advertise-selection {
              description
                  "Configure the DHCP6 advertise selection attributes";
              container solicit-delay {
                description
                    "Configure the DHCP6 solicit delay";
                leaf deci-seconds {
                  type uint32 {
                    range "1..100";
                  }
                } //deci-seconds

              } //container solicit-delay

              container client-mac {
                description
                    "Configure the DHCP6 client-mac";
                leaf client-mac-id {
                  type enumeration {
                    enum even;
                    enum odd;
                  }
                } //client-mac-id

                container solicit-delay {
                  description
                      "Configure the DHCP6 client-mac solicit delay";
                  leaf deci-seconds {
                    type uint32 {
                      range "1..100";
                    }
                  } //deci-seconds

                } //container solicit-delay

                container preference-option {
                  presence
                      "Configure the DHCP6 client-mac preference option";
                  container value {
                    description
                        "Configure the DHCP6 client-mac preference option";
                    leaf value-id {
                      type uint32 {
                        range "0..255";
                      }
                    } //value-id

                  } //container value

                } //container preference-option

              } //container client-mac

              container preference-option {
                presence
                    "Configure the DHCP6 preference option";
                container value {
                  description
                      "Configure the DHCP6 preference option";
                  leaf value-id {
                    type uint32 {
                      range "0..255";
                    }
                  } //value-id

                } //container value

              } //container preference-option

              list server {
                key "ipv6-address";
                description
                    "Configure the DHCP6 server";
                leaf ipv6-address {
                  type inet:ipv6-address;
                } //ipv6-address

                container solicit-delay {
                  description
                      "Configure the DHCP6 server solicit delay";
                  leaf deci-seconds {
                    type uint32 {
                      range "1..100";
                    }
                  } //deci-seconds

                } //container solicit-delay

                container preference-option {
                  presence
                      "Configure the DHCP6 server preference option";
                  container value {
                    description
                        "Configure the DHCP6 server preference option";
                    leaf value-id {
                      type uint32 {
                        range "0..255";
                      }
                    } //value-id

                  } //container value

                } //container preference-option

              } //list server

            } //container advertise-selection

          } //container relay

        } //container dhcp6

        container router-advertisements {
          presence
              "Configure IPv6 router advertisements";
          container current-hop-limit {
            description
                "Set the hop-limit to be advertised";
            leaf limit {
              type uint16 {
                range "0..255";
              }
              default 64;
            } //limit

          } //container current-hop-limit

          container force-mcast {
            description
                "Configure multicast router advertisements";
            leaf ip {
              type boolean;
            } //ip

            leaf mac {
              type boolean;
            } //mac

          } //container force-mcast

          leaf managed-configuration {
            type boolean;
            description
                "Set/reset managed address configuration flag";
          }

          container max-advertisement {
            description
                "Set the maximum advertisement interval";
            leaf seconds {
              type uint32 {
                range "900..1800";
              }
              default 1800;
            } //seconds

          } //container max-advertisement

          container min-advertisement {
            description
                "Set the minimum advertisement interval";
            leaf seconds {
              type uint32 {
                range "900..1350";
              }
              default 900;
            } //seconds

          } //container min-advertisement

          container mtu {
            description
                "Set the advertised MTU value";
            leaf bytes {
              type uint32 {
                range "1280..9212";
              }
              default 1280;
            } //bytes

          } //container mtu

          leaf other-stateful-configuration {
            type boolean;
            description
                "Set/reset other-stateful-configuration flag";
          }

          container reachable-time {
            description
                "Set the reachable time for advertisements";
            leaf milli-seconds {
              type uint32 {
                range "0..3600000";
              }
              default 0;
            } //milli-seconds

          } //container reachable-time

          container retransmit-time {
            description
                "Set the retransmit time for advertisements";
            leaf milli-seconds {
              type uint32 {
                range "0..1800000";
              }
              default 0;
            } //milli-seconds

          } //container retransmit-time

          container router-lifetime {
            description
                "Set the router lifetime";
            leaf seconds {
              type uint32 {
                range "2700..9000";
              }
              default 4500;
            } //seconds

            leaf no-default-router {
              type boolean;
            } //no-default-router

          } //container router-lifetime

          leaf shutdown {
            type boolean;
            description
                "Administratively enable/disable router advertisements";
          }

          container dns-options {
            presence
                "Set/reset DNS options";
            leaf include-dns {
              type boolean;
              description
                  "Set/reset inclusion of the RDNSS server option 25";
            }

            container rdnss-lifetime {
              description
                  "Maximum time the RDNSS address is valid";
              leaf seconds {
                type uint32 {
                  range "900..3600";
                }
              } //seconds

              leaf infinite {
                type boolean;
              } //infinite

            } //container rdnss-lifetime

          } //container dns-options

          container prefix-options {
            presence
                "Set/reset prefix options";
            leaf autonomous {
              type boolean;
              description
                  "Enable/disable prefix for stateless address autoconfiguration";
            }

            leaf on-link {
              type boolean;
              description
                  "Enable/disable assigning of the prefix to an interface on the specified link";
            }

            container preferred-lifetime {
              description
                  "Time for prefix to remain preferred";
              leaf seconds {
                type uint32;
                default 3600;
              } //seconds

              leaf infinite {
                type boolean;
              } //infinite

            } //container preferred-lifetime

            container valid-lifetime {
              description
                  "Time for prefix to remain valid";
              leaf seconds {
                type uint32;
                default 3600;
              } //seconds

              leaf infinite {
                type boolean;
              } //infinite

            } //container valid-lifetime

          } //container prefix-options

        } //container router-advertisements

        container router-solicit {
          presence
              "Configure parameters used for router-solicit based authentication";
          container inactivity-timer {
            description
                "Configure the time before an inactive host is removed";
            leaf infinite {
              type boolean;
            } //infinite

            leaf days {
              type uint32 {
                range "0..365";
              }
            } //days

            leaf hrs {
              type uint32 {
                range "0..23";
              }
            } //hrs

            leaf min {
              type uint32 {
                range "0..59";
              }
            } //min

            leaf sec {
              type uint32 {
                range "0..59";
              }
            } //sec

          } //container inactivity-timer

        } //container router-solicit

        container subscriber-prefixes {
          description
              "Configure IPv6 subscriber prefixes";
          list prefix {
            key "ipv6-address-prefix-length";
            description
                "Configure IPv6 subscriber prefix";
            leaf ipv6-address-prefix-length {
              type string;
              description
                  "ipv6-address x:x:x:x:x:x:x:x (eight 16-bit pieces) 
                   x:x:x:x:x:x:d.d.d.d 
                   x [0..FFFF]H 
                   d [0..255]D 
                   prefix-length [32..127]";
            } //ipv6-address-prefix-length

            leaf pd {
              type boolean;
            } //pd

            leaf wan-host {
              type boolean;
            } //wan-host

            leaf track-srrp {
              type uint32 {
                range "1..4294967295";
              }
            } //track-srrp

            leaf holdup-time {
              type uint32 {
                range "100..5000";
              }
            } //holdup-time

          } //list prefix

        } //container subscriber-prefixes

      } //container ipv6

      container local-address-assignment {
        description
            "Configures local address assignment";
        container client-application {
          description
              "Configure the client applications";
          leaf ppp-v4 {
            type boolean;
          } //ppp-v4

          leaf ipoe-v4 {
            type boolean;
          } //ipoe-v4

        } //container client-application

        container default-pool {
          description
              "Configure the default pool";
          leaf pool-name {
            type string {
              length "1..32";
            }
          } //pool-name

          leaf secondary {
            type string {
              length "1..32";
            }
          } //secondary

        } //container default-pool

        container server {
          description
              "Configure the DHCP server";
          leaf server-name {
            type string;
          } //server-name

        } //container server

        leaf shutdown {
          type boolean;
          description
              "Administratively enable/disable local address assignment";
        }

        container ipv6 {
          presence
              "Configures IPv6 local address assignment";
          container client-application {
            description
                "Configure the IPv6 client applications";
            leaf ppp-slaac {
              type boolean;
              description
                  "enable PPP hosts to request addresses from a local address server";
            } //ppp-slaac

            leaf ipoe-wan {
              type boolean;
              description
                  "enable DHCP_NA requests to request addresses from a local address server";
            } //ipoe-wan

            leaf ipoe-slaac {
              type boolean;
              description
                  "enable IPoE hosts to request SLAAC prefixes from a local address server";
            } //ipoe-slaac

          } //container client-application

          container server {
            description
                "Configure the DHCPv6 server";
            leaf server-name {
              type string;
            } //server-name

          } //container server

        } //container ipv6

      } //container local-address-assignment

      container pppoe {
        presence
            "Configure PPPoE parameters";
        container description {
          description
              "Description for PPPoE";
          leaf description-string {
            type string {
              length "1..80";
            }
          } //description-string

        } //container description

        container session-limit {
          description
              "Configure the maximum number of PPPoE sessions";
          leaf session-limit {
            type int32 {
              range "1..262143";
            }
            description
                "Attribute session-limit for session-limit";
          } //session-limit

        } //container session-limit

        leaf shutdown {
          type boolean;
          description
              "Administratively enable/disable PPPoE";
        }

      } //container pppoe

      container wlan-gw {
        presence
            "Configure WLAN Gateway functions";
        container pool-manager {
          description
              "Configure WLAN Gateway pool manager";
          container watermarks {
            description
                "Configure the watermarks for the pool manager";
            leaf high {
              type uint32 {
                range "51..99";
              }
            } //high

            leaf low {
              type uint32 {
                range "50..98";
              }
            } //low

          } //container watermarks

          container wlan-gw-group {
            description
                "Configure the ISA WLAN-GW Group";
            leaf nat-group-id {
              type uint32 {
                range "1..4";
              }
            } //nat-group-id

          } //container wlan-gw-group

          container dhcpv6-client {
            description
                "Configure the DHCPv6 client for the pool manager";
            container lease-query {
              description
                  "Enable/disable lease query";
              leaf max-retry {
                type uint32 {
                  range "0..10";
                }
              } //max-retry

            } //container lease-query

            container server {
              description
                  "Configure the DHCPv6 server(s) used for requesting addresses";
              leaf-list ipv6-address {
                type inet:ipv6-address;
                max-elements 8;
              } //ipv6-address

            } //container server

            container source-ip {
              description
                  "Configure the source IP-address to be used by the DHCPv6 client";
              leaf ipv6-address {
                type inet:ipv6-address;
              } //ipv6-address

            } //container source-ip

            container dhcpv4-nat {
              description
                  "Configure DHCPv4 NAT for the DHCPv6 client";
              container link-addr {
                description
                    "Configure the link address of the relay header";
                leaf ipv6-address {
                  type inet:ipv6-address;
                } //ipv6-address

              } //container link-addr

              container pool-name {
                description
                    "Configure the pool name to be sent in the DHCPv6 messages";
                leaf name {
                  type string;
                } //name

              } //container pool-name

              leaf shutdown {
                type boolean;
                description
                    "Disable/enable DHCPv4 NAT";
              }

            } //container dhcpv4-nat

            container ia-na {
              description
                  "Configure IA-NA for the DHCPv6 client";
              container link-addr {
                description
                    "Configure the link address of the relay header";
                leaf ipv6-address {
                  type inet:ipv6-address;
                } //ipv6-address

              } //container link-addr

              container pool-name {
                description
                    "Configure the pool name to be sent in the DHCPv6 messages";
                leaf name {
                  type string;
                } //name

              } //container pool-name

              leaf shutdown {
                type boolean;
                description
                    "Disable/enable IA-NA";
              }

            } //container ia-na

            container slaac {
              description
                  "Configure SLAAC for the DHCPv6 client";
              container link-addr {
                description
                    "Configure the link address of the relay header";
                leaf ipv6-address {
                  type inet:ipv6-address;
                } //ipv6-address

              } //container link-addr

              container pool-name {
                description
                    "Configure the pool name to be sent in the DHCPv6 messages";
                leaf name {
                  type string;
                } //name

              } //container pool-name

              leaf shutdown {
                type boolean;
                description
                    "Disable/enable SLAAC";
              }

            } //container slaac

          } //container dhcpv6-client

        } //container pool-manager

        container redundancy {
          description
              "Configure WLAN Gateway redundancy";
          container export {
            description
                "Configure the route to export to the peer";
            leaf ip-prefix-length {
              type inet:ip-prefix;
              description
                  "Attribute ip-prefix/length for export";
            } //ip-prefix-length

          } //container export

          container monitor {
            description
                "Configure the peer route to monitor";
            leaf ip-prefix-length {
              type inet:ip-prefix;
              description
                  "Attribute ip-prefix/length for monitor";
            } //ip-prefix-length

          } //container monitor

          leaf shutdown {
            type boolean;
            description
                "Disable/enable redundancy";
          }

        } //container redundancy

      } //container wlan-gw

    } //list subscriber-interface

  } //grouping alu-conf-svc-vprn-subif-r13

} //module  alu-conf-svc-vprn-subif-r13
