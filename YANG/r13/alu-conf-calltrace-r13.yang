module alu-conf-calltrace-r13 {
  yang-version "1";

  namespace "urn:alcatel-lucent.com:sros:ns:yang:conf-calltrace-r13";

  prefix "conf-calltrace-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Call Trace on SR OS based routers. 
       
       Copyright 2014-2015 Alcatel-Lucent, 2016 Nokia. All rights reserved. 
       Reproduction of this document is authorized on the condition that the 
       foregoing copyright notice is included. 
       
       This alu-conf-calltrace-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-04-20";

  grouping alu-conf-calltrace-r13 {
    container call-trace {
      description
          "Configure Call Trace";
      leaf buffering {
        type boolean;
        description
            "Configure call trace buffering";
      }

      container max-files-number {
        description
            "Configure max. number of trace log files stored on all cflashes";
        leaf number {
          type uint32 {
            range "1..1024";
          }
          default 200;
          description
              "[1..1024] - Default: 200";
        } //number

      } //container max-files-number

      container primary-cf {
        description
            "Select primary cflash to be used for call trace logs storage";
        leaf cflash-id {
          type enumeration {
            enum cf1;
            enum cf2;
          }
          default "cf1";
          description
              "cf1|cf2 - Default:cf1";
        } //cflash-id

      } //container primary-cf

      container location {
        description
            "Configure local storage of call trace logs";
        leaf location-id {
          type enumeration {
            enum cf1;
            enum cf2;
          }
        } //location-id

        leaf disable {
          type boolean;
          description
              "Disable storing of call trace log files on the cflash";
        }

        container size-limit {
          description
              "Configure maximum data volume for all trace log files on the cflash";
          leaf limit-value {
            type uint32 {
              range "1..65536";
            }
            default 1000;
            description
                "[1..65536] in MB - Default: 1000";
          } //limit-value

        } //container size-limit

      } //container location

      list trace-profile {
        key "profile-name";
        description
            "Configure a call trace trace-profile";
        leaf profile-name {
          type string;
        } //profile-name

        container applications {
          description
              "Specify applications to trace";
          leaf-list application {
            type enumeration {
              enum connectivity-management;
              enum gx;
              enum gy;
              enum nasreq;
              enum radius-auth;
              enum radius-acct;
              enum python;
              enum ludb;
              enum msap;
              enum portal-traffic;
              enum ppp-event;
            }
            max-elements 20;
          } //application

          leaf all {
            type boolean;
            description
                "Enable all applications except ppp-event";
          } //all

          leaf-list applications-id {
            type enumeration {
              enum mobility;
            }
            max-elements 4;
            status "obsolete";
          } //applications-id

        } //container applications

        leaf debug-output {
          type boolean;
          description
              "Enable/disable output to the debug log";
        }

        container description {
          description
              "Description for this trace-profile";
          leaf description-string {
            type string {
              length "1..80";
            }
          } //description-string

        } //container description

        container events {
          description
              "Enable/disable tracing of events";
          leaf events-id {
            type enumeration {
              enum none;
              enum public-only;
              enum all;
            }
          } //events-id

        } //container events

        container live-output {
          description
              "Configure live output destination for trace logs";
          leaf ip-address-fqdn {
            type string;
            description
                "Attribute ip-address|fqdn for live-output";
          } //ip-address-fqdn

          leaf port {
            type int32 {
              range "1..65535";
            }
            default 29770;
            description
                "[1..65535] UDP - Default: 29770";
          } //port

          leaf router {
            type boolean;
          } //router

          leaf router-instance {
            type string {
              length "1..32";
            }
            default "Base";
            description
                "Attribute router-instance for live-output";
          } //router-instance

          leaf service-name {
            type string;
          } //service-name

        } //container live-output

        container size-limit {
          description
              "Configure maximum data volume for trace logs";
          leaf limit-value {
            type uint32 {
              range "1..1000";
            }
            default 10;
            description
                "[1..1000] in MB - Default: 10";
          } //limit-value

        } //container size-limit

        container time-limit {
          description
              "Configure maximum duration for trace logs";
          leaf limit-value {
            type uint32 {
              range "1..604800";
            }
            default 86400;
            description
                "[1..604800] in seconds - Default: 86400";
          } //limit-value

        } //container time-limit

      } //list trace-profile

    } //container call-trace

  } //grouping alu-conf-calltrace-r13

} //module  alu-conf-calltrace-r13
