module alu-conf-subscrmgmt-r13 {
  yang-version "1";

  namespace "urn:alcatel-lucent.com:sros:ns:yang:conf-subscrmgmt-r13";

  prefix "conf-subscrmgmt-r13";

  import alu-conf-submgmt-ludb-r13 {
    prefix "conf-submgmt-ludb-r13";
  }
  import alu-conf-submgmt-wlangw-r13 {
    prefix "conf-submgmt-wlangw-r13";
  }
  import alu-conf-svc-chain-r13 {
    prefix "conf-svc-chain-r13";
  }
  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure subscriber management on SR OS 
       based routers. 
       
       Copyright 2014-2015 Alcatel-Lucent, 2016 Nokia. All rights reserved. 
       Reproduction of this document is authorized on the condition that the 
       foregoing copyright notice is included. 
       
       This alu-conf-subscrmgmt-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-03-12";

  grouping alu-conf-subscrmgmt-r13 {
    container subscriber-mgmt {
      description
          "Configure subscriber management";
      list accu-stats-policy {
        key "policy-name";
        description
            "Configure a policy for per-subscriber accumulated statistics";
        leaf policy-name {
          type string;
        } //policy-name

        container description {
          description
              "Configure a description";
          leaf description-string {
            type string {
              length "1..80";
            }
          } //description-string

        } //container description

        list entry {
          key "direction type id";
          description
              "Configure a policy entry";
          leaf direction {
            type enumeration {
              enum egress;
              enum ingress;
            }
          } //direction

          leaf type {
            type enumeration {
              enum queue;
              enum policer;
            }
          } //type

          leaf id {
            type uint32 {
              range "1..63";
            }
          } //id

        } //list entry

      } //list accu-stats-policy

      container ancp {
        description
            "Configure Access Node Control Protocol parameters";
        list ancp-policy {
          key "policy-name";
          description
              "Configure an ANCP policy";
          leaf policy-name {
            type string {
              length "1..32";
            }
          } //policy-name

          container egress {
            description
                "Configure egress policy parameters";
            container rate-adjustment {
              description
                  "Configure the egress rate adjustment";
              leaf adjusted-percent {
                type uint32 {
                  range "1..200";
                }
              } //adjusted-percent

            } //container rate-adjustment

            container rate-modify {
              description
                  "Configure the egress rate modify scheduler";
              leaf scheduler {
                type string {
                  length "1..32";
                }
              } //scheduler

              leaf agg-rate-limit {
                type boolean;
              } //agg-rate-limit

            } //container rate-modify

            container rate-monitor {
              description
                  "Configure the egress rate monitor level";
              leaf kilobit-per-second {
                type uint32;
              } //kilobit-per-second

              leaf alarm {
                type boolean;
              } //alarm

            } //container rate-monitor

            container rate-reduction {
              description
                  "Configure the egress rate reduction";
              leaf kilobit-per-second {
                type uint32;
              } //kilobit-per-second

            } //container rate-reduction

          } //container egress

          container ingress {
            description
                "Configure ingress policy parameters";
            container rate-adjustment {
              description
                  "Configure the ingress rate adjustment";
              leaf adjusted-percent {
                type uint32 {
                  range "1..200";
                }
              } //adjusted-percent

            } //container rate-adjustment

            container rate-modify {
              description
                  "Configure the ingress rate modify scheduler";
              leaf scheduler {
                type string {
                  length "1..32";
                }
              } //scheduler

            } //container rate-modify

            container rate-monitor {
              description
                  "Configure the ingress rate monitor level";
              leaf kilobit-per-second {
                type uint32;
              } //kilobit-per-second

              leaf alarm {
                type boolean;
              } //alarm

            } //container rate-monitor

            container rate-reduction {
              description
                  "Configure the ingress rate reduction";
              leaf kilobit-per-second {
                type uint32;
              } //kilobit-per-second

            } //container rate-reduction

          } //container ingress

          container port-down {
            presence
                "Configure actions taken on port-down";
            container disable-shcv {
              description
                  "Enable/disable Subscr Host Connectivity Verification";
              leaf alarm {
                type boolean;
              } //alarm

              leaf hold-time {
                type uint32 {
                  range "0..7200";
                }
              } //hold-time

            } //container disable-shcv

          } //container port-down

        } //list ancp-policy

        container ancp-static-map {
          description
              "Configure a static ANCP name map";
          list entry {
            key "key";
            description
                "Configure an ANCP name";
            leaf key {
              type string {
                length "1..63";
              }
            } //key

            leaf sap {
              type string;
              description
                  "Attribute sap-id for entry";
            } //sap

            leaf ancp-policy {
              type string {
                length "1..32";
              }
            } //ancp-policy

            leaf customer {
              type uint32 {
                range "1..2147483647";
              }
            } //customer

            leaf multi-service-site {
              type string {
                length "1..32";
              }
            } //multi-service-site

          } //list entry

        } //container ancp-static-map

      } //container ancp

      list authentication-policy {
        key "name";
        description
            "Configure a subscriber authentication policy";
        leaf name {
          type string {
            length "1..32";
          }
        } //name

        leaf accept-authorization-change {
          type boolean;
          description
              "Enable/disable authorization change";
        }

        container accept-script-policy {
          description
              "Configure RADIUS script policy to modify Access-Accept";
          leaf policy-name {
            type string {
              length "1..32";
            }
          } //policy-name

        } //container accept-script-policy

        container coa-script-policy {
          description
              "Configure RADIUS script policy to modify Change-of-Authorization";
          leaf policy-name {
            type string {
              length "1..32";
            }
          } //policy-name

        } //container coa-script-policy

        container description {
          description
              "Description for authentication policy";
          leaf description-string {
            type string {
              length "1..80";
            }
          } //description-string

        } //container description

        container fallback-action {
          description
              "Configure the action when no RADIUS server is available";
          leaf accept {
            type boolean;
          } //accept

          leaf user-db {
            type string {
              length "1..32";
            }
          } //user-db

          leaf force-probing {
            type boolean;
            description
                "keyword, enable/disable force-probing";
          } //force-probing

        } //container fallback-action

        container gtp-user-name {
          description
              "Configure the GTP user name format";
          leaf gtp-format {
            type enumeration {
              enum imsi;
              enum imsi-apn;
            }
          } //gtp-format

        } //container gtp-user-name

        container password {
          description
              "Configure the password used in the RADIUS request";
          leaf password {
            type string {
              length "1..500";
            }
            description
                "secret-key - [64 chars max] 
                 hash-key 
                 hash2-key 
                 custom-key";
          } //password

          leaf hash-hash2-custom {
            type enumeration {
              enum hash;
              enum hash2;
              enum custom;
            }
            description
                "keywords - specify hashing scheme";
          } //hash-hash2-custom

        } //container password

        container ppp-user-name {
          description
              "Configure the PPP user name operation";
          leaf append {
            type string {
              length "1..128";
            }
            description
                "max 128 chars, no @ needed";
          } //append

          leaf default-domain {
            type string {
              length "1..128";
            }
            description
                "domain-name";
          } //default-domain

          leaf replace {
            type string {
              length "1..128";
            }
            description
                "domain-name";
          } //replace

          leaf strip {
            type boolean;
          } //strip

        } //container ppp-user-name

        container pppoe-access-method {
          description
              "Configure the PPPoE access method";
          leaf pppoe-access-method-id {
            type enumeration {
              enum none;
              enum padi;
              enum pap-chap;
            }
          } //pppoe-access-method-id

        } //container pppoe-access-method

        container radius-server-policy {
          description
              "Configure a RADIUS server policy for this policy";
          leaf radius-server-policy-name {
            type string {
              length "1..32";
            }
          } //radius-server-policy-name

        } //container radius-server-policy

        leaf re-authentication {
          type boolean;
          description
              "Enable/disable re-authentication on IPOE renewal";
        }

        container request-script-policy {
          description
              "Configure RADIUS script policy to modify Access-Request";
          leaf policy-name {
            type string {
              length "1..32";
            }
          } //policy-name

        } //container request-script-policy

        container send-acct-stop-on-fail {
          description
              "Configure if and when to send acct-stop on failure";
          leaf on-request-failure {
            type boolean;
          } //on-request-failure

          leaf on-reject {
            type boolean;
            description
                "keyword - send acct-stop on access-reject";
          } //on-reject

          leaf on-accept-failure {
            type boolean;
            description
                "keyword - send acct-stop on host authentication and instantiation failure 
                 after access-accept";
          } //on-accept-failure

        } //container send-acct-stop-on-fail

        container user-name-format {
          description
              "Configure the user name format in RADIUS message";
          leaf format {
            type enumeration {
              enum ascii-converted-circuit-id;
              enum ascii-converted-tuple;
              enum circuit-id;
              enum dhcp-client-vendor-opts;
              enum mac;
              enum mac-giaddr;
              enum ppp-user-name;
              enum tuple;
            }
          } //format

          leaf append {
            type boolean;
          } //append

          leaf default-domain {
            type string {
              length "1..128";
            }
            description
                "domain-name";
          } //default-domain

          leaf strip {
            type boolean;
          } //strip

          leaf replace {
            type string {
              length "1..128";
            }
            description
                "domain-name";
          } //replace

          leaf domain-name {
            type string {
              length "1..128";
            }
            description
                "max 128 chars, no @ needed";
          } //domain-name

          leaf domain-name-1 {
            type boolean;
          } //domain-name-1

          leaf mac-format {
            type string {
              length "1..7";
            }
            description
                "(only when format is dhcp-client-vendor-opts) 
                 like ab: for 00:0c:f1:99:85:b8 
                 or XY- for 00-0C-F1-99-85-B8 
                 or mmmm. for 0002.03aa.abff 
                 or xx for 000cf19985b8";
          } //mac-format

        } //container user-name-format

        container include-radius-attribute {
          presence
              "Configure applicable RADIUS attributes";
          leaf access-loop-options {
            type boolean;
            description
                "Enable/disable generation of the DSL Forum access loop characteristics RADIUS 
                 attributes";
          }

          container acct-session-id {
            description
                "Enable/disable generation of the Acct-Session-Id RADIUS attribute";
            leaf session-id-type {
              type enumeration {
                enum host;
                enum session;
              }
            } //session-id-type

          } //container acct-session-id

          leaf apn {
            type boolean;
            description
                "Enable/disable generation of the APN RADIUS attribute";
          }

          leaf called-station-id {
            type boolean;
            description
                "Enable/disable generation of the called-station-id RADIUS attribute";
          }

          container calling-station-id {
            description
                "Enable/disable generation of the calling-station-id RADIUS attribute";
            leaf calling-station-id-id {
              type enumeration {
                enum llid;
                enum mac;
                enum remote-id;
                enum sap-id;
                enum sap-string;
              }
            } //calling-station-id-id

          } //container calling-station-id

          leaf circuit-id {
            type boolean;
            description
                "Enable/disable generation of the agent-circuit-id RADIUS attribute";
          }

          leaf dhcp-options {
            type boolean;
            description
                "Enable/disable generation of the dhcp-options RADIUS attribute";
          }

          leaf dhcp-vendor-class-id {
            type boolean;
            description
                "Enable/disable generation of the dhcp-vendor-class-id RADIUS attribute";
          }

          leaf dhcp6-options {
            type boolean;
            description
                "Enable/disable generation of the dhcp6-options RADIUS attribute";
          }

          leaf gprs-negotiated-qos-profile {
            type boolean;
            description
                "Enable/disable generation of the GPRS Negotiated QoS Profile RADIUS attribute";
          }

          leaf imei {
            type boolean;
            description
                "Enable/disable generation of the IMEI RADIUS attribute";
          }

          leaf mac-address {
            type boolean;
            description
                "Enable/disable generation of the client MAC address RADIUS attribute";
          }

          leaf msisdn {
            type boolean;
            description
                "Enable/disable generation of the MSISDN RADIUS attribute";
          }

          leaf nas-identifier {
            type boolean;
            description
                "Enable/disable generation of the NAS-Identifier RADIUS attribute";
          }

          container nas-port {
            description
                "Enable/disable include of the NAS-Port attribute";
            leaf binary-spec {
              type string {
                length "1..255";
              }
              description
                  "Attribute binary-spec for nas-port";
            } //binary-spec

          } //container nas-port

          container nas-port-id {
            description
                "Enable/disable generation of the NAS-Port-Id RADIUS attribute";
            leaf prefix-string {
              type string {
                length "1..8";
              }
            } //prefix-string

            leaf suffix {
              type enumeration {
                enum circuit-id;
                enum remote-id;
              }
            } //suffix

          } //container nas-port-id

          container nas-port-type {
            description
                "Enable/disable generation of the NAS-Port-Type RADIUS attribute";
            leaf nas-port-type-id {
              type uint8;
            } //nas-port-type-id

          } //container nas-port-type

          leaf pppoe-service-name {
            type boolean;
            description
                "Enable/disable generation of the pppoe-service-name RADIUS attribute";
          }

          leaf rat-type {
            type boolean;
            description
                "Enable/disable generation of the RAT Type RADIUS attribute";
          }

          leaf remote-id {
            type boolean;
            description
                "Enable/disable generation of the agent-remote-id RADIUS attribute";
          }

          leaf sap-session-index {
            type boolean;
            description
                "Enable/disable generation of the per-SAP unique session index";
          }

          leaf tunnel-server-attrs {
            type boolean;
            description
                "Enable/disable generation of the tunnel-server-attrs RADIUS attribute";
          }

          leaf uli {
            type boolean;
            description
                "Enable/disable generation of the ULI RADIUS attribute";
          }

          leaf wifi-num-attached-ues {
            type boolean;
            description
                "Enable/disable including the Alc-Num-Attached-UEs RADIUS attribute";
          }

          leaf wifi-ssid-vlan {
            type boolean;
            description
                "Enable/disable including the per-SSID VLAN ID in Alc-Wlan-SSID-VLAN";
          }

          leaf xconnect-tunnel-home-address {
            type boolean;
            description
                "Enable/disable generation of the Cross Connect Tunnel Home Address RADIUS 
                 attribute";
          }

        } //container include-radius-attribute

        container radius-authentication-server {
          description
              "Configure RADIUS server for this policy";
          container access-algorithm {
            description
                "Configure the algorithm used to access the set of RADIUS servers";
            leaf direct-round-robin {
              type enumeration {
                enum direct;
                enum round-robin;
              }
              description
                  "keywords";
            } //direct-round-robin

          } //container access-algorithm

          container hold-down-time {
            description
                "Hold time before re-using a RADIUS server that was down";
            leaf seconds {
              type uint32 {
                range "30..900";
              }
            } //seconds

          } //container hold-down-time

          container retry {
            description
                "Number of retries for contacting the RADIUS server";
            leaf count {
              type uint32 {
                range "1..256";
              }
            } //count

          } //container retry

          container router {
            description
                "Configure the routing instance";
            leaf router-instance {
              type string {
                length "1..32";
              }
              default "Base";
              description
                  "Attribute router-instance for router";
            } //router-instance

            leaf service-name {
              type string;
            } //service-name

          } //container router

          list server {
            key "server-index";
            description
                "Add/remove a RADIUS server";
            leaf server-index {
              type uint32 {
                range "1..16";
              }
              description
                  "[1..16] max 5 authentication servers";
            } //server-index

            leaf address {
              type inet:ip-address;
            } //address

            leaf secret {
              type string {
                length "1..500";
              }
              description
                  "secret-key - [20 chars max] 
                   hash-key 
                   hash2-key 
                   custom-key";
            } //secret

            leaf hash-hash2-custom {
              type enumeration {
                enum hash;
                enum hash2;
                enum custom;
              }
              description
                  "keywords - specify hashing scheme";
            } //hash-hash2-custom

            leaf port {
              type uint16 {
                range "1..65535";
              }
            } //port

            leaf coa-only {
              type boolean;
              description
                  "Change-of-Authorization Messages only";
            } //coa-only

            leaf pending-requests-limit {
              type uint32 {
                range "1..4096";
              }
            } //pending-requests-limit

          } //list server

          container source-address {
            description
                "Source address of the RADIUS message";
            leaf ip-address {
              type inet:ip-address;
            } //ip-address

          } //container source-address

          container timeout {
            description
                "Timeout for a response from the RADIUS server";
            leaf seconds {
              type uint32 {
                range "1..340";
              }
            } //seconds

          } //container timeout

        } //container radius-authentication-server

      } //list authentication-policy

      container auto-sub-id-key {
        description
            "Configure auto-generated subscriber identification keys";
        leaf implicit-generation {
          type boolean;
          description
              "Configure if this system implicitly generates a subscriber identifier if none 
               is provided by other means";
        }

        container ipoe-sub-id-key {
          description
              "Configure auto-generated sub-id keys for IPoE hosts";
          leaf-list sub-id-key {
            type enumeration {
              enum mac;
              enum sap-id;
              enum circuit-id;
              enum remote-id;
              enum dual-stack-remote-id;
            }
            max-elements 4;
          } //sub-id-key

        } //container ipoe-sub-id-key

        container ppp-sub-id-key {
          description
              "Configure auto-generated sub-id keys for PPP hosts";
          leaf-list sub-id-key {
            type enumeration {
              enum mac;
              enum sap-id;
              enum circuit-id;
              enum remote-id;
              enum session-id;
            }
            max-elements 5;
          } //sub-id-key

        } //container ppp-sub-id-key

      } //container auto-sub-id-key

      list bgp-peering-policy {
        key "policy-name";
        description
            "Create/Configure or delete a BGP peering policy";
        leaf policy-name {
          type string {
            length "1..32";
          }
        } //policy-name

        leaf advertise-inactive {
          type boolean;
          description
              "Enable/disable advertising of inactive BGP routes to other BGP peers";
        }

        leaf aggregator-id-zero {
          type boolean;
          description
              "Enable/disable setting the service vprn ID to 0 in the aggregator path 
               attribute";
        }

        leaf as-override {
          type boolean;
          description
              "Enable/disable BGP AS override feature";
        }

        container auth-keychain {
          description
              "Configure TCP authentication keychain to use for the session";
          leaf name {
            type string {
              length "1..32";
            }
            description
                "keychain-name (32 char max)";
          } //name

        } //container auth-keychain

        container authentication-key {
          description
              "Configure the BGP authentication key for the peer";
          leaf authentication-key-hash-key {
            type string {
              length "1..500";
            }
            description
                "authentication-key - [255 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        container cluster {
          description
              "Configure the cluster ID for a route reflector server";
          leaf cluster-id {
            type inet:ip-address;
            description
                "expressed in dotted decimal format (a.b.c.d)";
          } //cluster-id

        } //container cluster

        container connect-retry {
          description
              "Configure the BGP Connect Retry timer value";
          leaf seconds {
            type uint32 {
              range "1..65535";
            }
          } //seconds

        } //container connect-retry

        leaf damping {
          type boolean;
          description
              "Enable/disable BGP route damping for learned routes as defined within the 
               route policy";
        }

        container description {
          description
              "Create a textual description stored in the configuration file";
          leaf description-string {
            type string {
              length "1..80";
            }
          } //description-string

        } //container description

        leaf disable-4byte-asn {
          type boolean;
          description
              "Enable/disable the advertisement of 4-byte ASN capability";
        }

        leaf disable-client-reflect {
          type boolean;
          description
              "Enable/disable the reflection of routes by the route reflector";
        }

        container disable-communities {
          description
              "Configure BGP to disable sending communities";
          leaf standard {
            type boolean;
          } //standard

          leaf extended {
            type boolean;
          } //extended

        } //container disable-communities

        leaf disable-fast-external-failover {
          type boolean;
          description
              "Configure BGP fast external failover";
        }

        container export {
          description
              "Export route policies used to determine which routes are advertised";
          leaf-list policy-name {
            type string {
              length "1..32";
            }
            max-elements 15;
          } //policy-name

        } //container export

        container hold-time {
          description
              "Configure BGP hold time";
          leaf seconds {
            type string;
            description
                "<0|[3..65535]>";
          } //seconds

        } //container hold-time

        container import {
          description
              "Import route policies used to determine which routes are accepted";
          leaf-list policy-name {
            type string {
              length "1..32";
            }
            max-elements 15;
          } //policy-name

        } //container import

        container keepalive {
          description
              "Configure BGP keepalive timer";
          leaf seconds {
            type uint32 {
              range "0..21845";
            }
            default 30;
          } //seconds

        } //container keepalive

        container local-address {
          description
              "Configure the local ip address";
          leaf ip-address {
            type string;
            description
                "Attribute ip-address for local-address";
          } //ip-address

        } //container local-address

        container local-as {
          description
              "Add/remove a BGP virtual AS number";
          leaf as-number {
            type uint32 {
              range "1..4294967295";
            }
          } //as-number

          leaf private {
            type boolean;
          } //private

        } //container local-as

        container local-preference {
          description
              "Configure BGP local-preference attribute in incoming routes from all peers if 
               not specified";
          leaf local-preference {
            type uint32;
          } //local-preference

        } //container local-preference

        container loop-detect {
          description
              "Configure how the BGP peer session handles loop detection in the AS Path";
          leaf drop-peer-discard-route-ignore-loop-off {
            type enumeration {
              enum drop-peer;
              enum discard-route;
              enum ignore-loop;
              enum off;
            }
            description
                "keywords";
          } //drop-peer-discard-route-ignore-loop-off

        } //container loop-detect

        container med-out {
          description
              "Enable/disable advertising the Multi-Exit Discriminator (MED)";
          leaf number {
            type uint32;
          } //number

          leaf igp-cost {
            type boolean;
          } //igp-cost

        } //container med-out

        container min-as-origination {
          status "obsolete";
          description
              "Minimum interval at which a given path attribute is advertised to a peer";
          leaf seconds {
            type uint16 {
              range "2..255";
            }
          } //seconds

        } //container min-as-origination

        container min-route-advertisement {
          description
              "Minimum interval at which a given prefix is advertised to a peer";
          leaf seconds {
            type uint16 {
              range "1..255";
            }
            description
                "[1..255]";
          } //seconds

        } //container min-route-advertisement

        container multihop {
          description
              "TTL value entered in the IP header of packets sent to a peer";
          leaf ttl-value {
            type uint8 {
              range "1..255";
            }
          } //ttl-value

        } //container multihop

        leaf next-hop-self {
          type boolean;
          description
              "Configure the peer to always set the nexthop path attribute to itself when 
               advertising to a peer";
        }

        leaf passive {
          type boolean;
          description
              "Enable/disable passive mode for the BGP peer";
        }

        container peer-as {
          description
              "Configure the AS number for the remote peer";
          leaf as-number {
            type uint32 {
              range "1..4294967295";
            }
          } //as-number

        } //container peer-as

        container preference {
          description
              "Configure the route preference for routes learned from all peers";
          leaf preference {
            type uint16 {
              range "1..255";
            }
          } //preference

        } //container preference

        container prefix-limit {
          description
              "Maximum number of routes BGP can learn from the peers for this peer";
          leaf limit {
            type uint64 {
              range "1..4294967295";
            }
          } //limit

        } //container prefix-limit

        container remove-private {
          description
              "Remove private AS numbers from the AS Path before advertising to a peer";
          leaf limited {
            type boolean;
            description
                "keyword";
          } //limited

        } //container remove-private

        container ttl-security {
          description
              "Configure TTL security parameters for incoming packet";
          leaf min-ttl-value {
            type int32 {
              range "1..255";
            }
            description
                "[1..255], minimum TTL value";
          } //min-ttl-value

        } //container ttl-security

        container type {
          description
              "Configure the peers for this peer as type internal or external";
          leaf internal-external {
            type enumeration {
              enum internal;
              enum external;
            }
            description
                "keywords";
          } //internal-external

        } //container type

      } //list bgp-peering-policy

      list brg-profile {
        key "profile-name";
        status "obsolete";
        description
            "Configure a profile for Bridged Residential Gateway devices";
        leaf profile-name {
          type string;
        } //profile-name

        container connectivity-verification {
          status "obsolete";
          description
              "Configure the BRG connectivity verification";
          leaf count {
            type uint32 {
              range "1..5";
            }
          } //count

          leaf timeout {
            type uint32 {
              range "5..60";
            }
          } //timeout

          leaf retry-time {
            type uint32 {
              range "300..3600";
            }
          } //retry-time

        } //container connectivity-verification

        container description {
          status "obsolete";
          description
              "Configure a description text";
          leaf description-string {
            type string {
              length "1..80";
            }
          } //description-string

        } //container description

        container hold-time {
          status "obsolete";
          description
              "Configure the time to hold on to a BRG that went down";
          leaf seconds {
            type uint32 {
              range "30..2592000";
            }
          } //seconds

          leaf days {
            type uint32 {
              range "1..30";
            }
          } //days

          leaf hrs {
            type uint32 {
              range "1..23";
            }
          } //hrs

          leaf min {
            type uint32 {
              range "1..59";
            }
          } //min

          leaf sec {
            type uint32 {
              range "1..59";
            }
          } //sec

        } //container hold-time

        container initial-hold-time {
          status "obsolete";
          description
              "Configure the time to hold on to a BRG after it appeared";
          leaf seconds {
            type uint32 {
              range "0..900";
            }
          } //seconds

          leaf min {
            type uint32 {
              range "1..15";
            }
          } //min

          leaf sec {
            type uint32 {
              range "1..59";
            }
          } //sec

        } //container initial-hold-time

        list radius-proxy-server {
          key "router name";
          status "obsolete";
          description
              "Subscribe to a Radius proxy server";
          leaf router {
            type string {
              length "1..32";
            }
            description
                "Attribute router-instance for radius-proxy-server";
          } //router

          leaf name {
            type string {
              length "1..32";
            }
          } //name

        } //list radius-proxy-server

        container sla-profile-string {
          status "obsolete";
          description
              "Configure the SLA profile string";
          leaf string {
            type string;
          } //string

        } //container sla-profile-string

        container sub-profile-string {
          status "obsolete";
          description
              "Configure the subscriber profile string";
          leaf string {
            type string;
          } //string

        } //container sub-profile-string

        container dhcp-pool {
          status "obsolete";
          description
              "Configure a per-subscriber IPv4 address pool";
          container lease-time {
            status "obsolete";
            description
                "Configure the lease time";
            leaf seconds {
              type uint32 {
                range "300..315446399";
              }
            } //seconds

            leaf days {
              type uint32 {
                range "1..3650";
              }
            } //days

            leaf hrs {
              type uint32 {
                range "1..23";
              }
            } //hrs

            leaf min {
              type uint32 {
                range "1..59";
              }
            } //min

            leaf sec {
              type uint32 {
                range "1..59";
              }
            } //sec

          } //container lease-time

          container standby-ip-lifetime {
            status "obsolete";
            description
                "Configure the lifetime of the standby IP addresses";
            leaf seconds {
              type uint32 {
                range "300..315446399";
              }
            } //seconds

            leaf days {
              type uint32 {
                range "1..3650";
              }
            } //days

            leaf hrs {
              type uint32 {
                range "1..23";
              }
            } //hrs

            leaf min {
              type uint32 {
                range "1..59";
              }
            } //min

            leaf sec {
              type uint32 {
                range "1..59";
              }
            } //sec

          } //container standby-ip-lifetime

          container subnet {
            status "obsolete";
            description
                "Configure the IPv4 address subnet and range";
            leaf ip-prefix-prefix-length {
              type string {
                length "1..64";
              }
              description
                  "Attribute ip-prefix/prefix-length for subnet";
            } //ip-prefix-prefix-length

            leaf start {
              type inet:ip-address;
              description
                  "a.b.c.d";
            } //start

            leaf end {
              type inet:ip-address;
              description
                  "ip-address";
            } //end

          } //container subnet

          container options {
            status "obsolete";
            description
                "Configure DHCP options";
            list custom-option {
              key "option-number";
              status "obsolete";
              description
                  "Configure a DHCP option";
              leaf option-number {
                type int32 {
                  range "1..254";
                }
              } //option-number

              leaf-list address {
                type inet:ip-address;
                max-elements 4;
              } //address

              leaf string {
                type string {
                  length "1..127";
                }
              } //string

              leaf hex {
                type string {
                }
                description
                    "[0x0..0xFFFFFFFF...(max 254 hex nibbles)]";
              } //hex

            } //list custom-option

          } //container options

        } //container dhcp-pool

        container radius-authentication {
          status "obsolete";
          description
              "Configure Radius authentication of the BRG";
          container password {
            status "obsolete";
            description
                "Configure the Radius User-Password";
            leaf password {
              type string {
              }
              description
                  "secret-key - [64 chars max] 
                   hash1-key 
                   hash2-key 
                   custom-key";
            } //password

            leaf hash-hash2-custom {
              type enumeration {
                enum hash;
                enum hash2;
                enum custom;
              }
            } //hash-hash2-custom

          } //container password

          container radius-server-policy {
            status "obsolete";
            description
                "Configure the Radius server policy used to authenticate the BRG";
            leaf policy-name {
              type string;
            } //policy-name

          } //container radius-server-policy

        } //container radius-authentication

      } //list brg-profile

      list category-map {
        key "category-map-name";
        description
            "Create/Configure or delete a Category Map";
        leaf category-map-name {
          type string {
            length "1..32";
          }
        } //category-map-name

        container activity-threshold {
          description
              "Configure the activity threshold value in kilobits per second";
          leaf kilobits-per-second {
            type uint32 {
              range "1..100000000";
            }
          } //kilobits-per-second

        } //container activity-threshold

        container credit-exhaust-threshold {
          description
              "Configure the credit exhaust threshold percentage";
          leaf threshold-percentage {
            type uint32 {
              range "50..100";
            }
          } //threshold-percentage

        } //container credit-exhaust-threshold

        container credit-type {
          description
              "Configure the type of credit";
          leaf credit-type-id {
            type enumeration {
              enum volume;
              enum time;
            }
          } //credit-type-id

        } //container credit-type

        container description {
          description
              "Description for this category map";
          leaf description-string {
            type string {
              length "1..80";
            }
          } //description-string

        } //container description

        leaf gx-session-level-usage {
          type boolean;
          description
              "Enable or disable support for Gx session level usage monitoring";
        }

        list category {
          key "category-name";
          description
              "Configure a category in this category-map";
          leaf category-name {
            type string {
              length "1..32";
            }
          } //category-name

          container credit-type-override {
            description
                "Configure the credit type override value";
            leaf credit-type-override-id {
              type enumeration {
                enum volume;
                enum time;
              }
            } //credit-type-override-id

          } //container credit-type-override

          container default-credit {
            description
                "configure the default credit used by this category";
            leaf volume {
              type uint32 {
                range "1..4294967295";
              }
            } //volume

            leaf time {
              type uint32 {
                range "1..4294967295";
              }
            } //time

            leaf default-credit-id {
              type enumeration {
                enum bytes;
                enum kilobytes;
                enum megabytes;
                enum gigabytes;
              }
            } //default-credit-id

          } //container default-credit

          container description {
            description
                "Create a textual description stored in the configuration file";
            leaf description-string {
              type string {
                length "1..80";
              }
            } //description-string

          } //container description

          container out-of-credit-action-override {
            description
                "Configure the out of credit override action";
            leaf out-of-credit-action-override-id {
              type enumeration {
                enum continue;
                enum block-category;
                enum change-service-level;
              }
            } //out-of-credit-action-override-id

          } //container out-of-credit-action-override

          list policer {
            key "policer-id";
            description
                "Configure a policer in this category";
            leaf policer-id {
              type uint32 {
                range "1..63";
              }
            } //policer-id

            leaf policer-id-1 {
              type enumeration {
                enum ingress-only;
                enum egress-only;
                enum ingress-egress;
              }
            } //policer-id-1

          } //list policer

          list queue {
            key "queue-id";
            description
                "Configure a queue in this category";
            leaf queue-id {
              type uint32 {
                range "1..32";
              }
            } //queue-id

            leaf queue-id-1 {
              type enumeration {
                enum ingress-only;
                enum egress-only;
                enum ingress-egress;
              }
            } //queue-id-1

          } //list queue

          container rating-group {
            description
                "Configure the diameter rating group id";
            leaf rating-group-id {
              type uint32;
            } //rating-group-id

          } //container rating-group

          container exhausted-credit-service-level {
            presence
                "Configure the exhausted credit service level";
            container pir {
              description
                  "Configure the pir";
              leaf pir-rate {
                type uint32 {
                  range "1..100000000";
                }
              } //pir-rate

              leaf max {
                type boolean;
              } //max

            } //container pir

            container egress-ip-filter-entries {
              presence
                  "Configure the egress IP-filter entries";
              list entry {
                key "entry-id";
                description
                    "Configure ip-filter entry";
                leaf entry-id {
                  type uint32 {
                    range "1..65535";
                  }
                } //entry-id

                container action {
                  description
                      "Configure action for the filter entry";
                  leaf drop {
                    type boolean;
                  } //drop

                  leaf forward {
                    type boolean;
                    description
                        "keyword";
                  } //forward

                  leaf http-redirect {
                    type string {
                      length "1..255";
                    }
                  } //http-redirect

                  leaf allow-override {
                    type boolean;
                    description
                        "keyword - allow URL override by Diameter Gy Final-Unit-Indication";
                  } //allow-override

                } //container action

                container description {
                  description
                      "Description for this filter entry";
                  leaf description-string {
                    type string {
                      length "1..80";
                    }
                  } //description-string

                } //container description

                container match {
                  description
                      "Configure match criteria for this ip filter entry";
                  leaf protocol {
                    type string;
                    description
                        "Attribute protocol-id for match";
                  } //protocol

                  container dscp {
                    description
                        "Configure DSCP match condition";
                    leaf dscp-name {
                      type string {
                        length "1..32";
                      }
                    } //dscp-name

                  } //container dscp

                  container dst-port {
                    description
                        "Configure dest. port match condition";
                    leaf lt-gt-eq {
                      type enumeration {
                        enum lt;
                        enum gt;
                        enum eq;
                      }
                      description
                          "operators";
                    } //lt-gt-eq

                    leaf dst-port-number {
                      type string;
                      description
                          "Attribute dst-port-number for dst-port";
                    } //dst-port-number

                    leaf-list range {
                      type string;
                      max-elements 2;
                      description
                          "dst-port-number";
                    } //range

                  } //container dst-port

                  container fragment {
                    description
                        "Configure fragmentation match condition";
                    leaf true-false {
                      type enumeration {
                        enum true;
                        enum false;
                      }
                      description
                          "keywords - sets/resets fragmentation check";
                    } //true-false

                  } //container fragment

                  container icmp-code {
                    description
                        "Configure ICMP code match condition";
                    leaf icmp-code {
                      type string;
                      description
                          "Attribute icmp-code for icmp-code";
                    } //icmp-code

                  } //container icmp-code

                  container icmp-type {
                    description
                        "Configure ICMP type match condition";
                    leaf icmp-type {
                      type string;
                      description
                          "Attribute icmp-type for icmp-type";
                    } //icmp-type

                  } //container icmp-type

                  container ip-option {
                    description
                        "Configure ip-option match condition";
                    leaf ip-option-value {
                      type string;
                      description
                          "[0..255] - accepted in decimal hex or binary";
                    } //ip-option-value

                    leaf ip-option-mask {
                      type string;
                      description
                          "[0..255] - accepted in decimal hex or binary";
                    } //ip-option-mask

                  } //container ip-option

                  container multiple-option {
                    description
                        "Configure multiple-option match condition";
                    leaf true-false {
                      type enumeration {
                        enum true;
                        enum false;
                      }
                      description
                          "keywords - sets/resets multiple-option check";
                    } //true-false

                  } //container multiple-option

                  container option-present {
                    description
                        "Configure option-present match condition";
                    leaf true-false {
                      type enumeration {
                        enum true;
                        enum false;
                      }
                      description
                          "keywords - sets/resets option-present check";
                    } //true-false

                  } //container option-present

                  container src-ip {
                    description
                        "Configure src. ip match condition";
                    leaf ip-address-mask {
                      type string;
                      description
                          "ip-address a.b.c.d 
                           mask [0..32]";
                    } //ip-address-mask

                    leaf netmask {
                      type string;
                      description
                          "a.b.c.d any mask expressed as dotted quad";
                    } //netmask

                  } //container src-ip

                  container src-port {
                    description
                        "Configure source port match condition";
                    leaf lt-gt-eq {
                      type enumeration {
                        enum lt;
                        enum gt;
                        enum eq;
                      }
                      description
                          "operators";
                    } //lt-gt-eq

                    leaf src-port-number {
                      type string;
                      description
                          "Attribute src-port-number for src-port";
                    } //src-port-number

                    leaf-list range {
                      type string;
                      max-elements 2;
                      description
                          "src-port-number";
                    } //range

                  } //container src-port

                  container tcp-ack {
                    description
                        "Configure TCP ACK match condition";
                    leaf true-false {
                      type enumeration {
                        enum true;
                        enum false;
                      }
                      description
                          "keywords - sets/resets TCP ACK check";
                    } //true-false

                  } //container tcp-ack

                  container tcp-syn {
                    description
                        "Configure TCP SYN match condition";
                    leaf true-false {
                      type enumeration {
                        enum true;
                        enum false;
                      }
                      description
                          "keywords - sets/resets TCP SYN check";
                    } //true-false

                  } //container tcp-syn

                } //container match

              } //list entry

            } //container egress-ip-filter-entries

            container egress-ipv6-filter-entries {
              presence
                  "Configure the egress IPv6-filter entries";
              list entry {
                key "entry-id";
                description
                    "Configure ip-filter entry";
                leaf entry-id {
                  type uint32 {
                    range "1..65535";
                  }
                } //entry-id

                container action {
                  description
                      "Configure action for the filter entry";
                  leaf drop {
                    type boolean;
                  } //drop

                  leaf forward {
                    type boolean;
                    description
                        "keyword";
                  } //forward

                } //container action

                container description {
                  description
                      "Description for this filter entry";
                  leaf description-string {
                    type string {
                      length "1..80";
                    }
                  } //description-string

                } //container description

                container match {
                  description
                      "Configure match criteria for this ip filter entry";
                  leaf next-header {
                    type string;
                    description
                        "Attribute next-header for match";
                  } //next-header

                  container dscp {
                    description
                        "Configure DSCP match condition";
                    leaf dscp-name {
                      type string {
                        length "1..32";
                      }
                    } //dscp-name

                  } //container dscp

                  container dst-port {
                    description
                        "Configure dest. port match condition";
                    leaf lt-gt-eq {
                      type enumeration {
                        enum lt;
                        enum gt;
                        enum eq;
                      }
                      description
                          "operators";
                    } //lt-gt-eq

                    leaf dst-port-number {
                      type string;
                      description
                          "Attribute dst-port-number for dst-port";
                    } //dst-port-number

                    leaf-list range {
                      type string;
                      max-elements 2;
                      description
                          "dst-port-number";
                    } //range

                  } //container dst-port

                  container icmp-code {
                    description
                        "Configure ICMP code match condition";
                    leaf icmp-code {
                      type string;
                      description
                          "Attribute icmp-code for icmp-code";
                    } //icmp-code

                  } //container icmp-code

                  container icmp-type {
                    description
                        "Configure ICMP type match condition";
                    leaf icmp-type {
                      type string;
                      description
                          "Attribute icmp-type for icmp-type";
                    } //icmp-type

                  } //container icmp-type

                  container src-ip {
                    description
                        "Configure src. ip match condition";
                    leaf ipv6-address-prefix-length {
                      type string;
                      description
                          "ipv6-address x:x:x:x:x:x:x:x (eight 16-bit pieces) 
                           x:x:x:x:x:x:d.d.d.d 
                           x [0..FFFF]H 
                           d [0..255]D 
                           prefix-length [1..128]";
                    } //ipv6-address-prefix-length

                  } //container src-ip

                  container src-port {
                    description
                        "Configure source port match condition";
                    leaf lt-gt-eq {
                      type enumeration {
                        enum lt;
                        enum gt;
                        enum eq;
                      }
                      description
                          "operators";
                    } //lt-gt-eq

                    leaf src-port-number {
                      type string;
                      description
                          "Attribute src-port-number for src-port";
                    } //src-port-number

                    leaf-list range {
                      type string;
                      max-elements 2;
                      description
                          "src-port-number";
                    } //range

                  } //container src-port

                  container tcp-ack {
                    description
                        "Configure TCP ACK match condition";
                    leaf true-false {
                      type enumeration {
                        enum true;
                        enum false;
                      }
                      description
                          "keywords - sets/resets TCP ACK check";
                    } //true-false

                  } //container tcp-ack

                  container tcp-syn {
                    description
                        "Configure TCP SYN match condition";
                    leaf true-false {
                      type enumeration {
                        enum true;
                        enum false;
                      }
                      description
                          "keywords - sets/resets TCP SYN check";
                    } //true-false

                  } //container tcp-syn

                } //container match

              } //list entry

            } //container egress-ipv6-filter-entries

            container ingress-ip-filter-entries {
              presence
                  "Configure the ingress IP-filter entries";
              list entry {
                key "entry-id";
                description
                    "Configure ip-filter entry";
                leaf entry-id {
                  type uint32 {
                    range "1..65535";
                  }
                } //entry-id

                container action {
                  description
                      "Configure action for the filter entry";
                  leaf drop {
                    type boolean;
                  } //drop

                  leaf forward {
                    type boolean;
                    description
                        "keyword";
                  } //forward

                  leaf http-redirect {
                    type string {
                      length "1..255";
                    }
                  } //http-redirect

                  leaf allow-override {
                    type boolean;
                    description
                        "keyword - allow URL override by Diameter Gy Final-Unit-Indication";
                  } //allow-override

                } //container action

                container description {
                  description
                      "Description for this filter entry";
                  leaf description-string {
                    type string {
                      length "1..80";
                    }
                  } //description-string

                } //container description

                container match {
                  description
                      "Configure match criteria for this ip filter entry";
                  leaf protocol {
                    type string;
                    description
                        "Attribute protocol-id for match";
                  } //protocol

                  container dscp {
                    description
                        "Configure DSCP match condition";
                    leaf dscp-name {
                      type string {
                        length "1..32";
                      }
                    } //dscp-name

                  } //container dscp

                  container dst-ip {
                    description
                        "Configure dest. ip match condition";
                    leaf ip-address-mask {
                      type string;
                      description
                          "ip-address a.b.c.d 
                           mask [0..32]";
                    } //ip-address-mask

                    leaf netmask {
                      type string;
                      description
                          "a.b.c.d any mask expressed as dotted quad";
                    } //netmask

                  } //container dst-ip

                  container dst-port {
                    description
                        "Configure dest. port match condition";
                    leaf lt-gt-eq {
                      type enumeration {
                        enum lt;
                        enum gt;
                        enum eq;
                      }
                      description
                          "operators";
                    } //lt-gt-eq

                    leaf dst-port-number {
                      type string;
                      description
                          "Attribute dst-port-number for dst-port";
                    } //dst-port-number

                    leaf-list range {
                      type string;
                      max-elements 2;
                      description
                          "dst-port-number";
                    } //range

                  } //container dst-port

                  container fragment {
                    description
                        "Configure fragmentation match condition";
                    leaf true-false {
                      type enumeration {
                        enum true;
                        enum false;
                      }
                      description
                          "keywords - sets/resets fragmentation check";
                    } //true-false

                  } //container fragment

                  container icmp-code {
                    description
                        "Configure ICMP code match condition";
                    leaf icmp-code {
                      type string;
                      description
                          "Attribute icmp-code for icmp-code";
                    } //icmp-code

                  } //container icmp-code

                  container icmp-type {
                    description
                        "Configure ICMP type match condition";
                    leaf icmp-type {
                      type string;
                      description
                          "Attribute icmp-type for icmp-type";
                    } //icmp-type

                  } //container icmp-type

                  container ip-option {
                    description
                        "Configure ip-option match condition";
                    leaf ip-option-value {
                      type string;
                      description
                          "[0..255] - accepted in decimal hex or binary";
                    } //ip-option-value

                    leaf ip-option-mask {
                      type string;
                      description
                          "[0..255] - accepted in decimal hex or binary";
                    } //ip-option-mask

                  } //container ip-option

                  container multiple-option {
                    description
                        "Configure multiple-option match condition";
                    leaf true-false {
                      type enumeration {
                        enum true;
                        enum false;
                      }
                      description
                          "keywords - sets/resets multiple-option check";
                    } //true-false

                  } //container multiple-option

                  container option-present {
                    description
                        "Configure option-present match condition";
                    leaf true-false {
                      type enumeration {
                        enum true;
                        enum false;
                      }
                      description
                          "keywords - sets/resets option-present check";
                    } //true-false

                  } //container option-present

                  container src-port {
                    description
                        "Configure source port match condition";
                    leaf lt-gt-eq {
                      type enumeration {
                        enum lt;
                        enum gt;
                        enum eq;
                      }
                      description
                          "operators";
                    } //lt-gt-eq

                    leaf src-port-number {
                      type string;
                      description
                          "Attribute src-port-number for src-port";
                    } //src-port-number

                    leaf-list range {
                      type string;
                      max-elements 2;
                      description
                          "src-port-number";
                    } //range

                  } //container src-port

                  container tcp-ack {
                    description
                        "Configure TCP ACK match condition";
                    leaf true-false {
                      type enumeration {
                        enum true;
                        enum false;
                      }
                      description
                          "keywords - sets/resets TCP ACK check";
                    } //true-false

                  } //container tcp-ack

                  container tcp-syn {
                    description
                        "Configure TCP SYN match condition";
                    leaf true-false {
                      type enumeration {
                        enum true;
                        enum false;
                      }
                      description
                          "keywords - sets/resets TCP SYN check";
                    } //true-false

                  } //container tcp-syn

                } //container match

              } //list entry

            } //container ingress-ip-filter-entries

            container ingress-ipv6-filter-entries {
              presence
                  "Configure the ingress IPv6-filter entries";
              list entry {
                key "entry-id";
                description
                    "Configure ip-filter entry";
                leaf entry-id {
                  type uint32 {
                    range "1..65535";
                  }
                } //entry-id

                container action {
                  description
                      "Configure action for the filter entry";
                  leaf drop {
                    type boolean;
                  } //drop

                  leaf forward {
                    type boolean;
                    description
                        "keyword";
                  } //forward

                } //container action

                container description {
                  description
                      "Description for this filter entry";
                  leaf description-string {
                    type string {
                      length "1..80";
                    }
                  } //description-string

                } //container description

                container match {
                  description
                      "Configure match criteria for this ip filter entry";
                  leaf next-header {
                    type string;
                    description
                        "Attribute next-header for match";
                  } //next-header

                  container dscp {
                    description
                        "Configure DSCP match condition";
                    leaf dscp-name {
                      type string {
                        length "1..32";
                      }
                    } //dscp-name

                  } //container dscp

                  container dst-ip {
                    description
                        "Configure dst. ip match condition";
                    leaf ipv6-address-prefix-length {
                      type string;
                      description
                          "ipv6-address x:x:x:x:x:x:x:x (eight 16-bit pieces) 
                           x:x:x:x:x:x:d.d.d.d 
                           x [0..FFFF]H 
                           d [0..255]D 
                           prefix-length [1..128]";
                    } //ipv6-address-prefix-length

                  } //container dst-ip

                  container dst-port {
                    description
                        "Configure dest. port match condition";
                    leaf lt-gt-eq {
                      type enumeration {
                        enum lt;
                        enum gt;
                        enum eq;
                      }
                      description
                          "operators";
                    } //lt-gt-eq

                    leaf dst-port-number {
                      type string;
                      description
                          "Attribute dst-port-number for dst-port";
                    } //dst-port-number

                    leaf-list range {
                      type string;
                      max-elements 2;
                      description
                          "dst-port-number";
                    } //range

                  } //container dst-port

                  container icmp-code {
                    description
                        "Configure ICMP code match condition";
                    leaf icmp-code {
                      type string;
                      description
                          "Attribute icmp-code for icmp-code";
                    } //icmp-code

                  } //container icmp-code

                  container icmp-type {
                    description
                        "Configure ICMP type match condition";
                    leaf icmp-type {
                      type string;
                      description
                          "Attribute icmp-type for icmp-type";
                    } //icmp-type

                  } //container icmp-type

                  container src-port {
                    description
                        "Configure source port match condition";
                    leaf lt-gt-eq {
                      type enumeration {
                        enum lt;
                        enum gt;
                        enum eq;
                      }
                      description
                          "operators";
                    } //lt-gt-eq

                    leaf src-port-number {
                      type string;
                      description
                          "Attribute src-port-number for src-port";
                    } //src-port-number

                    leaf-list range {
                      type string;
                      max-elements 2;
                      description
                          "src-port-number";
                    } //range

                  } //container src-port

                  container tcp-ack {
                    description
                        "Configure TCP ACK match condition";
                    leaf true-false {
                      type enumeration {
                        enum true;
                        enum false;
                      }
                      description
                          "keywords - sets/resets TCP ACK check";
                    } //true-false

                  } //container tcp-ack

                  container tcp-syn {
                    description
                        "Configure TCP SYN match condition";
                    leaf true-false {
                      type enumeration {
                        enum true;
                        enum false;
                      }
                      description
                          "keywords - sets/resets TCP SYN check";
                    } //true-false

                  } //container tcp-syn

                } //container match

              } //list entry

            } //container ingress-ipv6-filter-entries

          } //container exhausted-credit-service-level

        } //list category

      } //list category-map

      list credit-control-policy {
        key "policy-name";
        description
            "Create/Configure or delete a Credit Control policy";
        leaf policy-name {
          type string {
            length "1..32";
          }
        } //policy-name

        container credit-control-server {
          description
              "Configure the credit control server";
          leaf radius {
            type boolean;
          } //radius

          leaf diameter {
            type string {
              length "1..32";
            }
          } //diameter

        } //container credit-control-server

        container default-category-map {
          description
              "Configure the default category map for this policy";
          leaf category-map-name {
            type string {
              length "1..32";
            }
          } //category-map-name

        } //container default-category-map

        container description {
          description
              "Description for this policy";
          leaf description-string {
            type string {
              length "1..80";
            }
          } //description-string

        } //container description

        container error-handling-action {
          description
              "Configure the error handling action for this policy";
          leaf error-handling-action-id {
            type enumeration {
              enum continue;
              enum block;
            }
          } //error-handling-action-id

        } //container error-handling-action

        container out-of-credit-action {
          description
              "Configure the action to be taken when out of credit is reached";
          leaf out-of-credit-action-id {
            type enumeration {
              enum continue;
              enum disconnect-host;
              enum block-category;
              enum change-service-level;
            }
          } //out-of-credit-action-id

        } //container out-of-credit-action

      } //list credit-control-policy

      list diameter-application-policy {
        key "application-policy-name";
        description
            "Configure a Diameter application policy";
        leaf application-policy-name {
          type string;
        } //application-policy-name

        container application {
          description
              "Configure the application";
          leaf application-id {
            type enumeration {
              enum gx;
              enum gy;
              enum nasreq;
            }
          } //application-id

        } //container application

        container description {
          description
              "Configure a description of this Diameter application policy";
          leaf description-string {
            type string {
              length "1..80";
            }
          } //description-string

        } //container description

        container diameter-node {
          description
              "Configure the Diameter node for this Diameter application policy";
          leaf origin-host-string {
            type string {
              length "1..80";
            }
          } //origin-host-string

          leaf destination-realm {
            type string {
              length "1..80";
            }
          } //destination-realm

        } //container diameter-node

        container diameter-peer-policy {
          description
              "Configure the policy for the Diameter peers";
          leaf peer-policy-name {
            type string;
          } //peer-policy-name

        } //container diameter-peer-policy

        container on-failure {
          description
              "Configure session failure handling";
          leaf failover {
            type enumeration {
              enum enabled;
              enum disabled;
            }
          } //failover

          leaf handling {
            type enumeration {
              enum continue;
              enum retry-and-terminate;
              enum terminate;
            }
          } //handling

        } //container on-failure

        container tx-timer {
          description
              "Configure the maximum wait time (seconds) while a client is pending";
          leaf tx-timer-id {
            type uint32 {
              range "10..1000";
            }
          } //tx-timer-id

        } //container tx-timer

        container gx {
          description
              "Configure 3GPP Gx";
          container avp-subscription-id {
            description
                "Configure the format of the Subscription-Id-Data AVP";
            leaf origin {
              type enumeration {
                enum circuit-id;
                enum dual-stack-remote-id;
                enum imei;
                enum imsi;
                enum mac;
                enum msisdn;
                enum nas-port-id;
                enum subscriber-id;
                enum username;
              }
            } //origin

            leaf type {
              type enumeration {
                enum e164;
                enum imsi;
                enum nai;
                enum private;
              }
            } //type

          } //container avp-subscription-id

          container ccrt-replay-interval {
            status "obsolete";
            description
                "Configure the interval between two consecutive CCR Terminate replay attempts 
                 (seconds)";
            leaf interval {
              type uint32 {
                range "60..86400";
              }
            } //interval

          } //container ccrt-replay-interval

          container credit-mcs-interval {
            description
                "Configure the credit MCS interval";
            leaf minutes {
              type uint32 {
                range "5..60";
              }
            } //minutes

          } //container credit-mcs-interval

          container mac-format {
            description
                "Configure the format of MAC addresses";
            leaf mac-format {
              type string {
                length "1..7";
              }
              description
                  "like ab: for 00:0c:f1:99:85:b8 
                   or XY- for 00-0C-F1-99-85-B8 
                   or mmmm. for 0002.03aa.abff 
                   or xx for 000cf19985b8";
            } //mac-format

          } //container mac-format

          leaf report-ip-address-event {
            type boolean;
            description
                "Enable CCR-u upon IP address allocation events for dual stack subscribers";
          }

          container t3gpp-qos-mapping {
            description
                "Configure the 3GPP QoS mapping";
            container apn-ambr-dl {
              description
                  "Configure the APN-AMBR mapping for the downlink";
              leaf agg-rate {
                type boolean;
              } //agg-rate

              leaf policer {
                type uint32 {
                  range "1..63";
                }
              } //policer

              leaf queue {
                type int32 {
                  range "1..8";
                }
              } //queue

              leaf scheduler {
                type string {
                  length "1..32";
                }
              } //scheduler

              leaf arbiter {
                type string {
                  length "1..32";
                }
              } //arbiter

              leaf hs-sla-agg-rate {
                type boolean;
              } //hs-sla-agg-rate

            } //container apn-ambr-dl

            container apn-ambr-ul {
              description
                  "Configure the APN-AMBR mapping for the uplink";
              leaf policer {
                type uint32 {
                  range "1..63";
                }
              } //policer

              leaf queue {
                type int32 {
                  range "1..32";
                }
              } //queue

              leaf scheduler {
                type string {
                  length "1..32";
                }
              } //scheduler

              leaf arbiter {
                type string {
                  length "1..32";
                }
              } //arbiter

            } //container apn-ambr-ul

          } //container t3gpp-qos-mapping

          container ccrt-replay {
            description
                "Configure CCR-t Replay for Gx messages";
            container interval {
              description
                  "Configure the interval between two consecutive CCR-t replay attempts for a 
                   sessions";
              leaf seconds {
                type uint32 {
                  range "60..86400";
                }
              } //seconds

            } //container interval

            container max-lifetime {
              description
                  "Configure the maximum time for CCR-t replay attempts for a sessions";
              leaf hours {
                type uint32 {
                  range "1..24";
                }
              } //hours

            } //container max-lifetime

            leaf shutdown {
              type boolean;
              description
                  "Administratively enable/disable CCR-t Replay";
            }

          } //container ccrt-replay

          container include-avp {
            presence
                "Configure the attribute-value-pairs for Gx messages";
            leaf an-gw-address {
              type boolean;
              description
                  "Include the IP address of this gateway";
            }

            leaf apn-ambr {
              type boolean;
              description
                  "Include the APN aggregate maximum bitrate";
            }

            leaf called-station-id {
              type boolean;
              description
                  "Include the called station id";
            }

            container calling-station-id {
              description
                  "Include the calling station id";
              leaf type {
                type enumeration {
                  enum llid;
                  enum mac;
                  enum remote-id;
                  enum sap-id;
                  enum sap-string;
                }
              } //type

            } //container calling-station-id

            leaf ip-can-type {
              type boolean;
              description
                  "Include the IP CAN type";
            }

            leaf logical-access-id {
              type boolean;
              description
                  "Include the logical access id";
            }

            container nas-port {
              description
                  "Include the NAS port";
              leaf binary-spec {
                type string {
                }
                description
                    "Attribute binary-spec for nas-port";
              } //binary-spec

            } //container nas-port

            container nas-port-id {
              description
                  "Include the NAS port id";
              leaf prefix-type {
                type enumeration {
                  enum none;
                  enum user-string;
                }
              } //prefix-type

              leaf prefix-string {
                type string {
                  length "1..8";
                }
              } //prefix-string

              leaf suffix-type {
                type enumeration {
                  enum none;
                  enum circuit-id;
                  enum remote-id;
                  enum user-string;
                }
              } //suffix-type

              leaf suffix-string {
                type string {
                  length "1..64";
                }
              } //suffix-string

            } //container nas-port-id

            container nas-port-type {
              description
                  "Include the NAS port type";
              leaf nas-port-type-id {
                type uint8;
              } //nas-port-type-id

            } //container nas-port-type

            leaf pdn-connection-id {
              type boolean;
              description
                  "Include the PDN connection id";
            }

            leaf physical-access-id {
              type boolean;
              description
                  "Include the physical access id";
            }

            leaf rai {
              type boolean;
              description
                  "Include the routing area identity";
            }

            leaf rat-type {
              type boolean;
              description
                  "Include the RAT type";
            }

            leaf sgsn-mcc-mnc {
              type boolean;
              description
                  "Include the SGSN MCC and MNC";
            }

            leaf supported-features {
              type boolean;
              description
                  "Include the supported features";
            }

            container user-equipment-info {
              description
                  "Include the user equipment info";
              leaf type {
                type enumeration {
                  enum eui64;
                  enum imeisv;
                  enum mac;
                  enum modified-eui64;
                }
              } //type

            } //container user-equipment-info

            leaf user-location-info {
              type boolean;
              description
                  "Include the user location info";
            }

          } //container include-avp

        } //container gx

        container gy {
          description
              "Configure 3GPP Gy";
          container avp-subscription-id {
            description
                "Configure the format of the Subscription-Id-Data AVP";
            leaf origin {
              type enumeration {
                enum circuit-id;
                enum dual-stack-remote-id;
                enum imei;
                enum imsi;
                enum mac;
                enum msisdn;
                enum nas-port-id;
                enum subscriber-id;
                enum username;
              }
            } //origin

            leaf type {
              type enumeration {
                enum e164;
                enum imsi;
                enum nai;
                enum private;
              }
            } //type

          } //container avp-subscription-id

          container mac-format {
            description
                "Configure the format of MAC addresses";
            leaf mac-format {
              type string {
                length "1..7";
              }
              description
                  "like ab: for 00:0c:f1:99:85:b8 
                   or XY- for 00-0C-F1-99-85-B8 
                   or mmmm. for 0002.03aa.abff 
                   or xx for 000cf19985b8";
            } //mac-format

          } //container mac-format

          container out-of-credit-reporting {
            description
                "Configure the reporting reason when the final granted units have been consumed";
            leaf out-of-credit-reporting-id {
              type enumeration {
                enum final;
                enum quota-exhausted;
              }
            } //out-of-credit-reporting-id

          } //container out-of-credit-reporting

          container vendor-support {
            description
                "Configure the vendor type";
            leaf vendor-support-id {
              type enumeration {
                enum three-gpp;
                enum vodafone;
              }
            } //vendor-support-id

          } //container vendor-support

          container ccrt-replay {
            description
                "Configure CCR-t Replay for Gy messages";
            container interval {
              description
                  "Configure the interval between two consecutive CCR-t replay attempts for a 
                   sessions";
              leaf seconds {
                type uint32 {
                  range "60..86400";
                }
              } //seconds

            } //container interval

            container max-lifetime {
              description
                  "Configure the maximum time for CCR-t replay attempts for a sessions";
              leaf hours {
                type uint32 {
                  range "1..24";
                }
              } //hours

            } //container max-lifetime

            leaf shutdown {
              type boolean;
              description
                  "Administratively enable/disable CCR-t Replay";
            }

          } //container ccrt-replay

          container extended-failure-handling {
            description
                "Configure Extended Failure Handling for Gy sessions";
            leaf new-session-id {
              type boolean;
              description
                  "Enable/disable using a new session id for CCR-i messages";
            }

            leaf shutdown {
              type boolean;
              description
                  "Administratively enable/disable Extended Failure Handling";
            }

            container interim-credit {
              description
                  "Configure Interim Credit parameters";
              container max-attempts {
                description
                    "Configure the number of attempts to report used credit";
                leaf count {
                  type uint32 {
                    range "1..4294967295";
                  }
                } //count

                leaf infinite {
                  type boolean;
                } //infinite

              } //container max-attempts

              leaf reporting {
                type boolean;
                description
                    "Enable/disable Interim Credit reporting";
              }

              container validity-time {
                description
                    "Configure the validity time for interim credit";
                leaf seconds {
                  type uint32;
                } //seconds

              } //container validity-time

              container volume {
                description
                    "Configure the default volume credit";
                leaf credits {
                  type uint32 {
                    range "1..4294967295";
                  }
                } //credits

                leaf volume-id {
                  type enumeration {
                    enum bytes;
                    enum kilobytes;
                    enum megabytes;
                    enum gigabytes;
                  }
                } //volume-id

              } //container volume

            } //container interim-credit

          } //container extended-failure-handling

          container include-avp {
            presence
                "Configure the attribute-value-pairs for Gy messages";
            leaf t3gpp-charging-characteristics {
              type boolean;
              description
                  "Configure the DCCA 3GPP-Charging-Characteristics AVP Parameter";
            }

            container t3gpp-charging-id {
              description
                  "Configure the DCCA 3gpp-charging-id AVP parameter";
              leaf t3gpp-charging-id-id {
                type enumeration {
                  enum auto;
                  enum esm-info;
                  enum id;
                }
              } //t3gpp-charging-id-id

            } //container t3gpp-charging-id

            leaf t3gpp-ggsn-address {
              type boolean;
              description
                  "Include the 3GPP-GGSN-Address";
            }

            leaf t3gpp-ggsn-ipv6-address {
              type boolean;
              description
                  "Include the 3GPP-GGSN-Ipv6-Address";
            }

            leaf t3gpp-gprs-negotiated-qos-profile {
              type boolean;
              description
                  "Configure the DCCA 3GPP-GPRS-Negotiated-QoS-profile AVP Parameter";
            }

            container t3gpp-imsi {
              description
                  "Configure the origin of the information to send in the IMSI AVP";
              leaf t3gpp-imsi-id {
                type enumeration {
                  enum circuit-id;
                  enum imsi;
                  enum subscriber-id;
                }
              } //t3gpp-imsi-id

            } //container t3gpp-imsi

            leaf t3gpp-nsapi {
              type boolean;
              description
                  "Include the 3GPP-GGSN-Ipv6-Address";
            }

            container t3gpp-rat-type {
              description
                  "Configure the DCCA 3gpp-rat-type AVP parameter";
              leaf value {
                type uint32 {
                  range "1..255";
                }
              } //value

            } //container t3gpp-rat-type

            leaf t3gpp-selection-mode {
              type boolean;
              description
                  "Configure the DCCA 3GPP-Selection-Mode AVP Parameter";
            }

            leaf t3gpp-session-stop-indicator {
              type boolean;
              description
                  "Configure the DCCA 3GPP-Session-Stop-Indicator AVP Parameter";
            }

            leaf t3gpp-user-location-info {
              type boolean;
              description
                  "Configure the DCCA 3GPP-User-Location-Info AVP Parameter";
            }

            leaf address-avp {
              type boolean;
              description
                  "Configure the DCCA AVPs containing the host address or prefix";
            }

            container called-station-id {
              description
                  "Include the Called-Station-Id";
              leaf called-station-id-string {
                type string {
                  length "1..64";
                }
              } //called-station-id-string

            } //container called-station-id

            container charging-rule-base-name {
              description
                  "Configure the DCCA Charging-Rule-Base-Name AVP parameter";
              leaf category-map-name {
                type boolean;
                description
                    "keyword";
              } //category-map-name

              leaf string {
                type string {
                  length "1..64";
                }
              } //string

            } //container charging-rule-base-name

            container ggsn-address {
              description
                  "Include the GGSN-Address";
              leaf ggsn-address-id {
                type enumeration {
                  enum ipv4;
                  enum ipv6;
                }
              } //ggsn-address-id

            } //container ggsn-address

            leaf pdp-context-type {
              type boolean;
              description
                  "Configure the DCCA PDP-Context-Type AVP Parameter";
            }

            leaf ps-information {
              type boolean;
              description
                  "Enable reporting of AVPs in grouped PS-Information AVP";
            }

            leaf radius-user-name {
              type boolean;
              description
                  "Include the User-Name";
            }

            container service-context-id {
              description
                  "Include the Service-Context-Id";
              leaf name {
                type string;
              } //name

            } //container service-context-id

            container user-equipment-info {
              description
                  "Include the user equipment info";
              leaf type {
                type enumeration {
                  enum imeisv;
                }
              } //type

            } //container user-equipment-info

          } //container include-avp

        } //container gy

        container nasreq {
          description
              "Configure Diameter Network Access Server Application (NASREQ)";
          container mac-format {
            description
                "Configure the format of MAC addresses";
            leaf mac-format {
              type string {
                length "1..7";
              }
              description
                  "like ab: for 00:0c:f1:99:85:b8 
                   or XY- for 00-0C-F1-99-85-B8 
                   or mmmm. for 0002.03aa.abff 
                   or xx for 000cf19985b8";
            } //mac-format

          } //container mac-format

          container password {
            description
                "Configure the password used in the Diameter messages transmitted to the server";
            leaf password {
              type string {
                length "1..500";
              }
              description
                  "secret-key - [64 chars max] 
                   hash-key 
                   hash2-key 
                   custom-key";
            } //password

            leaf hash-hash2-custom {
              type enumeration {
                enum hash;
                enum hash2;
                enum custom;
              }
              description
                  "keywords - specify hashing scheme";
            } //hash-hash2-custom

          } //container password

          container user-name-format {
            description
                "Configure the format used to identify the user towards the Diameter server";
            leaf format {
              type enumeration {
                enum mac;
                enum circuit-id;
                enum tuple;
                enum ascii-converted-circuit-id;
                enum ascii-converted-tuple;
                enum dhcp-client-vendor-opts;
                enum mac-giaddr;
                enum nas-port-id;
              }
            } //format

          } //container user-name-format

          container user-name-operation {
            description
                "Configure the operation to perform on the user name";
            leaf operation {
              type enumeration {
                enum append-domain;
                enum strip-domain;
                enum default-domain;
                enum replace-domain;
              }
            } //operation

            leaf domain {
              type string {
                length "1..128";
              }
            } //domain

          } //container user-name-operation

          container include-avp {
            presence
                "Configure the attribute-value-pairs for NASREQ messages";
            leaf called-station-id {
              type boolean;
              description
                  "Include the Called-Station-Id";
            }

            container calling-station-id {
              description
                  "Include the Calling-Station-Id";
              leaf type {
                type enumeration {
                  enum llid;
                  enum mac;
                  enum remote-id;
                  enum sap-id;
                  enum sap-string;
                }
              } //type

            } //container calling-station-id

            leaf circuit-id {
              type boolean;
              description
                  "Include the Circuit-Id";
            }

            leaf imei {
              type boolean;
              description
                  "Include the IMEI";
            }

            container nas-port {
              description
                  "Include the NAS-Port";
              leaf binary-spec {
                type string {
                }
                description
                    "Attribute binary-spec for nas-port";
              } //binary-spec

            } //container nas-port

            container nas-port-id {
              description
                  "Include the NAS-Port-Id";
              leaf prefix-type {
                type enumeration {
                  enum none;
                  enum user-string;
                }
              } //prefix-type

              leaf prefix-string {
                type string {
                  length "1..8";
                }
              } //prefix-string

              leaf suffix-type {
                type enumeration {
                  enum circuit-id;
                  enum none;
                  enum remote-id;
                  enum user-string;
                }
              } //suffix-type

              leaf suffix-string {
                type string {
                  length "1..64";
                }
              } //suffix-string

            } //container nas-port-id

            container nas-port-type {
              description
                  "Include the NAS-Port-Type";
              leaf nas-port-type-id {
                type uint8;
              } //nas-port-type-id

            } //container nas-port-type

            leaf rat-type {
              type boolean;
              description
                  "Include the RAT-Type";
            }

            leaf remote-id {
              type boolean;
              description
                  "Include the Remote-Id";
            }

            leaf user-location-info {
              type boolean;
              description
                  "Include the user-location-info";
            }

          } //container include-avp

        } //container nasreq

      } //list diameter-application-policy

      container explicit-subscriber-map {
        description
            "Configure an explicit subscriber mapping";
        list entry {
          key "key";
          description
              "Configure a subscriber identification string";
          leaf key {
            type string;
            description
                "Attribute sub-ident-string for entry";
          } //key

          leaf sub-profile {
            type string {
              length "1..32";
            }
          } //sub-profile

          leaf alias {
            type string {
              length "1..64";
            }
          } //alias

          leaf sla-profile {
            type string {
              length "1..32";
            }
          } //sla-profile

          leaf app-profile {
            type string {
            }
          } //app-profile

        } //list entry

      } //container explicit-subscriber-map

      container gtp {
        description
            "Configure the GPRS Tunnel Protocol";
        container max-held-sessions {
          description
              "Configure the maximum number of GTP sessions to be held while their UE are 
               disconnected";
          leaf max-held-sessions {
            type uint32 {
              range "0..500000";
            }
            description
                "Attribute max-held-sessions for max-held-sessions";
          } //max-held-sessions

        } //container max-held-sessions

        container serving-network {
          description
              "Configure the Operator Identifier part of the APN";
          leaf mcc {
            type string {
              length "1..3";
            }
            description
                "3 digits";
          } //mcc

          leaf mnc {
            type string {
              length "1..3";
            }
            description
                "2 or 3 digits";
          } //mnc

        } //container serving-network

        list apn-policy {
          key "policy-name";
          description
              "Configure the GTP APN policy";
          leaf policy-name {
            type string;
          } //policy-name

          list apn {
            key "apn";
            description
                "Configure the GTP APN";
            leaf apn {
              type string {
                length "1..80";
              }
            } //apn

            container diameter-auth-policy {
              description
                  "Configure the DIAMETER authentication policy name";
              leaf diameter-authentication-policy-name {
                type string;
              } //diameter-authentication-policy-name

            } //container diameter-auth-policy

            container radius-auth-policy {
              description
                  "Configure the RADIUS authentication policy name";
              leaf radius-authentication-policy-name {
                type string;
              } //radius-authentication-policy-name

            } //container radius-auth-policy

            leaf skip-gtp-ipv4-alloc {
              type boolean;
              description
                  "Skip ipv4 gtp address allocation";
            }

            container user-db {
              description
                  "Configure the local user database name";
              leaf local-user-database-name {
                type string;
              } //local-user-database-name

            } //container user-db

            container ambr-qos-mapping {
              description
                  "Configure the APN-AMBR QoS mapping";
              container downlink {
                description
                    "Configure the APN-AMBR QoS mapping for downlink";
                leaf aggregate-rate {
                  type boolean;
                } //aggregate-rate

                leaf policer {
                  type uint32 {
                    range "1..63";
                  }
                } //policer

                leaf queue {
                  type int32 {
                    range "1..8";
                  }
                } //queue

                leaf scheduler {
                  type string {
                    length "1..32";
                  }
                } //scheduler

                leaf arbiter {
                  type string {
                    length "1..32";
                  }
                } //arbiter

              } //container downlink

              container uplink {
                description
                    "Configure the APN-AMBR QoS mapping for uplink";
                leaf policer {
                  type uint32 {
                    range "1..63";
                  }
                } //policer

                leaf queue {
                  type int32 {
                    range "1..32";
                  }
                } //queue

                leaf scheduler {
                  type string {
                    length "1..32";
                  }
                } //scheduler

                leaf arbiter {
                  type string {
                    length "1..32";
                  }
                } //arbiter

              } //container uplink

            } //container ambr-qos-mapping

            container defaults {
              description
                  "Configure the default values";
              container group-interface {
                description
                    "Configure the default values for the group interface";
                leaf interface-name {
                  type string;
                } //interface-name

                leaf svc-id {
                  type string;
                  description
                      "Attribute service-id for group-interface";
                } //svc-id

              } //container group-interface

            } //container defaults

          } //list apn

        } //list apn-policy

        list peer-profile {
          key "profile-name";
          description
              "Configure a peer profile";
          leaf profile-name {
            type string {
              length "1..32";
            }
          } //profile-name

          container change-reporting-action {
            description
                "Configure the Change Raporting Action sent to the peers";
            leaf reporting-action {
              type string {
              }
              description
                  "cgi-sai|rai|tai|ecgi|cgi-sai-rai|tai-ecgi|<0..255>";
            } //reporting-action

          } //container change-reporting-action

          container description {
            description
                "Configure a description";
            leaf description-string {
              type string {
                length "1..80";
              }
            } //description-string

          } //container description

          container end-marker-count {
            description
                "Configure the number of times the gtp-u end-marker packet is sent";
            leaf packets {
              type uint32 {
                range "0..5";
              }
            } //packets

          } //container end-marker-count

          container interface-type {
            description
                "Configure the 3GPP interface type";
            leaf interface-type-id {
              type enumeration {
                enum gn;
                enum s2a;
                enum s2b;
                enum s11;
              }
            } //interface-type-id

          } //container interface-type

          container ip-ttl {
            description
                "Configure the IP Time-To-Live";
            leaf hops {
              type uint16 {
                range "1..255";
              }
            } //hops

          } //container ip-ttl

          container ipv4-mtu {
            description
                "Configure the IPv4 MTU signaled in the PCO";
            leaf bytes {
              type uint32 {
                range "512..9000";
              }
            } //bytes

          } //container ipv4-mtu

          container keep-alive {
            description
                "Configure the Echo-Request messages";
            leaf interval {
              type uint32 {
                range "0..180";
              }
              description
                  "0|[60..180]";
            } //interval

            leaf retry-count {
              type uint32 {
                range "1..15";
              }
            } //retry-count

            leaf timeout {
              type uint32 {
                range "1..20";
              }
            } //timeout

          } //container keep-alive

          container message-retransmit {
            description
                "Configure the retransmission of signalling request messages";
            leaf timeout {
              type uint32 {
                range "1..30";
              }
            } //timeout

            leaf retry-count {
              type uint32 {
                range "1..8";
              }
            } //retry-count

          } //container message-retransmit

          container protocol-configuration-options {
            description
                "Configure the Information Element to use for the Protocol Configuration 
                 Options";
            leaf protocol-configuration-options-id {
              type enumeration {
                enum apco;
                enum pco;
              }
            } //protocol-configuration-options-id

          } //container protocol-configuration-options

          container python-policy {
            description
                "Configure the Python policy used to process GTP messages";
            leaf name {
              type string;
            } //name

          } //container python-policy

          container rat-type {
            description
                "Configure the default Radio Access Technology type signaled during GTP set-up";
            leaf type {
              type string {
              }
              description
                  "utran|geran|wlan|gan|hspa|eutran|virtual|<0..255>";
            } //type

          } //container rat-type

          leaf report-wlan-location {
            type boolean;
            description
                "Enable/disable reporting the WLAN location of the UE during session set-up";
          }

          container session-hold-time {
            description
                "Configure the time to hold a GTP session after its UE is disconnected";
            leaf seconds {
              type uint32 {
                range "0..3600";
              }
            } //seconds

            leaf remaining-lease-time {
              type boolean;
            } //remaining-lease-time

          } //container session-hold-time

          container charging-characteristics {
            description
                "Configure the charging characteristics";
            container home {
              description
                  "Configure the charging characteristics for home UE";
              leaf-list bit {
                type enumeration {
                  enum bit0;
                  enum bit1;
                  enum bit2;
                  enum bit3;
                  enum bit4;
                  enum bit5;
                  enum bit6;
                  enum bit7;
                  enum bit8;
                  enum bit9;
                  enum bit10;
                  enum bit11;
                  enum bit12;
                  enum bit13;
                  enum bit14;
                  enum bit15;
                }
                max-elements 16;
              } //bit

            } //container home

            container roaming {
              description
                  "Configure the charging characteristics for roaming UE";
              leaf-list bit {
                type enumeration {
                  enum bit0;
                  enum bit1;
                  enum bit2;
                  enum bit3;
                  enum bit4;
                  enum bit5;
                  enum bit6;
                  enum bit7;
                  enum bit8;
                  enum bit9;
                  enum bit10;
                  enum bit11;
                  enum bit12;
                  enum bit13;
                  enum bit14;
                  enum bit15;
                }
                max-elements 16;
              } //bit

            } //container roaming

          } //container charging-characteristics

          container ggsn {
            description
                "Configure the communication with a GGSN Mobile Gateway";
            container qos {
              description
                  "Configure the QoS for a GGSN peer profile";
              container ambr {
                description
                    "Configure the Aggregated Maximum Bit Rate (AMBR) to be used in the GTP 
                     messages as APN-AMBR IE";
                leaf down-link {
                  type uint32 {
                    range "0..10000000";
                  }
                } //down-link

                leaf up-link {
                  type uint32 {
                    range "0..10000000";
                  }
                  description
                      "kbps";
                } //up-link

              } //container ambr

              container arp {
                description
                    "Configure the Allocation/Retention Priority";
                leaf arp-value {
                  type uint32 {
                    range "1..3";
                  }
                } //arp-value

              } //container arp

              container down-link {
                description
                    "Configure the down-link bitrate in Kbps to be used in the GTP messages";
                leaf gbr {
                  type uint32 {
                    range "0..100000";
                  }
                  description
                      "rate";
                } //gbr

                leaf mbr {
                  type uint32 {
                    range "0..100000";
                  }
                } //mbr

              } //container down-link

              container up-link {
                description
                    "Configure the up-link bitrate in Kbps to be used in the GTP messages";
                leaf gbr {
                  type uint32 {
                    range "0..100000";
                  }
                } //gbr

                leaf mbr {
                  type uint32 {
                    range "0..100000";
                  }
                  description
                      "rate";
                } //mbr

              } //container up-link

            } //container qos

          } //container ggsn

          container mme {
            description
                "Configure the communication with a Mobility Management Entity";
            container qos {
              description
                  "Configure the QoS for the Mobility Management Entity";
              container ambr {
                description
                    "Configure the Aggregated Maximum Bit Rate (AMBR) to be used in the GTP 
                     messages as AMBR IE";
                leaf down-link {
                  type uint32 {
                    range "0..10000000";
                  }
                } //down-link

                leaf up-link {
                  type uint32 {
                    range "0..10000000";
                  }
                } //up-link

              } //container ambr

              container arp {
                description
                    "Configure the Allocation/Retention Priority";
                leaf arp-value {
                  type uint32 {
                    range "1..15";
                  }
                } //arp-value

              } //container arp

              container down-link {
                description
                    "Configure the down-link bitrate in Kbps to be used in the GTP messages";
                leaf gbr {
                  type uint32 {
                    range "0..100000";
                  }
                } //gbr

                leaf mbr {
                  type uint32 {
                    range "0..100000";
                  }
                } //mbr

              } //container down-link

              container qci {
                description
                    "Configure the QoS Class Identifier (QCI) value to be used in the GTP messages";
                leaf qci-value {
                  type uint32 {
                    range "1..9";
                  }
                } //qci-value

              } //container qci

              container up-link {
                description
                    "Configure the up-link bitrate in Kbps to be used in the GTP messages";
                leaf gbr {
                  type uint32 {
                    range "0..100000";
                  }
                } //gbr

                leaf mbr {
                  type uint32 {
                    range "0..100000";
                  }
                } //mbr

              } //container up-link

            } //container qos

          } //container mme

          container pgw {
            description
                "Configure the communication with a Packet Data Network Gateway";
            container qos {
              description
                  "Configure the QoS for a Packet Data Network Gateway";
              container ambr {
                description
                    "Configure the Aggregated Maximum Bit Rate (AMBR) to be used in the GTP 
                     messages as AMBR IE";
                leaf down-link {
                  type uint32 {
                    range "0..10000000";
                  }
                } //down-link

                leaf up-link {
                  type uint32 {
                    range "0..10000000";
                  }
                  description
                      "kbps";
                } //up-link

              } //container ambr

              container arp {
                description
                    "Configure the Allocation/Retention Priority";
                leaf arp-value {
                  type uint32 {
                    range "1..15";
                  }
                } //arp-value

              } //container arp

              container down-link {
                description
                    "Configure the down-link bitrate in Kbps to be used in the GTP messages";
                leaf gbr {
                  type uint32 {
                    range "0..100000";
                  }
                } //gbr

                leaf mbr {
                  type uint32 {
                    range "0..100000";
                  }
                  description
                      "rate";
                } //mbr

              } //container down-link

              container qci {
                description
                    "Configure the QoS Class Identifier (QCI) value to be used in the GTP messages";
                leaf qci-value {
                  type uint32 {
                    range "1..9";
                  }
                } //qci-value

              } //container qci

              container up-link {
                description
                    "Configure the up-link bitrate in Kbps to be used in the GTP messages";
                leaf gbr {
                  type uint32 {
                    range "0..100000";
                  }
                } //gbr

                leaf mbr {
                  type uint32 {
                    range "0..100000";
                  }
                  description
                      "rate";
                } //mbr

              } //container up-link

            } //container qos

          } //container pgw

        } //list peer-profile

      } //container gtp

      list host-lockout-policy {
        key "policy-name";
        description
            "Configure a host lockout policy";
        leaf policy-name {
          type string {
            length "1..32";
          }
        } //policy-name

        container description {
          description
              "Description for the host lockout policy";
          leaf description-string {
            type string {
              length "1..80";
            }
          } //description-string

        } //container description

        container host-key {
          description
              "Lockout host-key settings";
          leaf host-key-id {
            type enumeration {
              enum mac;
            }
          } //host-key-id

        } //container host-key

        container lockout-reset-time {
          description
              "Lockout reset time settings";
          leaf seconds {
            type int32 {
              range "1..86400";
            }
          } //seconds

        } //container lockout-reset-time

        container lockout-time {
          description
              "Lockout time settings";
          leaf min {
            type int32 {
              range "1..86400";
            }
          } //min

          leaf max {
            type int32 {
              range "1..86400";
            }
          } //max

        } //container lockout-time

        container max-lockout-hosts {
          description
              "Max lockout hosts";
          leaf hosts {
            type int32 {
              range "1..32000";
            }
            default 100;
          } //hosts

        } //container max-lockout-hosts

      } //list host-lockout-policy

      list host-tracking-policy {
        key "policy-name";
        description
            "Configure a host tracking policy";
        leaf policy-name {
          type string {
            length "1..32";
          }
        } //policy-name

        container description {
          description
              "Description for the host tracking policy";
          leaf description-string {
            type string {
              length "1..80";
            }
          } //description-string

        } //container description

        container egress-rate-modify {
          description
              "Configure the egress rate modification";
          leaf agg-rate-limit {
            type boolean;
          } //agg-rate-limit

          leaf scheduler {
            type string {
              length "1..32";
            }
          } //scheduler

        } //container egress-rate-modify

      } //list host-tracking-policy

      list http-redirect-policy {
        key "policy-name";
        description
            "Configure an HTTP redirect policy";
        leaf policy-name {
          type string;
        } //policy-name

        container description {
          description
              "Configure the description";
          leaf description-string {
            type string {
              length "1..80";
            }
          } //description-string

        } //container description

        container dst-port {
          description
              "Configure the TCP destination port number to match";
          leaf tcp-port {
            type uint16 {
              range "1..65535";
            }
          } //tcp-port

        } //container dst-port

        leaf ignore-app-profile {
          type boolean;
          description
              "Ignore/accept application profile attribute in RADIUS Access-Accept message";
        }

        container portal-hold-time {
          description
              "Configure the hold time for re-direct fwd resources after the subscriber has 
               left the portal";
          leaf seconds {
            type uint32 {
              range "1..60";
            }
          } //seconds

        } //container portal-hold-time

        container url {
          description
              "Configure the HTTP URL to re-direct the matching traffic to";
          leaf rdr-url-string {
            type string {
              length "1..255";
            }
            description
                "Attribute rdr-url-string for url";
          } //rdr-url-string

        } //container url

        container forward-entries {
          description
              "Configure traffic flows to be forwarded iso redirected";
          list dst-ip {
            key "ip-address protocol dst-port";
            description
                "Configure a traffic flow to be forwarded";
            leaf ip-address {
              type string;
              description
                  "Attribute ip-address for dst-ip";
            } //ip-address

            leaf protocol {
              type enumeration {
                enum tcp;
                enum udp;
              }
            } //protocol

            leaf dst-port {
              type uint16 {
                range "1..65535";
              }
            } //dst-port

            leaf prefix-length {
              type uint8 {
                range "1..128";
              }
            } //prefix-length

          } //list dst-ip

        } //container forward-entries

      } //list http-redirect-policy

      list igmp-policy {
        key "igmp-policy-name";
        description
            "Configure an IGMP policy";
        leaf igmp-policy-name {
          type string {
            length "1..32";
          }
        } //igmp-policy-name

        container description {
          description
              "Description for the policy";
          leaf description-string {
            type string {
              length "1..80";
            }
          } //description-string

        } //container description

        leaf disable-router-alert-check {
          type boolean;
          description
              "Enable/disable the router alert check option";
        }

        container egress-rate-modify {
          description
              "Configure the egress rate modification";
          leaf agg-rate-limit {
            type boolean;
          } //agg-rate-limit

          leaf scheduler {
            type string {
              length "1..32";
            }
          } //scheduler

        } //container egress-rate-modify

        leaf fast-leave {
          type boolean;
          description
              "Enable/disable fast-leave processing";
        }

        container import {
          description
              "Specify the import policy to filter packets";
          leaf policy-name {
            type string {
              length "1..32";
            }
          } //policy-name

        } //container import

        container max-num-groups {
          description
              "Configure the max number of multicast groups";
          leaf max-num-groups-id {
            type uint32 {
              range "1..16000";
            }
          } //max-num-groups-id

        } //container max-num-groups

        container max-num-grp-sources {
          description
              "Configure the max number of multicast group sources";
          leaf max-num-grp-sources-id {
            type uint16 {
              range "1..32000";
            }
          } //max-num-grp-sources-id

        } //container max-num-grp-sources

        container max-num-sources {
          description
              "Configure the max number of multicast sources";
          leaf max-num-sources-id {
            type int32 {
              range "1..1000";
            }
          } //max-num-sources-id

        } //container max-num-sources

        container per-host-replication {
          description
              "Enable/disable per-host-replication processing";
          leaf per-host-replication-id {
            type enumeration {
              enum uni-mac;
              enum mcast-mac;
            }
          } //per-host-replication-id

        } //container per-host-replication

        container query-interval {
          description
              "Configure the frequency at which Host-Query packets are transmitted";
          leaf seconds {
            type uint32 {
              range "2..1024";
            }
          } //seconds

        } //container query-interval

        container query-last-member-interval {
          description
              "Configure the frequency at which Group-Specific-Query packets are transmitted";
          leaf seconds {
            type uint32 {
              range "1..1023";
            }
          } //seconds

        } //container query-last-member-interval

        container query-response-interval {
          description
              "Configure the time to wait to receive a response to the Host-Query message 
               from the host";
          leaf seconds {
            type uint32 {
              range "1..1023";
            }
          } //seconds

        } //container query-response-interval

        container redirection-policy {
          description
              "Specify the redirection policy";
          leaf policy-name {
            type string {
              length "1..32";
            }
          } //policy-name

        } //container redirection-policy

        container version {
          description
              "Configure the version";
          leaf version {
            type uint32 {
              range "1..3";
            }
            description
                "[1, 2 or 3]";
          } //version

        } //container version

        container mcast-reporting {
          presence
              "Configure the mcast reporting";
          container mcast-reporting-dest {
            description
                "Set/reset mcast reporting destination";
            leaf mcast-reporting-dest-name {
              type string {
                length "1..32";
              }
            } //mcast-reporting-dest-name

          } //container mcast-reporting-dest

          container opt-reporting-fields {
            description
                "Set/reset optional mcast reporting fields";
            leaf host-mac {
              type boolean;
            } //host-mac

            leaf pppoe-session-id {
              type boolean;
            } //pppoe-session-id

            leaf svc-id {
              type boolean;
            } //svc-id

            leaf sap-id {
              type boolean;
            } //sap-id

          } //container opt-reporting-fields

          leaf shutdown {
            type boolean;
            description
                "Administratively enable/disable mcast reporting";
          }

        } //container mcast-reporting

        container static {
          description
              "Add/remove static group membership";
          list group {
            key "grp-ip-address";
            description
                "Add/remove a static multicast group";
            leaf grp-ip-address {
              type inet:ip-address;
              description
                  "a.b.c.d - multicast group address";
            } //grp-ip-address

            list source {
              key "ip-address";
              description
                  "Add/remove a static multicast source";
              leaf ip-address {
                type inet:ip-address;
              } //ip-address

            } //list source

            leaf starg {
              type boolean;
              description
                  "Add/remove a static starg entry";
            }

          } //list group

        } //container static

      } //list igmp-policy

      list ipoe-session-policy {
        key "policy-name";
        description
            "Configure an IPoE session policy";
        leaf policy-name {
          type string {
            length "1..32";
          }
        } //policy-name

        leaf circuit-id-from-auth {
          type boolean;
          description
              "Enable/disable using the Circuit-Id from the authentication server to identify 
               a session";
        }

        container description {
          description
              "Description for the IPoE session policy";
          leaf description-string {
            type string {
              length "1..80";
            }
          } //description-string

        } //container description

        container session-key {
          description
              "Configure the session key";
          leaf sap {
            type boolean;
            description
                "keyword - default is 'sap mac'";
          } //sap

          leaf mac {
            type boolean;
            description
                "keyword - default is 'sap mac'";
          } //mac

          leaf cid {
            type boolean;
            description
                "keyword - cid can not be combined with rid";
          } //cid

          leaf rid {
            type boolean;
            description
                "keyword - rid can not be combined with cid";
          } //rid

        } //container session-key

        container session-timeout {
          description
              "Configure the session timeout interval";
          leaf timeout {
            type uint32 {
              range "1..31104000";
            }
            description
                "[1..31104000] seconds";
          } //timeout

        } //container session-timeout

      } //list ipoe-session-policy

      list isa-filter {
        key "name";
        description
            "Configure an ISA filter";
        leaf name {
          type string;
        } //name

        leaf type {
          type enumeration {
            enum dsm;
            enum lanext;
          }
        } //type

        container default-action {
          description
              "Configure the action to take when no specific filter entry match is found";
          leaf default-action-id {
            type enumeration {
              enum drop;
              enum forward;
            }
          } //default-action-id

        } //container default-action

        container description {
          description
              "Configure a description for the ISA filter";
          leaf description-string {
            type string {
              length "1..80";
            }
          } //description-string

        } //container description

        list entry {
          key "entry-id";
          description
              "Configure an ISA filter entry";
          leaf entry-id {
            type uint32 {
              range "1..1024";
            }
          } //entry-id

          container action {
            description
                "Configure the action to take when a packet matches this filter entry match";
            leaf action-id {
              type enumeration {
                enum drop;
                enum forward;
                enum gtp-local-breakout;
                enum none;
              }
            } //action-id

          } //container action

          container description {
            description
                "Configure a description for the ISA filter entry";
            leaf description-string {
              type string {
                length "1..80";
              }
            } //description-string

          } //container description

          container match {
            description
                "Configure match criteria for the ISA filter entry";
            leaf protocol {
              type enumeration {
                enum any;
                enum icmp;
                enum tcp;
                enum udp;
                enum gre;
              }
            } //protocol

            container dst-ip {
              description
                  "Configure the destination IP prefix to match";
              leaf ip-prefix-length {
                type inet:ip-prefix;
                description
                    "ip-prefix a.b.c.d (host bits must be 0) 
                     length [0..32]";
              } //ip-prefix-length

            } //container dst-ip

            container dst-port {
              description
                  "Configure the destination IP port to match";
              leaf operator {
                type enumeration {
                  enum eq;
                }
              } //operator

              leaf port-number {
                type uint16;
              } //port-number

            } //container dst-port

            container src-ip {
              description
                  "Configure the source IP prefix to match";
              leaf ip-prefix-length {
                type inet:ip-prefix;
                description
                    "ip-prefix a.b.c.d (host bits must be 0) 
                     length [0..32]";
              } //ip-prefix-length

            } //container src-ip

            container src-port {
              description
                  "Configure the source IP port to match";
              leaf operator {
                type enumeration {
                  enum eq;
                }
              } //operator

              leaf port-number {
                type uint16;
              } //port-number

            } //container src-port

          } //container match

        } //list entry

        container ipv6 {
          container default-action {
            description
                "Configure the action to take when no specific filter entry match is found";
            leaf default-action-id {
              type enumeration {
                enum drop;
                enum forward;
              }
            } //default-action-id

          } //container default-action

          list entry {
            key "entry-id";
            description
                "Configure an IPv6 ISA filter entry";
            leaf entry-id {
              type uint32 {
                range "1..1024";
              }
            } //entry-id

            container action {
              description
                  "Configure the action to take when a packet matches this filter entry match";
              leaf action-id {
                type enumeration {
                  enum drop;
                  enum forward;
                  enum gtp-local-breakout;
                  enum none;
                }
              } //action-id

            } //container action

            container description {
              description
                  "Configure a description for the IPv6 ISA filter entry";
              leaf description-string {
                type string {
                  length "1..80";
                }
              } //description-string

            } //container description

            container match {
              description
                  "Configure match criteria for the IPv6 ISA filter entry";
              leaf protocol {
                type enumeration {
                  enum any;
                  enum icmp;
                  enum tcp;
                  enum udp;
                  enum gre;
                }
              } //protocol

              container dst-ip {
                description
                    "Configure the IPv6 destination IP-address to match";
                leaf ipv6-address-prefix-length {
                  type string {
                    length "1..64";
                  }
                  description
                      "IPv6-address x:x:x:x:x:x:x:x (eight 16-bit pieces) 
                       length [0..128]";
                } //ipv6-address-prefix-length

              } //container dst-ip

              container dst-port {
                description
                    "Configure the destination IP-port to match";
                leaf operator {
                  type enumeration {
                    enum eq;
                  }
                } //operator

                leaf port-number {
                  type uint16;
                } //port-number

              } //container dst-port

              container src-ip {
                description
                    "Configure the IPv6 source IP-address to match";
                leaf ipv6-address-prefix-length {
                  type string;
                  description
                      "IPv6-address x:x:x:x:x:x:x:x (eight 16-bit pieces) 
                       length [0..128]";
                } //ipv6-address-prefix-length

              } //container src-ip

              container src-port {
                description
                    "Configure the source IP-port to match";
                leaf operator {
                  type enumeration {
                    enum eq;
                  }
                } //operator

                leaf port-number {
                  type uint16;
                } //port-number

              } //container src-port

            } //container match

          } //list entry

        } //container ipv6

      } //list isa-filter

      list isa-policer {
        key "policer-name";
        description
            "Configure an ISA policer";
        leaf policer-name {
          type string;
        } //policer-name

        leaf type {
          type enumeration {
            enum single-bucket-bandwidth;
            enum dual-bucket-bandwidth;
          }
        } //type

        container action {
          description
              "Configure what to do with in-profile and out-of-profile packets";
          leaf action-id {
            type enumeration {
              enum permit-deny;
              enum priority-mark;
            }
          } //action-id

        } //container action

        container adaptation-rule {
          description
              "Configure the rules to compute the operational rates";
          leaf pir {
            type enumeration {
              enum max;
              enum min;
              enum closest;
            }
          } //pir

          leaf cir {
            type enumeration {
              enum max;
              enum min;
              enum closest;
            }
            description
                "adaptation-rule";
          } //cir

        } //container adaptation-rule

        container cbs {
          description
              "Configure the Committed Burst Size (kilobytes)";
          leaf burst-size {
            type uint32 {
              range "0..131071";
            }
          } //burst-size

        } //container cbs

        container description {
          description
              "Configure a description";
          leaf description-string {
            type string {
              length "1..80";
            }
          } //description-string

        } //container description

        container mbs {
          description
              "Configure the Maximum Burst Size (kilobytes)";
          leaf burst-size {
            type uint32 {
              range "0..131071";
            }
          } //burst-size

        } //container mbs

        container rate {
          description
              "Configure the peak and committed rates for the policer";
          leaf rate {
            type string;
            description
                "[1..100000000|max] Kbps";
          } //rate

          leaf cir {
            type string;
            description
                "[1..100000000|max] Kbps";
          } //cir

        } //container rate

      } //list isa-policer

      uses "conf-svc-chain-r13:alu-conf-svc-chain-r13";
      uses "conf-submgmt-ludb-r13:alu-conf-submgmt-ludb-r13";
      list mld-policy {
        key "mld-policy-name";
        description
            "Configure an MLD policy";
        leaf mld-policy-name {
          type string {
            length "1..32";
          }
        } //mld-policy-name

        container description {
          description
              "Description for the policy";
          leaf description-string {
            type string {
              length "1..80";
            }
          } //description-string

        } //container description

        leaf disable-router-alert-check {
          type boolean;
          description
              "Enable/disable the router alert check option";
        }

        container egress-rate-modify {
          description
              "Configure the egress rate modification";
          leaf agg-rate-limit {
            type boolean;
          } //agg-rate-limit

          leaf scheduler {
            type string {
              length "1..32";
            }
          } //scheduler

        } //container egress-rate-modify

        leaf fast-leave {
          type boolean;
          description
              "Enable/disable fast-leave processing";
        }

        container import {
          description
              "Specify the import policy to filter packets";
          leaf policy-name {
            type string {
              length "1..32";
            }
          } //policy-name

        } //container import

        container max-num-groups {
          description
              "Configure the max number of multicast groups";
          leaf max-num-groups-id {
            type uint32 {
              range "1..16000";
            }
          } //max-num-groups-id

        } //container max-num-groups

        container max-num-grp-sources {
          description
              "Configure the max number of multicast group sources";
          leaf max-num-grp-sources-id {
            type uint16 {
              range "1..32000";
            }
          } //max-num-grp-sources-id

        } //container max-num-grp-sources

        container max-num-sources {
          description
              "Configure the max number of multicast sources";
          leaf max-num-sources-id {
            type int32 {
              range "1..1000";
            }
          } //max-num-sources-id

        } //container max-num-sources

        container per-host-replication {
          description
              "Enable/disable per-host-replication processing";
          leaf per-host-replication-id {
            type enumeration {
              enum uni-mac;
              enum mcast-mac;
            }
          } //per-host-replication-id

        } //container per-host-replication

        container query-interval {
          description
              "Configure the frequency at which Host-Query packets are transmitted";
          leaf seconds {
            type uint32 {
              range "2..1024";
            }
          } //seconds

        } //container query-interval

        container query-last-listener-interval {
          description
              "Configure the frequency at which Group-Specific-Query packets are transmitted";
          leaf seconds {
            type uint32 {
              range "1..1023";
            }
          } //seconds

        } //container query-last-listener-interval

        container query-response-interval {
          description
              "Configure the time to wait to receive a response to the Host-Query message 
               from the host";
          leaf seconds {
            type uint32 {
              range "1..1023";
            }
          } //seconds

        } //container query-response-interval

        container redirection-policy {
          description
              "Specify the redirection policy";
          leaf policy-name {
            type string {
              length "1..32";
            }
          } //policy-name

        } //container redirection-policy

        container version {
          description
              "Configure the version";
          leaf version {
            type int32 {
              range "1..2";
            }
          } //version

        } //container version

        container static {
          description
              "Add/remove static group membership";
          list group {
            key "grp-ipv6-address";
            description
                "Add/remove a static multicast group";
            leaf grp-ipv6-address {
              type inet:ipv6-address;
              description
                  "Attribute grp-ipv6-address for group";
            } //grp-ipv6-address

            list source {
              key "ipv6-address";
              description
                  "Add/remove a static multicast source";
              leaf ipv6-address {
                type inet:ipv6-address;
                description
                    "Attribute ipv6-address for source";
              } //ipv6-address

            } //list source

            leaf starg {
              type boolean;
              description
                  "Add/remove a static starg entry";
            }

          } //list group

        } //container static

      } //list mld-policy

      list msap-policy {
        key "msap-policy-name";
        description
            "Configure a Managed SAP policy";
        leaf msap-policy-name {
          type string {
            length "1..32";
          }
        } //msap-policy-name

        container cpu-protection {
          description
              "Configure CPU protection";
          leaf policy-id {
            type uint32 {
              range "1..255";
            }
          } //policy-id

          leaf mac-monitoring {
            type boolean;
            description
                "keyword - enable MAC monitoring";
          } //mac-monitoring

          leaf ip-src-monitoring {
            type boolean;
            description
                "keyword - enable monitoring per IP source address";
          } //ip-src-monitoring

        } //container cpu-protection

        container description {
          description
              "Description for the Managed SAP policy";
          leaf description-string {
            type string {
              length "1..80";
            }
          } //description-string

        } //container description

        container dist-cpu-protection {
          description
              "Assign Distributed CPU protection policy for the SAP";
          leaf policy-name {
            type string;
          } //policy-name

        } //container dist-cpu-protection

        container lag-link-map-profile {
          description
              "Configure lag link map profile";
          leaf link-map-profile-id {
            type string;
            description
                "Attribute link-map-profile-id for lag-link-map-profile";
          } //link-map-profile-id

        } //container lag-link-map-profile

        leaf sticky-msaps {
          type boolean;
          description
              "Enable/disable managed SAP stickiness. Idle sticky managed SAP's are not 
               automatically removed";
        }

        container atm {
          description
              "Configure ATM";
          container egress {
            description
                "Configure egress properties";
            container traffic-desc {
              description
                  "Assign ATM traffic descriptor profile";
              leaf traffic-desc-id {
                type int32 {
                  range "1..1000";
                }
              } //traffic-desc-id

            } //container traffic-desc

          } //container egress

          container ingress {
            description
                "Configure ingress properties";
            container traffic-desc {
              description
                  "Assign ATM traffic descriptor profile";
              leaf traffic-desc-id {
                type int32 {
                  range "1..1000";
                }
              } //traffic-desc-id

            } //container traffic-desc

          } //container ingress

          container oam {
            description
                "Configure OAM properties";
            leaf alarm-cells {
              type boolean;
              description
                  "Disable/enable handling and generation of AIS/RDI";
            }

            leaf periodic-loopback {
              type boolean;
              description
                  "Disable/enable periodic loopback cells";
            }

          } //container oam

        } //container atm

        container ies-vprn-only-sap-parameters {
          description
              "Configure Managed SAP IES/VPRN properties";
          container anti-spoof {
            description
                "Configures anti-spoof filtering for the MSAP";
            leaf ip-mac-nh-mac {
              type enumeration {
                enum ip-mac;
                enum nh-mac;
              }
              description
                  "keywords";
            } //ip-mac-nh-mac

          } //container anti-spoof

          container egress {
            description
                "Configure egress parameters";
            container qos {
              description
                  "Apply an egress qos policy";
              leaf policy-id {
                type string;
                description
                    "[1..65535]|<name:64 char max>";
              } //policy-id

            } //container qos

          } //container egress

          container ingress {
            description
                "Configure ingress parameters";
            container qos {
              description
                  "Apply an ingress qos policy";
              leaf policy-id {
                type string;
                description
                    "[1..65535]|<name:64 char max>";
              } //policy-id

              leaf shared-queuing-service-queuing {
                type enumeration {
                  enum shared-queuing;
                  enum service-queuing;
                }
                description
                    "keywords - specify queuing-type";
              } //shared-queuing-service-queuing

            } //container qos

          } //container ingress

        } //container ies-vprn-only-sap-parameters

        container igmp-host-tracking {
          description
              "Configure Managed SAP IGMP host tracking parameters";
          container expiry-time {
            description
                "Configure the time that the system continues to track inactive hosts";
            leaf expiry-time {
              type uint32 {
                range "1..65535";
              }
              description
                  "[1..65535] seconds";
            } //expiry-time

          } //container expiry-time

          container import {
            description
                "Specify the import policy to filter IGMP packets";
            leaf policy-name {
              type string {
                length "1..32";
              }
            } //policy-name

          } //container import

          container max-num-groups {
            description
                "Configure the max number of multicast groups allowed to be tracked";
            leaf max-num-groups-id {
              type uint32 {
                range "1..16000";
              }
            } //max-num-groups-id

          } //container max-num-groups

          container max-num-grp-sources {
            description
                "Configure the max number of combinations of group and source";
            leaf max-num-grp-sources-id {
              type uint16 {
                range "1..32000";
              }
            } //max-num-grp-sources-id

          } //container max-num-grp-sources

          container max-num-sources {
            description
                "Configure the max number of multicast sources allowed to be tracked per group";
            leaf max-num-sources-id {
              type uint32 {
                range "1..1000";
              }
            } //max-num-sources-id

          } //container max-num-sources

        } //container igmp-host-tracking

        container sub-sla-mgmt {
          description
              "Configure Managed SAP subscriber policies and profiles";
          container def-app-profile {
            description
                "Configure default application profile";
            leaf app-profile-name {
              type string {
                length "1..32";
              }
            } //app-profile-name

          } //container def-app-profile

          container def-inter-dest-id {
            description
                "Configure default inter-dest-id";
            leaf string {
              type string {
                length "1..32";
              }
            } //string

            leaf def-inter-dest-id-id {
              type enumeration {
                enum use-top-q;
                enum use-vpi;
              }
            } //def-inter-dest-id-id

          } //container def-inter-dest-id

          container def-sla-profile {
            description
                "Configure default SLA profile";
            leaf sla-profile-name {
              type string {
                length "1..32";
              }
            } //sla-profile-name

          } //container def-sla-profile

          container def-sub-id {
            description
                "Configure default subscriber id";
            leaf use-sap-id {
              type boolean;
            } //use-sap-id

            leaf string {
              type string;
              description
                  "Attribute sub-id for def-sub-id";
            } //string

            leaf use-auto-id {
              type boolean;
              description
                  "keyword - use auto-generated subscriber-id";
            } //use-auto-id

          } //container def-sub-id

          container def-sub-profile {
            description
                "Configure default subscriber profile";
            leaf sub-profile-name {
              type string {
                length "1..32";
              }
            } //sub-profile-name

          } //container def-sub-profile

          container multi-sub-sap {
            description
                "Configure multi subscriber sap limit";
            leaf limit {
              type uint32 {
                range "1..131071";
              }
              description
                  "Attribute limit for multi-sub-sap";
            } //limit

          } //container multi-sub-sap

          container sub-ident-policy {
            description
                "Configure subscriber identification policy";
            leaf policy-name {
              type string {
                length "1..32";
              }
            } //policy-name

          } //container sub-ident-policy

          container single-sub-parameters {
            description
                "Configure the single-sub-parameters";
            container non-sub-traffic {
              description
                  "Configure non-subscriber-traffic profiles";
              leaf sub-profile {
                type string {
                  length "1..32";
                }
              } //sub-profile

              leaf sla-profile {
                type string {
                  length "1..32";
                }
              } //sla-profile

              leaf subscriber {
                type string;
                description
                    "Attribute sub-ident-string for non-sub-traffic";
              } //subscriber

              leaf app-profile {
                type string {
                  length "1..32";
                }
              } //app-profile

            } //container non-sub-traffic

            leaf profiled-traffic-only {
              type boolean;
              description
                  "Enable/disable profiled-traffic-only";
            }

          } //container single-sub-parameters

        } //container sub-sla-mgmt

        container vpls-only-sap-parameters {
          description
              "Configure Managed SAP VPLS properties";
          container arp-reply-agent {
            description
                "Enable/disable arp-reply-agent function";
            leaf sub-ident {
              type boolean;
            } //sub-ident

          } //container arp-reply-agent

          leaf mac-da-hashing {
            type boolean;
            description
                "Enable/disable hashing on MAC DA iso subscriber id";
          }

          container split-horizon-group {
            description
                "Configure a split horizon group";
            leaf group-name {
              type string {
                length "1..32";
              }
            } //group-name

          } //container split-horizon-group

          container arp-host {
            description
                "Configure ARP host parameters";
            container host-limit {
              description
                  "Configure the maximum number of ARP hosts";
              leaf max-num-hosts {
                type int32 {
                  range "1..131071";
                }
                description
                    "Attribute max-num-hosts for host-limit";
              } //max-num-hosts

            } //container host-limit

            container min-auth-interval {
              description
                  "Configure the minimum authentication interval";
              leaf min-auth-interval {
                type uint32 {
                  range "1..6000";
                }
                description
                    "[1..6000] minutes";
              } //min-auth-interval

            } //container min-auth-interval

          } //container arp-host

          container dhcp {
            description
                "Configures IPOE parameters for the Managed SAPs";
            container lease-populate {
              description
                  "Configure the maximum number of DHCPv4 leases per Managed SAP";
              leaf nbr-of-leases {
                type int32 {
                  range "1..131071";
                }
                description
                    "Attribute nbr-of-leases for lease-populate";
              } //nbr-of-leases

            } //container lease-populate

            container option {
              presence
                  "Configure the IPOE information options";
              container action {
                description
                    "Configure the IPOE option action";
                leaf dhcp-action {
                  type enumeration {
                    enum replace;
                    enum drop;
                    enum keep;
                  }
                  description
                      "replace|drop|keep - keywords";
                } //dhcp-action

              } //container action

              container circuit-id {
                description
                    "Configure the circuit-id suboption of the IPOE Relay packet";
                leaf ascii-tuple {
                  type boolean;
                } //ascii-tuple

                leaf vlan-ascii-tuple {
                  type boolean;
                } //vlan-ascii-tuple

              } //container circuit-id

              container remote-id {
                description
                    "Configure the remote-id suboption of the IPOE Relay packet";
                leaf mac {
                  type boolean;
                } //mac

                leaf string {
                  type string {
                    length "1..32";
                  }
                  description
                      "Max 32 chars";
                } //string

              } //container remote-id

              container vendor-specific-option {
                presence
                    "Configure the Nokia vendor specific suboption of the IPOE Relay packet";
                leaf client-mac-address {
                  type boolean;
                  description
                      "Enable/disable sending of the MAC address in the Nokia vendor specific 
                       suboption of the IPOE Relay packet";
                }

                leaf sap-id {
                  type boolean;
                  description
                      "Enable/disable sending of the SAP-id in the Nokia vendor specific suboption of 
                       the IPOE Relay packet";
                }

                leaf service-id {
                  type boolean;
                  description
                      "Enable/disable sending of the service-id in the Nokia vendor specific 
                       suboption of the IPOE Relay packet";
                }

                container string {
                  description
                      "Specifies the string in the Nokia vendor specific suboption of the IPOE Relay 
                       packet";
                  leaf text {
                    type string {
                      length "1..32";
                    }
                  } //text

                } //container string

                leaf system-id {
                  type boolean;
                  description
                      "Enable/disable sending of the system-id in the Nokia vendor specific suboption 
                       of the IPOE Relay packet";
                }

              } //container vendor-specific-option

            } //container option

            container proxy-server {
              description
                  "Configure the IPOE proxy server";
              container emulated-server {
                description
                    "Specify the emulated server address";
                leaf ip-address {
                  type inet:ip-address;
                } //ip-address

              } //container emulated-server

              container lease-time {
                description
                    "Configure the IPOE lease time";
                leaf days {
                  type int32 {
                    range "0..3650";
                  }
                } //days

                leaf hrs {
                  type int32 {
                    range "0..23";
                  }
                } //hrs

                leaf min {
                  type int32 {
                    range "0..59";
                  }
                } //min

                leaf sec {
                  type int32 {
                    range "0..59";
                  }
                } //sec

                leaf radius-override {
                  type boolean;
                } //radius-override

              } //container lease-time

              leaf shutdown {
                type boolean;
                description
                    "Administratively enable/disable IPOE proxy on this SAP";
              }

            } //container proxy-server

          } //container dhcp

          container egress {
            description
                "Configures egress policies for the Managed SAPs";
            container multicast-group {
              status "obsolete";
              description
                  "Configure egress multicast group";
              leaf group-name {
                type string {
                  length "1..32";
                }
              } //group-name

            } //container multicast-group

            container qos {
              description
                  "Apply an egress qos policy";
              leaf policy-id {
                type string;
                description
                    "[1..65535]|<name:64 char max>";
              } //policy-id

            } //container qos

          } //container egress

          container igmp-snooping {
            description
                "Configure IGMP snooping parameters";
            leaf fast-leave {
              type boolean;
              description
                  "Enable/disable IGMP fast-leave processing";
            }

            container import {
              description
                  "Import a policy to filter IGMP packets";
              leaf policy-name {
                type string {
                  length "1..32";
                }
              } //policy-name

            } //container import

            container last-member-query-interval {
              description
                  "Configure the IGMP Last Member Query Interval";
              leaf t1-10-seconds {
                type uint32 {
                  range "1..50";
                }
              } //t1-10-seconds

            } //container last-member-query-interval

            container max-num-groups {
              description
                  "Configure the max number of multicast groups allowed";
              leaf max-num-groups-id {
                type uint32 {
                  range "1..16000";
                }
              } //max-num-groups-id

            } //container max-num-groups

            container query-interval {
              description
                  "Configure the IGMP Query Interval";
              leaf seconds {
                type uint32 {
                  range "2..1024";
                }
              } //seconds

            } //container query-interval

            container query-response-interval {
              description
                  "Configure the IGMP Query Response Interval";
              leaf seconds {
                type uint32 {
                  range "1..1023";
                }
              } //seconds

            } //container query-response-interval

            container robust-count {
              description
                  "Configure the IGMP Robustness Variable";
              leaf robust-count {
                type uint32 {
                  range "2..7";
                }
              } //robust-count

            } //container robust-count

            leaf send-queries {
              type boolean;
              description
                  "Enable/disable generation of IGMP General Queries";
            }

            container version {
              description
                  "Configure the version of IGMP";
              leaf version {
                type uint32 {
                  range "1..3";
                }
                description
                    "[1, 2 or 3]";
              } //version

            } //container version

            container mcac {
              description
                  "Configure multicast CAC policy and constraints for this SAP";
              container if-policy {
                description
                    "Configure multicast CAC if-policy";
                leaf if-policy-name {
                  type string {
                    length "1..32";
                  }
                } //if-policy-name

              } //container if-policy

              container policy {
                description
                    "Enable/disable multicast CAC policy";
                leaf policy-name {
                  type string {
                    length "1..32";
                  }
                  description
                      "max 32 chars";
                } //policy-name

              } //container policy

              container unconstrained-bw {
                description
                    "Set/reset unconstrained-bw for multicast CAC policy on this SAP";
                leaf bandwidth {
                  type int32 {
                    range "0..2147483647";
                  }
                } //bandwidth

                leaf mandatory-bw {
                  type int32 {
                    range "0..2147483647";
                  }
                } //mandatory-bw

              } //container unconstrained-bw

              container mc-constraints {
                description
                    "create context that allows for the configuration of the different levels and 
                     their associated bandwidth for multicast CAC policy on this SAP";
                list level {
                  key "level-id";
                  description
                      "Configure levels and their associated bandwidth for multicast CAC policy on 
                       this SAP";
                  leaf level-id {
                    type uint32 {
                      range "1..8";
                    }
                  } //level-id

                  leaf bw {
                    type uint32;
                    description
                        "[0..4294967295] kbps";
                  } //bw

                } //list level

                list number-down {
                  key "number-lag-port-down";
                  description
                      "Configure number of ports down along with level for multicast CAC policy on 
                       this SAP";
                  leaf number-lag-port-down {
                    type string;
                    description
                        "Attribute number-lag-port-down for number-down";
                  } //number-lag-port-down

                  leaf level {
                    type uint32 {
                      range "1..8";
                    }
                  } //level

                } //list number-down

                leaf use-lag-port-weight {
                  type boolean;
                  description
                      "Enable/disable using the LAG port weight while calculating Multicast CAC 
                       constraints";
                }

              } //container mc-constraints

            } //container mcac

            container mvr {
              description
                  "Configure Multicast VPLS Registration parameters";
              container from-vpls {
                description
                    "The MVR VPLS from which the multicast channels are taken";
                leaf service-id {
                  type string;
                  description
                      "Attribute service-id for from-vpls";
                } //service-id

              } //container from-vpls

            } //container mvr

          } //container igmp-snooping

          container ingress {
            description
                "Configure ingress parameters";
            container qos {
              description
                  "Apply an ingress qos policy";
              leaf policy-id {
                type string;
                description
                    "[1..65535]|<name:64 char max>";
              } //policy-id

              leaf multipoint-shared-service-queuing {
                type enumeration {
                  enum multipoint-shared;
                  enum service-queuing;
                }
                description
                    "keywords - specify queuing-type";
              } //multipoint-shared-service-queuing

            } //container qos

          } //container ingress

        } //container vpls-only-sap-parameters

      } //list msap-policy

      list pim-policy {
        key "name";
        description
            "Configure a Protocol Independent Multicast (PIM) policy";
        leaf name {
          type string;
        } //name

        container description {
          description
              "Configure a descriptive text for this PIM policy";
          leaf description-string {
            type string {
              length "1..80";
            }
          } //description-string

        } //container description

      } //list pim-policy

      list ppp-policy {
        key "ppp-policy-name";
        description
            "Configure a PPP policy";
        leaf ppp-policy-name {
          type string {
            length "1..32";
          }
        } //ppp-policy-name

        container default-pap-password {
          description
              "Configure the default PAP password, to be used when the PPP client does not 
               provide a password during PAP authentication";
          leaf password {
            type string {
              length "1..500";
            }
            description
                "password - [64 chars max] 
                 hash-key 
                 hash2-key 
                 custom-key";
          } //password

          leaf hash-hash2-custom {
            type enumeration {
              enum hash;
              enum hash2;
              enum custom;
            }
          } //hash-hash2-custom

        } //container default-pap-password

        container default-user-name {
          description
              "Configure the default PPP username, to be used when the PPP client does not 
               provide a username during PAP or CHAP authentication; without a username, 
               authentication fails";
          leaf ppp-username {
            type string {
              length "1..253";
            }
          } //ppp-username

        } //container default-user-name

        container description {
          description
              "Description for the PPP policy";
          leaf description-string {
            type string {
              length "1..80";
            }
          } //description-string

        } //container description

        leaf disable-cookies {
          type boolean;
          description
              "Enable/disable the use of AC-Cookie tags";
        }

        leaf force-ppp-mtu-gt-1492 {
          type boolean;
          description
              "Force the PPPoE MTU size to go above 1492 without RFC 4638";
        }

        leaf ipcp-subnet-negotiation {
          type boolean;
          description
              "Configure the IPCP subnet negotiation";
        }

        container keepalive {
          description
              "Configure the PPP keepalive interval and multiplier";
          leaf seconds {
            type uint32 {
              range "4..300";
            }
          } //seconds

          leaf hold-up-multiplier {
            type uint32 {
              range "1..5";
            }
          } //hold-up-multiplier

        } //container keepalive

        leaf lcp-ignore-magic-numbers {
          type boolean;
          description
              "Disable/enable checking the Magic-Number field in LCP Echo-Request and LCP 
               Echo-Reply messages";
        }

        container max-sessions-per-mac {
          description
              "Configure the maximum number of sessions per MAC";
          leaf sessions {
            type uint32 {
              range "1..8191";
            }
          } //sessions

          leaf allow-same-circuit-id-for-dhcp {
            type boolean;
          } //allow-same-circuit-id-for-dhcp

        } //container max-sessions-per-mac

        container pado-ac-name {
          description
              "Configure the Access-Concentrator-Name to send with a PADO";
          leaf name {
            type string {
              length "1..128";
            }
          } //name

        } //container pado-ac-name

        container pado-delay {
          description
              "Configure the delay timeout before sending a PADO";
          leaf deci-seconds {
            type uint32 {
              range "1..30";
            }
          } //deci-seconds

        } //container pado-delay

        container ppp-authentication {
          description
              "Configure the PPP authentication protocol to negotiate";
          leaf ppp-authentication-id {
            type enumeration {
              enum pap;
              enum chap;
              enum pref-chap;
              enum pref-pap;
            }
          } //ppp-authentication-id

        } //container ppp-authentication

        container ppp-chap-challenge-length {
          description
              "Configure the max and min PPP CHAP challenge length";
          leaf min {
            type uint32 {
              range "8..64";
            }
          } //min

          leaf max {
            type uint32 {
              range "8..64";
            }
          } //max

        } //container ppp-chap-challenge-length

        container ppp-initial-delay {
          description
              "Configure the delay timeout before starting the PPP stack";
        }

        container ppp-mtu {
          description
              "Configure the maximum PPP MTU size";
          leaf mtu-bytes {
            type uint32 {
              range "512..9212";
            }
          } //mtu-bytes

        } //container ppp-mtu

        container re-establish-session {
          description
              "Enable/disable to reconnect and override an existing session";
          leaf padr {
            type boolean;
            description
                "keyword; override existing session";
          } //padr

        } //container re-establish-session

        leaf reject-disabled-ncp {
          type boolean;
          description
              "Enable/disable reject disabled NCP";
        }

        leaf reply-on-padt {
          type boolean;
          description
              "Enable/disable reply on PADT packets";
        }

        container session-timeout {
          description
              "Configure the session timeout interval";
          leaf timeout {
            type uint32 {
              range "1..31104000";
            }
            description
                "[1..31104000] seconds";
          } //timeout

        } //container session-timeout

        container unique-sid-per-sap {
          description
              "Enable/disable generation of per SAP session-id";
          leaf per-msap {
            type boolean;
            description
                "keyword; allocate session-id map per MSAP";
          } //per-msap

        } //container unique-sid-per-sap

        container mlppp {
          description
              "Configure MLPPP parameters";
          leaf accept-mrru {
            type boolean;
            description
                "Accept Multilink MRRU LCP option";
          }

          container endpoint {
            description
                "Configure the endpoint ID";
            leaf ip {
              type inet:ip-address;
              description
                  "a.b.c.d";
            } //ip

            leaf mac {
              type alu:ieee-address;
              description
                  "xx:xx:xx:xx:xx:xx or xx-xx-xx-xx-xx-xx (cannot be all zeros)";
            } //mac

            leaf system-ip {
              type boolean;
            } //system-ip

            leaf system-mac {
              type boolean;
            } //system-mac

          } //container endpoint

          leaf short-sequence-numbers {
            type boolean;
            description
                "Request the peer to send us short sequence numbers";
          }

        } //container mlppp

        container ppp-options {
          description
              "Configure PPP options";
          list custom-option {
            key "protocol option-number";
            description
                "Configure a PPP option";
            leaf protocol {
              type enumeration {
                enum lcp;
                enum ipcp;
                enum ipv6cp;
              }
            } //protocol

            leaf option-number {
              type uint32 {
                range "0..255";
              }
            } //option-number

            leaf address {
              type inet:ip-address;
            } //address

            leaf string {
              type string {
                length "1..127";
              }
            } //string

            leaf hex {
              type string {
              }
              description
                  "[0x0..0xFFFFFF...(max 254 hex nibbles)]";
            } //hex

          } //list custom-option

        } //container ppp-options

      } //list ppp-policy

      list pppoe-client-policy {
        key "pppoe-client-policy-name";
        description
            "Configure a PPPoE client policy";
        leaf pppoe-client-policy-name {
          type string {
            length "1..32";
          }
        } //pppoe-client-policy-name

        container description {
          description
              "Description for the PPPoE client policy";
          leaf description-string {
            type string {
              length "1..80";
            }
          } //description-string

        } //container description

        container keepalive {
          description
              "Configure the PPPoE keepalive interval and multiplier";
          leaf seconds {
            type uint32 {
              range "10..300";
            }
          } //seconds

          leaf hold-up-multiplier {
            type uint32 {
              range "1..5";
            }
          } //hold-up-multiplier

        } //container keepalive

        container mru {
          description
              "Configure the PPPoE MRU";
          leaf mru-bytes {
            type uint32 {
              range "512..9154";
            }
          } //mru-bytes

        } //container mru

        container mtu {
          description
              "Configure the PPPoE MTU";
          leaf mtu-bytes {
            type uint32 {
              range "512..9154";
            }
          } //mtu-bytes

        } //container mtu

        container python-policy {
          description
              "Configure the Python policy to be applied to all messages in the PPPoE client 
               policy";
          leaf name {
            type string;
          } //name

        } //container python-policy

        container restart-backoff {
          description
              "Configure the exponential backoff mechanism, used to restart the PPPoE client 
               after failure";
          leaf initial-time {
            type uint32 {
              range "10..3600";
            }
          } //initial-time

          leaf max-time {
            type uint32 {
              range "10..3600";
            }
          } //max-time

        } //container restart-backoff

        container stack {
          description
              "Configure which NCP sessions will be started in the PPPoE client : IPCP for 
               IPv4 and/or IPv6CP/SLAAC for IPv6";
          leaf ipv4 {
            type boolean;
            description
                "start IPCP and use it to retrieve an IPv4 address";
          } //ipv4

          leaf ipv6-slaac {
            type boolean;
            description
                "start IPv6CP and use SLAAC to retrieve an IPv6 address";
          } //ipv6-slaac

        } //container stack

      } //list pppoe-client-policy

      list radius-accounting-policy {
        key "name";
        description
            "Configure a RADIUS accounting policy";
        leaf name {
          type string {
            length "1..32";
          }
        } //name

        container acct-request-script-policy {
          description
              "Configure RADIUS script policy to modify Accounting-Request";
          leaf policy-name {
            type string {
              length "1..32";
            }
          } //policy-name

        } //container acct-request-script-policy

        container acct-tunnel-connection-fmt {
          description
              "Configure the accounting tunnel connection ascii-specification";
          leaf ascii-spec {
            type string {
              length "1..253";
            }
            description
                "Attribute ascii-spec for acct-tunnel-connection-fmt";
          } //ascii-spec

        } //container acct-tunnel-connection-fmt

        container delay-start-time {
          description
              "Configure the accounting-start delay (in sec)";
          leaf delay {
            type uint32 {
              range "1..10";
            }
            description
                "[1..10 seconds]";
          } //delay

        } //container delay-start-time

        container description {
          description
              "Description for this accounting policy";
          leaf description-string {
            type string {
              length "1..80";
            }
          } //description-string

        } //container description

        container host-accounting {
          description
              "Enable/disable per-host accounting";
          leaf interim-update {
            type boolean;
            description
                "keyword";
          } //interim-update

        } //container host-accounting

        container mcs-interval {
          description
              "Configure the mcs update interval";
          leaf minutes {
            type uint32 {
              range "5..60";
            }
          } //minutes

          leaf use-update-interval {
            type boolean;
          } //use-update-interval

        } //container mcs-interval

        container queue-instance-accounting {
          description
              "Enable/disable per-queue-instance accounting";
          leaf interim-update {
            type boolean;
            description
                "keyword";
          } //interim-update

        } //container queue-instance-accounting

        container radius-server-policy {
          description
              "Configure a RADIUS server policy for this policy";
          leaf radius-server-policy-name {
            type string {
              length "1..32";
            }
          } //radius-server-policy-name

        } //container radius-server-policy

        container session-accounting {
          description
              "Enable/disable per-session accounting";
          leaf interim-update {
            type boolean;
            description
                "keyword";
          } //interim-update

          leaf host-update {
            type boolean;
            description
                "keyword";
          } //host-update

        } //container session-accounting

        container session-id-format {
          description
              "Configure the format used in accounting session-id attributes";
          leaf description-number {
            type enumeration {
              enum description;
              enum number;
            }
            description
                "keywords";
          } //description-number

        } //container session-id-format

        container update-interval {
          description
              "Configure the intermediate update interval";
          leaf minutes {
            type uint32 {
              range "5..259200";
            }
          } //minutes

        } //container update-interval

        container update-interval-jitter {
          description
              "Configure the intermediate update interval jitter";
          leaf absolute {
            type uint32 {
              range "0..3600";
            }
            description
                "[0..3600]";
          } //absolute

        } //container update-interval-jitter

        container custom-record {
          presence
              "Configure the accounting policy custom record";
          container significant-change {
            description
                "Configure the significant change required to generate the record";
            leaf delta {
              type uint32;
            } //delta

          } //container significant-change

          list override-counter {
            key "override-counter-id";
            description
                "Configure an override counter";
            leaf override-counter-id {
              type uint32 {
                range "1..8";
              }
            } //override-counter-id

            container e-counters {
              presence
                  "Configure egress counters for this override";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this override";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-packets-discarded-count {
                type boolean;
                description
                    "include/exclude the high packets discarded count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-packets-discarded-count {
                type boolean;
                description
                    "include/exclude the low packets discarded count";
              }

              leaf out-profile-octets-forwarded-count {
                type boolean;
                description
                    "include/exclude the out profile octets forwarded count";
              }

              leaf out-profile-packets-forwarded-count {
                type boolean;
                description
                    "include/exclude the out profile packets forwarded count";
              }

            } //container i-counters

          } //list override-counter

          list queue {
            key "queue-id";
            description
                "Configure a queue";
            leaf queue-id {
              type int32 {
                range "1..32";
              }
            } //queue-id

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-octets-offered-count {
                type boolean;
                description
                    "include/exclude the high octets offered count";
              }

              leaf high-packets-discarded-count {
                type boolean;
                description
                    "include/exclude the high packets discarded count";
              }

              leaf high-packets-offered-count {
                type boolean;
                description
                    "include/exclude the high packets offered count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-octets-offered-count {
                type boolean;
                description
                    "include/exclude the low octets offered count";
              }

              leaf low-packets-discarded-count {
                type boolean;
                description
                    "include/exclude the low packets discarded count";
              }

              leaf low-packets-offered-count {
                type boolean;
                description
                    "include/exclude the low packets offered count";
              }

              leaf out-profile-octets-forwarded-count {
                type boolean;
                description
                    "include/exclude the out profile octets forwarded count";
              }

              leaf out-profile-packets-forwarded-count {
                type boolean;
                description
                    "include/exclude the out profile packets forwarded count";
              }

              leaf uncoloured-octets-offered-count {
                type boolean;
                description
                    "include/exclude the uncoloured octets offered count";
              }

              leaf uncoloured-packets-offered-count {
                type boolean;
                description
                    "include/exclude the uncoloured packets offered count";
              }

            } //container i-counters

          } //list queue

          container ref-override-counter {
            description
                "Configure a reference override counter";
            leaf ref-override-counter-id {
              type uint32 {
                range "1..8";
              }
            } //ref-override-counter-id

            leaf all {
              type boolean;
            } //all

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-packets-discarded-count {
                type boolean;
                description
                    "include/exclude the high packets discarded count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-packets-discarded-count {
                type boolean;
                description
                    "include/exclude the low packets discarded count";
              }

              leaf out-profile-octets-forwarded-count {
                type boolean;
                description
                    "include/exclude the out profile octets forwarded count";
              }

              leaf out-profile-packets-forwarded-count {
                type boolean;
                description
                    "include/exclude the out profile packets forwarded count";
              }

            } //container i-counters

          } //container ref-override-counter

          container ref-queue {
            description
                "Configure a reference queue";
            leaf queue-id {
              type int32 {
                range "1..32";
              }
            } //queue-id

            leaf all {
              type boolean;
            } //all

            container e-counters {
              presence
                  "Configure egress counters for this queue";
              leaf all {
                type boolean;
                description
                    "include all counters";
              }

              leaf in-profile-octets-discarded-count {
                type boolean;
                description
                    "include/exclude the in profile octets discarded count";
              }

              leaf in-profile-octets-forwarded-count {
                type boolean;
                description
                    "include/exclude the in profile octets forwarded count";
              }

              leaf in-profile-packets-discarded-count {
                type boolean;
                description
                    "include/exclude the in profile packets discarded count";
              }

              leaf in-profile-packets-forwarded-count {
                type boolean;
                description
                    "include/exclude the in profile packets forwarded count";
              }

              leaf out-profile-octets-discarded-count {
                type boolean;
                description
                    "include/exclude the out profile octets discarded count";
              }

              leaf out-profile-octets-forwarded-count {
                type boolean;
                description
                    "include/exclude the out profile octets forwarded count";
              }

              leaf out-profile-packets-discarded-count {
                type boolean;
                description
                    "include/exclude the out profile packets discarded count";
              }

              leaf out-profile-packets-forwarded-count {
                type boolean;
                description
                    "include/exclude the out profile packets forwarded count";
              }

            } //container e-counters

            container i-counters {
              presence
                  "Configure ingress counters for this queue";
              leaf all {
                type boolean;
                description
                    "include all counters";
              }

              leaf all-octets-offered-count {
                type boolean;
                description
                    "include/exclude the all octets offered count";
              }

              leaf all-packets-offered-count {
                type boolean;
                description
                    "include/exclude the all packets offered count";
              }

              leaf high-octets-discarded-count {
                type boolean;
                description
                    "include/exclude the high octets discarded count";
              }

              leaf high-octets-offered-count {
                type boolean;
                description
                    "include/exclude the high octets offered count";
              }

              leaf high-packets-discarded-count {
                type boolean;
                description
                    "include/exclude the high packets discarded count";
              }

              leaf high-packets-offered-count {
                type boolean;
                description
                    "include/exclude the high packets offered count";
              }

              leaf in-profile-octets-forwarded-count {
                type boolean;
                description
                    "include/exclude the in profile octets forwarded count";
              }

              leaf in-profile-packets-forwarded-count {
                type boolean;
                description
                    "include/exclude the in profile packets forwarded count";
              }

              leaf low-octets-discarded-count {
                type boolean;
                description
                    "include/exclude the low octets discarded count";
              }

              leaf low-octets-offered-count {
                type boolean;
                description
                    "include/exclude the low octets offered count";
              }

              leaf low-packets-discarded-count {
                type boolean;
                description
                    "include/exclude the low packets discarded count";
              }

              leaf low-packets-offered-count {
                type boolean;
                description
                    "include/exclude the low packets offered count";
              }

              leaf out-profile-octets-forwarded-count {
                type boolean;
                description
                    "include/exclude the out profile octets forwarded count";
              }

              leaf out-profile-packets-forwarded-count {
                type boolean;
                description
                    "include/exclude the out profile packets forwarded count";
              }

              leaf uncoloured-octets-offered-count {
                type boolean;
                description
                    "include/exclude the uncoloured octets offered count";
              }

              leaf uncoloured-packets-offered-count {
                type boolean;
                description
                    "include/exclude the uncoloured packets offered count";
              }

            } //container i-counters

          } //container ref-queue

        } //container custom-record

        container include-radius-attribute {
          presence
              "Configure RADIUS attributes to be included";
          leaf access-loop-options {
            type boolean;
            description
                "Enable/disable include of the access-loop-options attribute";
          }

          leaf acct-authentic {
            type boolean;
            description
                "Enable/disable include of the acct-authentic attribute";
          }

          leaf acct-delay-time {
            type boolean;
            description
                "Enable/disable include of the acct-delay-time attribute";
          }

          leaf alc-acct-triggered-reason {
            type boolean;
            description
                "Enable/disable include of alc-acct-triggered-reason attribute";
          }

          leaf alc-error-code {
            type boolean;
            description
                "Enable/disable include of detailed error codes";
          }

          leaf all-authorized-session-addresses {
            type boolean;
            description
                "Enable/disable include of all included and authorized address/prefix 
                 attributes in session accounting";
          }

          leaf apn {
            type boolean;
            description
                "Enable/disable include of the APN attribute";
          }

          leaf bearer-fteid {
            type boolean;
            description
                "Enable/disable include of the Gtp-Bearer-Fteid attribute";
          }

          leaf bonding-active-connections {
            type boolean;
            description
                "Enable/disable including the Radius attribute Alc-Bonding-Active-Connections";
          }

          leaf bonding-id {
            type boolean;
            description
                "Enable/disable including the Radius attribute Alc-Bonding-Id";
          }

          leaf brg-num-active-sessions {
            type boolean;
            description
                "Enable/disable including the Radius attribute Alc-BRG-Num-Active-Sessions";
          }

          leaf called-station-id {
            type boolean;
            description
                "Enable/disable include of called-station-id attribute";
          }

          container calling-station-id {
            description
                "Enable/disable include of calling-station-id attribute";
            leaf calling-station-id-id {
              type enumeration {
                enum llid;
                enum mac;
                enum remote-id;
                enum sap-id;
                enum sap-string;
              }
            } //calling-station-id-id

          } //container calling-station-id

          leaf circuit-id {
            type boolean;
            description
                "Enable/disable include of circuit-id attribute";
          }

          leaf delegated-ipv6-prefix {
            type boolean;
            description
                "Enable/disable include of delegated-ipv6-prefix attribute";
          }

          leaf detailed-acct-attributes {
            type boolean;
            description
                "Enable/disable include of more detailed accounting attributes";
          }

          leaf dhcp-vendor-class-id {
            type boolean;
            description
                "Enable/disable include of the IPOE-Vendor-Class-Id RADIUS attribute";
          }

          leaf firewall-info {
            type boolean;
            description
                "Include the firewall information attribute";
          }

          leaf framed-interface-id {
            type boolean;
            description
                "Enable/disable include of framed-interface-id attribute";
          }

          leaf framed-ip-addr {
            type boolean;
            description
                "Enable/disable include of framed-ip-addr attribute";
          }

          leaf framed-ip-netmask {
            type boolean;
            description
                "Enable/disable include of framed-ip-netmask attribute";
          }

          leaf framed-ipv6-prefix {
            type boolean;
            description
                "Enable/disable include of framed-ipv6-prefix attribute";
          }

          leaf framed-ipv6-route {
            type boolean;
            description
                "Enable/disable include of framed-ipv6-route attribute";
          }

          leaf framed-route {
            type boolean;
            description
                "Enable/disable include of framed-route attribute";
          }

          leaf imei {
            type boolean;
            description
                "Enable/disable include of the IMEI attribute";
          }

          leaf ipv6-address {
            type boolean;
            description
                "Enable/disable include of ipv6-address attribute";
          }

          leaf lanext-bridge-id {
            type boolean;
            description
                "Enable/disable include of the lanext-bridge-id attribute";
          }

          leaf lanext-device-type {
            type boolean;
            description
                "Enable/disable include of the lanext-device-type attribute";
          }

          leaf lanext-route-distinguisher {
            type boolean;
            description
                "Enable/disable include of the lanext-route-distinguisher attribute";
          }

          leaf lanext-route-target {
            type boolean;
            description
                "Enable/disable include of the lanext-route-target attribute";
          }

          leaf lanext-vni {
            type boolean;
            description
                "Enable/disable include of the lanext-vni attribute";
          }

          leaf mac-address {
            type boolean;
            description
                "Enable/disable include of the MAC-Address attribute";
          }

          leaf msisdn {
            type boolean;
            description
                "Enable/disable include of the MSISDN attribute";
          }

          leaf nas-identifier {
            type boolean;
            description
                "Enable/disable include of the NAS-Identifier attribute";
          }

          container nas-port {
            description
                "Enable/disable include of the NAS-Port attribute";
            leaf binary-spec {
              type string {
                length "1..255";
              }
              description
                  "Attribute binary-spec for nas-port";
            } //binary-spec

          } //container nas-port

          container nas-port-id {
            description
                "Enable/disable include of the NAS-Port-Id attribute";
            leaf prefix-string {
              type string {
                length "1..8";
              }
            } //prefix-string

            leaf suffix {
              type enumeration {
                enum circuit-id;
                enum remote-id;
              }
            } //suffix

          } //container nas-port-id

          container nas-port-type {
            description
                "Enable/disable include of the NAS-Port-Type attribute";
            leaf nas-port-type-id {
              type uint8;
            } //nas-port-type-id

          } //container nas-port-type

          leaf nat-port-range {
            type boolean;
            description
                "Enable/disable include of nat-port-range attribute";
          }

          leaf remote-id {
            type boolean;
            description
                "Enable/disable include of remote-id attribute";
          }

          leaf sla-profile {
            type boolean;
            description
                "Enable/disable include of sla-profile attribute";
          }

          leaf spi-sharing-id {
            type boolean;
            description
                "Enable/disable include of the Alc-SPI-Sharing-Id attribute";
          }

          leaf std-acct-attributes {
            type boolean;
            description
                "Enable/disable include of standard accounting attributes";
          }

          leaf steering-profile {
            type boolean;
            description
                "Enable/disable including the Radius attribute Alc-Steering-Profile";
          }

          leaf sub-profile {
            type boolean;
            description
                "Enable/disable include of sub-profile attribute";
          }

          leaf subscriber-id {
            type boolean;
            description
                "Enable/disable include of subscriber-id attribute";
          }

          leaf tunnel-client-attrs {
            type boolean;
            description
                "Enable/disable include of tunnel-client attribute";
          }

          leaf tunnel-server-attrs {
            type boolean;
            description
                "Enable/disable include of tunnel-server attribute";
          }

          leaf uli {
            type boolean;
            description
                "Enable/disable include of the ULI attribute";
          }

          leaf user-name {
            type boolean;
            description
                "Enable/disable include of user-name attribute";
          }

          leaf v6-aggregate-stats {
            type boolean;
            description
                "Enable/disable include of summarized statistics of v6 traffic";
          }

          leaf wifi-num-attached-ues {
            type boolean;
            description
                "Enable/disable include of the Alc-Num-Attached-UEs attribute";
          }

          leaf wifi-rssi {
            type boolean;
            description
                "Enable/disable include of the 802.11 Received Signal Strength Indication 
                 attribute";
          }

          leaf wifi-ssid-vlan {
            type boolean;
            description
                "Enable/disable including the per-SSID VLAN ID in Alc-Wlan-SSID-VLAN";
          }

          leaf xconnect-tunnel-home-address {
            type boolean;
            description
                "Enable/disable generation of the Cross Connect Tunnel Home Address RADIUS 
                 attribute";
          }

        } //container include-radius-attribute

        container radius-accounting-server {
          description
              "Configure RADIUS accounting servers";
          container access-algorithm {
            description
                "Configure the algorithm used to access the set of RADIUS servers";
            leaf direct-round-robin {
              type enumeration {
                enum direct;
                enum round-robin;
              }
              description
                  "keywords";
            } //direct-round-robin

          } //container access-algorithm

          container retry {
            description
                "Number of retries for contacting the RADIUS server";
            leaf count {
              type uint32 {
                range "1..256";
              }
            } //count

          } //container retry

          container router {
            description
                "Configure the routing instance";
            leaf router-instance {
              type string {
                length "1..32";
              }
              default "Base";
              description
                  "Attribute router-instance for router";
            } //router-instance

            leaf service-name {
              type string;
            } //service-name

          } //container router

          list server {
            key "server-index";
            description
                "Add/remove a RADIUS server";
            leaf server-index {
              type uint32 {
                range "1..5";
              }
            } //server-index

            leaf address {
              type inet:ip-address;
            } //address

            leaf secret {
              type string {
                length "1..500";
              }
              description
                  "secret-key - [20 chars max] 
                   hash-key 
                   hash2-key 
                   custom-key";
            } //secret

            leaf hash-hash2-custom {
              type enumeration {
                enum hash;
                enum hash2;
                enum custom;
              }
              description
                  "keywords - specify hashing scheme";
            } //hash-hash2-custom

            leaf port {
              type uint16 {
                range "1..65535";
              }
            } //port

          } //list server

          container source-address {
            description
                "Source address of the RADIUS message";
            leaf ip-address {
              type inet:ip-address;
            } //ip-address

          } //container source-address

          container timeout {
            description
                "Timeout for a response from the RADIUS server";
            leaf seconds {
              type uint32 {
                range "1..340";
              }
            } //seconds

          } //container timeout

        } //container radius-accounting-server

        container triggered-updates {
          description
              "Configure triggered updates";
          leaf gtp-mobility {
            type boolean;
            description
                "Enable/disable gtp mobility triggered accounting updates";
          }

        } //container triggered-updates

      } //list radius-accounting-policy

      list rip-policy {
        key "policy-name";
        description
            "Create/Configure or delete a RIP policy";
        leaf policy-name {
          type string {
            length "1..32";
          }
        } //policy-name

        container authentication-key {
          description
              "Set authentication key";
          leaf authentication-key-hash-key {
            type string {
              length "1..500";
            }
            description
                "authentication-key - [16 chars max] 
                 hash-key 
                 hash2-key 
                 custom-key";
          } //authentication-key-hash-key

          leaf hash-hash2-custom {
            type enumeration {
              enum hash;
              enum hash2;
              enum custom;
            }
            description
                "keywords - specify hashing scheme";
          } //hash-hash2-custom

        } //container authentication-key

        container authentication-type {
          description
              "Set authentication type";
          leaf authentication-type {
            type enumeration {
              enum none;
              enum password;
              enum message-digest;
              enum message-digest-20;
              enum message-digest-16;
              enum message-digest-20-exact;
            }
            description
                "Attribute authentication-type for authentication-type";
          } //authentication-type

        } //container authentication-type

        container description {
          description
              "Description for the RIP policy";
          leaf description-string {
            type string {
              length "1..80";
            }
          } //description-string

        } //container description

      } //list rip-policy

      list router-advertisement-policy {
        key "name";
        description
            "Configure IPv6 router advertisements";
        leaf name {
          type string;
        } //name

        container current-hop-limit {
          description
              "Configure the hop-limit to be advertised";
          leaf limit {
            type uint16 {
              range "0..255";
            }
          } //limit

        } //container current-hop-limit

        container force-mcast {
          description
              "Configure the protocols for forced multicast";
          leaf-list force-mcast-id {
            type enumeration {
              enum ip;
              enum mac;
            }
            max-elements 2;
          } //force-mcast-id

        } //container force-mcast

        leaf managed-configuration {
          type boolean;
          description
              "Configure the managed-address-configuration flag";
        }

        container max-advertisement {
          description
              "Configure the maximum advertisement interval";
          leaf seconds {
            type uint32 {
              range "900..1800";
            }
          } //seconds

        } //container max-advertisement

        container min-advertisement {
          description
              "Configure the minimum advertisement interval";
          leaf seconds {
            type uint32 {
              range "900..1350";
            }
          } //seconds

        } //container min-advertisement

        container mtu {
          description
              "Configure the advertised MTU value";
          leaf bytes {
            type uint32 {
              range "1280..9212";
            }
          } //bytes

        } //container mtu

        leaf other-stateful-configuration {
          type boolean;
          description
              "Configure the other-stateful-configuration flag";
        }

        container reachable-time {
          description
              "Configure the reachable time for advertisements";
          leaf milli-seconds {
            type uint32 {
              range "0..3600000";
            }
          } //milli-seconds

        } //container reachable-time

        container retransmit-time {
          description
              "Configure the retransmit time for advertisements";
          leaf milli-seconds {
            type uint32 {
              range "0..1800000";
            }
          } //milli-seconds

        } //container retransmit-time

        container router-lifetime {
          description
              "Configure the router lifetime";
          leaf seconds {
            type uint32 {
              range "2700..9000";
            }
          } //seconds

          leaf no-default-router {
            type boolean;
          } //no-default-router

        } //container router-lifetime

        container dns-options {
          presence
              "Configure DNS options";
          leaf include-dns {
            type boolean;
            description
                "Configure the inclusion of the RDNSS server option 25";
          }

          container rdnss-lifetime {
            description
                "Configure the maximum time the RDNSS address is valid";
            leaf seconds {
              type uint32 {
                range "900..3600";
              }
            } //seconds

            leaf infinite {
              type boolean;
            } //infinite

          } //container rdnss-lifetime

        } //container dns-options

        container prefix-options {
          presence
              "Configure prefix options";
          container stateful {
            presence
                "Configure the prefix options for DHCPv6 addresses and or prefixes";
            leaf auto-lifetimes {
              type boolean;
              description
                  "Configure the use of automatic lifetimes for stateful prefixes";
            }

            leaf on-link {
              type boolean;
              description
                  "Configure assigning of the prefix to an interface on the specified link";
            }

            container preferred-lifetime {
              description
                  "Configure the time for prefix to remain preferred";
              leaf seconds {
                type string;
                description
                    "[0|900..86400]";
              } //seconds

              leaf infinite {
                type boolean;
              } //infinite

            } //container preferred-lifetime

            container valid-lifetime {
              description
                  "Configure the time for prefix to remain valid";
              leaf seconds {
                type string;
                description
                    "[0|900..86400]";
              } //seconds

              leaf infinite {
                type boolean;
              } //infinite

            } //container valid-lifetime

          } //container stateful

          container stateless {
            presence
                "Configure the prefix options for SLAAC prefixes";
            leaf on-link {
              type boolean;
              description
                  "Configure assigning of the prefix to an interface on the specified link";
            }

            container preferred-lifetime {
              description
                  "Configure the time for prefix to remain preferred";
              leaf seconds {
                type string;
                description
                    "[0|900..86400]";
              } //seconds

              leaf infinite {
                type boolean;
              } //infinite

            } //container preferred-lifetime

            container valid-lifetime {
              description
                  "Configure the time for prefix to remain valid";
              leaf seconds {
                type string;
                description
                    "[0|900..86400]";
              } //seconds

              leaf infinite {
                type boolean;
              } //infinite

            } //container valid-lifetime

          } //container stateless

        } //container prefix-options

      } //list router-advertisement-policy

      list shcv-policy {
        key "name";
        description
            "Configure Subscriber Host Connectivity Verification (SHCV) policies";
        leaf name {
          type string;
        } //name

        container description {
          description
              "Configure a description";
          leaf description-string {
            type string {
              length "1..80";
            }
          } //description-string

        } //container description

        container layer-3 {
          description
              "Configure SHCV behavior in IES and VPRN services";
          container source-ip-origin {
            description
                "Configure the origin of the IP address to be used as source address for 
                 connectivity verification";
            leaf source-ip-origin-id {
              type enumeration {
                enum interface;
                enum vrrp;
              }
            } //source-ip-origin-id

          } //container source-ip-origin

        } //container layer-3

        container periodic {
          description
              "Configure periodic connectivity verification";
          container action {
            description
                "Configure action to take when the periodic connectivity verification failed";
            leaf action-id {
              type enumeration {
                enum alarm;
                enum remove;
              }
            } //action-id

          } //container action

          container interval {
            description
                "Configure the interval between connectivity checks";
            leaf minutes {
              type uint32 {
                range "1..6000";
              }
            } //minutes

          } //container interval

          container retry-count {
            description
                "Configure the number of retransmissions";
            leaf retry-count-id {
              type uint32 {
                range "2..29";
              }
            } //retry-count-id

          } //container retry-count

          leaf shutdown {
            type boolean;
            description
                "Disable/enable periodic connectivity verification";
          }

          container timeout {
            description
                "Configure the timeout before a retransmission";
            leaf seconds {
              type uint32 {
                range "10..60";
              }
            } //seconds

          } //container timeout

        } //container periodic

        container trigger {
          description
              "Configure the SHCV triggers";
          leaf trigger-type {
            type enumeration {
              enum ip-conflict;
              enum host-limit-exceeded;
              enum inactivity;
              enum mobility;
              enum mac-learning;
            }
          } //trigger-type

          container retry-count {
            description
                "Configure the number of retransmissions";
            leaf retry-count-id {
              type uint32 {
                range "1..29";
              }
            } //retry-count-id

          } //container retry-count

          leaf shutdown {
            type boolean;
            description
                "Disable/enable this connectivity verification trigger";
          }

          container timeout {
            description
                "Configure the timeout before a retransmission";
            leaf seconds {
              type uint32 {
                range "1..60";
              }
            } //seconds

          } //container timeout

        } //container trigger

        container vpls {
          description
              "Configure SHCV behavior in VPLS services";
          container source-ip {
            description
                "Configure the IPv4 address to be used as source address for connectivity 
                 verification in a VPLS service";
            leaf ip-address {
              type inet:ip-address;
              description
                  "a.b.c.d";
            } //ip-address

          } //container source-ip

          container source-mac {
            description
                "Configure the MAC address to be used as source address for connectivity 
                 verification in a VPLS service";
            leaf ieee-address {
              type alu:ieee-address;
              description
                  "xx:xx:xx:xx:xx:xx or xx-xx-xx-xx-xx-xx";
            } //ieee-address

          } //container source-mac

        } //container vpls

      } //list shcv-policy

      list sla-profile {
        key "sla-profile-name";
        description
            "Configure an SLA profile";
        leaf sla-profile-name {
          type string {
            length "1..32";
          }
        } //sla-profile-name

        container credit-control-policy {
          description
              "Configure the credit policy for this SLA profile";
          leaf policy-name {
            type string {
              length "1..32";
            }
          } //policy-name

        } //container credit-control-policy

        container def-instance-sharing {
          description
              "Default method for SLA Profile Instance sharing of IPoE and PPPoE sessions";
          leaf def-instance-sharing-id {
            type enumeration {
              enum per-sap;
              enum per-session;
            }
          } //def-instance-sharing-id

        } //container def-instance-sharing

        container description {
          description
              "Description for this SLA profile";
          leaf description-string {
            type string {
              length "1..80";
            }
          } //description-string

        } //container description

        container one-time-http-redirection {
          description
              "Configure one-time HTTP redirection for this SLA profile";
          leaf ip-filter {
            type uint32 {
              range "1..65535";
            }
          } //ip-filter

        } //container one-time-http-redirection

        container category-map {
          description
              "Configure the category map for this SLA profile";
          leaf category-map-name {
            type string {
              length "1..32";
            }
          } //category-map-name

          list category {
            key "category-name";
            description
                "Configure a category of this category map";
            leaf category-name {
              type string {
                length "1..32";
              }
            } //category-name

            container idle-timeout {
              description
                  "Configure the idle timeout for this category";
              leaf timeout {
                type uint32 {
                  range "60..15552000";
                }
                description
                    "[60..15552000] seconds";
              } //timeout

            } //container idle-timeout

            container idle-timeout-action {
              description
                  "Configure the idle timeout action for this category";
              leaf idle-timeout-action-id {
                type enumeration {
                  enum shcv-check;
                  enum terminate;
                }
              } //idle-timeout-action-id

            } //container idle-timeout-action

          } //list category

        } //container category-map

        container egress {
          description
              "Configure egress parameters";
          container hs-agg-rate-limit {
            description
                "Configure the maximum rate for expanded egress HS queues";
            leaf kilobits-per-second {
              type int32 {
                range "1..100000000";
              }
            } //kilobits-per-second

          } //container hs-agg-rate-limit

          container ip-filter {
            description
                "Configure an ip-filter";
            leaf ip-filter-id {
              type string;
              description
                  "[1..65535]|<name:64 char max>";
            } //ip-filter-id

            leaf force {
              type boolean;
            } //force

          } //container ip-filter

          container ipv6-filter {
            description
                "Configure an ipv6-filter";
            leaf ipv6-filter-id {
              type string;
              description
                  "[1..65535]|<name:64 char max>";
            } //ipv6-filter-id

            leaf force {
              type boolean;
            } //force

          } //container ipv6-filter

          leaf qos-marking-from-sap {
            type boolean;
            description
                "Define the sap-egress qos-policy from which the egress qos marking rules are 
                 taken";
          }

          container report-rate {
            description
                "Configure the type of rate to report for L2TP";
            leaf agg-rate-limit {
              type boolean;
            } //agg-rate-limit

            leaf scheduler {
              type string {
                length "1..32";
              }
            } //scheduler

            leaf pppoe-actual-rate {
              type boolean;
            } //pppoe-actual-rate

            leaf rfc5515-actual-rate {
              type boolean;
            } //rfc5515-actual-rate

            leaf policer {
              type uint32 {
                range "1..63";
              }
            } //policer

          } //container report-rate

          leaf use-ingress-l2tp-dscp {
            type boolean;
            description
                "Specify that the DSCP of the ingress L2TP header be used to do egress 
                 reclassification";
          }

          container bonding-selection {
            description
                "Configure the parameters for the link selection behaviour in a bonding context";
            container rate-thresholds {
              description
                  "Configure the high- and low-threshold rate percentages";
              leaf high {
                type uint32 {
                  range "56..99";
                }
              } //high

              leaf low {
                type uint32 {
                  range "55..98";
                }
              } //low

            } //container rate-thresholds

            container weight {
              description
                  "Configure the weight parameters of the preferred connection";
              leaf initial-weight-percentage {
                type uint32 {
                  range "1..100";
                }
              } //initial-weight-percentage

              leaf weight-change-percentage {
                type uint32 {
                  range "0..10";
                }
              } //weight-change-percentage

            } //container weight

          } //container bonding-selection

          container qos {
            description
                "Apply an egress qos policy";
            leaf policy-id {
              type string;
              description
                  "[1..65535]|<name:64 char max>";
            } //policy-id

            leaf qos-id {
              type enumeration {
                enum vport-scheduler;
                enum port-scheduler;
              }
            } //qos-id

            leaf force {
              type boolean;
              description
                  "keyword - forces policy change";
            } //force

            container hs-queue-stat-mode {
              description
                  "Configure the egress HS queue stats mode";
              leaf mode {
                type enumeration {
                  enum no-override;
                  enum v4-v6;
                }
              } //mode

            } //container hs-queue-stat-mode

            list hs-wrr-group {
              key "group-id";
              description
                  "Configure egress HS WRR group override parameters";
              leaf group-id {
                type int32 {
                  range "1..2";
                }
              } //group-id

              container hs-class-weight {
                description
                    "Configure the class weight override for WRR group";
                leaf weight {
                  type int32;
                  description
                      "Attribute weight for hs-class-weight";
                } //weight

              } //container hs-class-weight

              container rate {
                description
                    "Configure the rate (PIR) override for WRR group";
                leaf rate {
                  type string;
                  description
                      "Attribute rate for rate";
                } //rate

              } //container rate

            } //list hs-wrr-group

            list policer {
              key "policer-id";
              description
                  "Configure egress policer override parameters";
              leaf policer-id {
                type uint32 {
                  range "1..63";
                }
              } //policer-id

              container cbs {
                description
                    "Specify Cbs";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container rate {
                description
                    "Specify rates (CIR and PIR)";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-profile-cir;
                    enum offered-total-cir;
                    enum offered-limited-capped-cir;
                    enum offered-profile-capped-cir;
                    enum v4-v6;
                    enum offered-total-cir-exceed;
                    enum offered-four-profile-no-cir;
                    enum offered-total-cir-four-profile;
                  }
                } //stat-mode

              } //container stat-mode

            } //list policer

            list queue {
              key "queue-id";
              description
                  "Configure egress queue override parameters";
              leaf queue-id {
                type int32 {
                  range "1..8";
                }
              } //queue-id

              container avg-frame-overhead {
                description
                    "Specify the average frame overhead";
                leaf percentage {
                  type string;
                  description
                      "[0.00..100.00]";
                } //percentage

              } //container avg-frame-overhead

              container cbs {
                description
                    "Specify CBS";
                leaf size-in-kbytes {
                  type string;
                  description
                      "Attribute size-in-kbytes for cbs";
                } //size-in-kbytes

              } //container cbs

              container high-prio-only {
                description
                    "Specify high priority only burst size";
                leaf percent {
                  type string;
                  description
                      "[0..100 | default]";
                } //percent

              } //container high-prio-only

              container hs-class-weight {
                description
                    "Configure the class-weight override for expanded egress HS queues";
                leaf weight {
                  type int32;
                  description
                      "Attribute weight for hs-class-weight";
                } //weight

              } //container hs-class-weight

              container hs-wred-queue-policy {
                description
                    "Configure the slope-policy override for expanded egress HS queues";
                leaf name {
                  type string;
                } //name

              } //container hs-wred-queue-policy

              container hs-wrr-weight {
                description
                    "Configure the WRR weight override for expanded egress HS queues";
                leaf hs-wrr-weight-id {
                  type uint32 {
                    range "1..127";
                  }
                } //hs-wrr-weight-id

              } //container hs-wrr-weight

              container mbs {
                description
                    "Specify MBS";
                leaf size {
                  type string;
                  description
                      "Attribute size for mbs";
                } //size

                leaf bytes-kilobytes {
                  type enumeration {
                    enum bytes;
                    enum kilobytes;
                  }
                  description
                      "keyword";
                } //bytes-kilobytes

              } //container mbs

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container stat-mode {
                description
                    "Specify Stat Mode for the queue";
                leaf stat-mode-id {
                  type enumeration {
                    enum v4-v6;
                  }
                } //stat-mode-id

              } //container stat-mode

            } //list queue

          } //container qos

          container scheduler-policy {
            description
                "Apply an egress scheduler policy";
            leaf scheduler-policy-name {
              type string {
                length "1..32";
              }
            } //scheduler-policy-name

            list scheduler {
              key "scheduler-name";
              description
                  "Configure scheduler override parameters";
              leaf scheduler-name {
                type string {
                  length "1..32";
                }
              } //scheduler-name

              leaf rate {
                type string;
                description
                    "[1..3200000000|max] Kbps";
              } //rate

              leaf cir {
                type string;
                description
                    "[0..3200000000|sum|max] Kbps";
              } //cir

            } //list scheduler

          } //container scheduler-policy

        } //container egress

        container host-limits {
          presence
              "Host-limits for this SLA profile";
          container ipv4-arp {
            description
                "Maximum number of IPv4 ARP hosts";
            leaf max-nr-of-hosts {
              type int32 {
                range "0..131071";
              }
              description
                  "Attribute max-nr-of-hosts for ipv4-arp";
            } //max-nr-of-hosts

          } //container ipv4-arp

          container ipv4-dhcp {
            description
                "Maximum number of IPv4 DHCP hosts";
            leaf max-nr-of-hosts {
              type int32 {
                range "0..131071";
              }
              description
                  "Attribute max-nr-of-hosts for ipv4-dhcp";
            } //max-nr-of-hosts

          } //container ipv4-dhcp

          container ipv4-overall {
            description
                "Maximum number of IPv4 hosts";
            leaf max-nr-of-hosts {
              type int32 {
                range "0..131071";
              }
              description
                  "Attribute max-nr-of-hosts for ipv4-overall";
            } //max-nr-of-hosts

          } //container ipv4-overall

          container ipv4-ppp {
            description
                "Maximum number of IPv4 PPP hosts";
            leaf max-nr-of-hosts {
              type int32 {
                range "0..131071";
              }
              description
                  "Attribute max-nr-of-hosts for ipv4-ppp";
            } //max-nr-of-hosts

          } //container ipv4-ppp

          container ipv6-overall {
            description
                "Maximum number of IPv6 hosts";
            leaf max-nr-of-hosts {
              type int32 {
                range "0..131071";
              }
              description
                  "Attribute max-nr-of-hosts for ipv6-overall";
            } //max-nr-of-hosts

          } //container ipv6-overall

          container ipv6-pd-ipoe-dhcp {
            description
                "Maximum number of IPv6-PD IPOE DHCP hosts";
            leaf max-nr-of-hosts {
              type int32 {
                range "0..131071";
              }
              description
                  "Attribute max-nr-of-hosts for ipv6-pd-ipoe-dhcp";
            } //max-nr-of-hosts

          } //container ipv6-pd-ipoe-dhcp

          container ipv6-pd-overall {
            description
                "Maximum number of IPv6-PD hosts";
            leaf max-nr-of-hosts {
              type int32 {
                range "0..131071";
              }
              description
                  "Attribute max-nr-of-hosts for ipv6-pd-overall";
            } //max-nr-of-hosts

          } //container ipv6-pd-overall

          container ipv6-pd-ppp-dhcp {
            description
                "Maximum number of IPv6-PD PPP DHCP hosts";
            leaf max-nr-of-hosts {
              type int32 {
                range "0..131071";
              }
              description
                  "Attribute max-nr-of-hosts for ipv6-pd-ppp-dhcp";
            } //max-nr-of-hosts

          } //container ipv6-pd-ppp-dhcp

          container ipv6-wan-ipoe-dhcp {
            description
                "Maximum number of IPv6-Wan IPOE DHCP hosts";
            leaf max-nr-of-hosts {
              type int32 {
                range "0..131071";
              }
              description
                  "Attribute max-nr-of-hosts for ipv6-wan-ipoe-dhcp";
            } //max-nr-of-hosts

          } //container ipv6-wan-ipoe-dhcp

          container ipv6-wan-ipoe-slaac {
            description
                "Maximum number of IPv6-Wan IPOE SLAAC hosts";
            leaf max-nr-of-hosts {
              type int32 {
                range "0..131071";
              }
              description
                  "Attribute max-nr-of-hosts for ipv6-wan-ipoe-slaac";
            } //max-nr-of-hosts

          } //container ipv6-wan-ipoe-slaac

          container ipv6-wan-overall {
            description
                "Maximum number of IPv6-Wan hosts";
            leaf max-nr-of-hosts {
              type int32 {
                range "0..131071";
              }
              description
                  "Attribute max-nr-of-hosts for ipv6-wan-overall";
            } //max-nr-of-hosts

          } //container ipv6-wan-overall

          container ipv6-wan-ppp-dhcp {
            description
                "Maximum number of IPv6-Wan PPP DHCP hosts";
            leaf max-nr-of-hosts {
              type int32 {
                range "0..131071";
              }
              description
                  "Attribute max-nr-of-hosts for ipv6-wan-ppp-dhcp";
            } //max-nr-of-hosts

          } //container ipv6-wan-ppp-dhcp

          container ipv6-wan-ppp-slaac {
            description
                "Maximum number of IPv6-Wan PPP SLAAC hosts";
            leaf max-nr-of-hosts {
              type int32 {
                range "0..131071";
              }
              description
                  "Attribute max-nr-of-hosts for ipv6-wan-ppp-slaac";
            } //max-nr-of-hosts

          } //container ipv6-wan-ppp-slaac

          container lac-overall {
            description
                "Maximum number of L2TP LAC hosts";
            leaf max-nr-of-hosts {
              type int32 {
                range "0..131071";
              }
              description
                  "Attribute max-nr-of-hosts for lac-overall";
            } //max-nr-of-hosts

          } //container lac-overall

          container overall {
            description
                "Maximum number of hosts";
            leaf max-nr-of-hosts {
              type int32 {
                range "1..131071";
              }
              description
                  "Attribute max-nr-of-hosts for overall";
            } //max-nr-of-hosts

          } //container overall

          leaf remove-oldest {
            type boolean;
            description
                "Remove oldest";
          }

        } //container host-limits

        container ingress {
          description
              "Configure ingress parameters";
          container ip-filter {
            description
                "Configure an ip-filter";
            leaf ip-filter-id {
              type string;
              description
                  "[1..65535]|<name:64 char max>";
            } //ip-filter-id

            leaf force {
              type boolean;
            } //force

          } //container ip-filter

          container ipv6-filter {
            description
                "Configure an ipv6-filter";
            leaf ipv6-filter-id {
              type string;
              description
                  "[1..65535]|<name:64 char max>";
            } //ipv6-filter-id

            leaf force {
              type boolean;
            } //force

          } //container ipv6-filter

          container report-rate {
            description
                "Configure the type of rate to report for L2TP";
            leaf agg-rate-limit {
              type boolean;
            } //agg-rate-limit

            leaf scheduler {
              type string {
                length "1..32";
              }
            } //scheduler

            leaf pppoe-actual-rate {
              type boolean;
            } //pppoe-actual-rate

            leaf rfc5515-actual-rate {
              type boolean;
            } //rfc5515-actual-rate

            leaf policer {
              type uint32 {
                range "1..63";
              }
            } //policer

          } //container report-rate

          container qos {
            description
                "Apply an ingress qos policy";
            leaf policy-id {
              type string;
              description
                  "[1..65535]|<name:64 char max>";
            } //policy-id

            leaf shared-queuing-multipoint-shared-service-queuing {
              type enumeration {
                enum shared-queuing;
                enum multipoint-shared;
                enum service-queuing;
              }
              description
                  "keywords - specify queuing-type";
            } //shared-queuing-multipoint-shared-service-queuing

            leaf force {
              type boolean;
              description
                  "keyword - forces policy change";
            } //force

            list policer {
              key "policer-id";
              description
                  "Configure ingress policer override parameters";
              leaf policer-id {
                type uint32 {
                  range "1..63";
                }
              } //policer-id

              container cbs {
                description
                    "Specify Cbs";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "specify packet byte offset";
                leaf add {
                  type uint32 {
                    range "0..31";
                  }
                } //add

                leaf subtract {
                  type uint32 {
                    range "1..32";
                  }
                } //subtract

              } //container packet-byte-offset

              container rate {
                description
                    "Specify rates (CIR and PIR)";
                leaf pir-rate {
                  type string;
                  description
                      "[1..2000000000|max] Kbps";
                } //pir-rate

                leaf cir {
                  type string;
                  description
                      "[0..2000000000|max] Kbps";
                } //cir

              } //container rate

              container stat-mode {
                description
                    "Specify Stat Mode for the policer";
                leaf stat-mode {
                  type enumeration {
                    enum no-stats;
                    enum minimal;
                    enum offered-profile-no-cir;
                    enum offered-priority-no-cir;
                    enum offered-profile-cir;
                    enum offered-priority-cir;
                    enum offered-total-cir;
                    enum offered-limited-profile-cir;
                    enum offered-profile-capped-cir;
                    enum offered-limited-capped-cir;
                    enum v4-v6;
                  }
                } //stat-mode

              } //container stat-mode

            } //list policer

            list queue {
              key "queue-id";
              description
                  "Configure ingress queue override parameters";
              leaf queue-id {
                type int32 {
                  range "1..32";
                }
              } //queue-id

              container cbs {
                description
                    "Specify CBS";
                leaf size-in-kbytes {
                  type string;
                  description
                      "Attribute size-in-kbytes for cbs";
                } //size-in-kbytes

              } //container cbs

              container high-prio-only {
                description
                    "Specify high priority only burst size";
                leaf percent {
                  type string;
                  description
                      "[0..100 | default]";
                } //percent

              } //container high-prio-only

              container mbs {
                description
                    "Specify MBS";
                leaf size {
                  type string;
                  description
                      "Attribute size for mbs";
                } //size

                leaf bytes-kilobytes {
                  type enumeration {
                    enum bytes;
                    enum kilobytes;
                  }
                  description
                      "keyword";
                } //bytes-kilobytes

              } //container mbs

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container stat-mode {
                description
                    "Specify Stat Mode for the queue";
                leaf stat-mode-id {
                  type enumeration {
                    enum v4-v6;
                  }
                } //stat-mode-id

              } //container stat-mode

            } //list queue

          } //container qos

        } //container ingress

      } //list sla-profile

      list steering-profile {
        key "steering-profile";
        description
            "Configure a L2TP LAC steering profile";
        leaf steering-profile {
          type string {
            length "1..32";
          }
        } //steering-profile

        container access {
          description
              "Configure the next-hop for upstream packets (from subscriber)";
          leaf router {
            type string;
            default "Base";
            description
                "Attribute router-name for access";
          } //router

          leaf service-name {
            type string;
          } //service-name

        } //container access

        container description {
          description
              "Configure the description of the steering profile";
          leaf description-string {
            type string {
              length "1..80";
            }
          } //description-string

        } //container description

        container network {
          description
              "Configure the next-hop for downstream packets (from network)";
          leaf next-hop {
            type inet:ip-address;
          } //next-hop

          leaf router {
            type string;
            default "Base";
            description
                "Attribute router-name for network";
          } //router

          leaf service-name {
            type string;
          } //service-name

        } //container network

      } //list steering-profile

      list sub-ident-policy {
        key "sub-ident-policy-name";
        description
            "Configure a subscriber identification policy";
        leaf sub-ident-policy-name {
          type string {
            length "1..32";
          }
        } //sub-ident-policy-name

        container description {
          description
              "Description for this subscriber identification policy";
          leaf description-string {
            type string {
              length "1..80";
            }
          } //description-string

        } //container description

        container strings-from-option {
          description
              "Configure IPOE option to get the identification strings from";
          leaf dhcp-option-number {
            type uint32 {
              range "1..254";
            }
          } //dhcp-option-number

        } //container strings-from-option

        container app-profile-map {
          description
              "Configure an application profile mapping";
          list entry {
            key "key";
            description
                "Configure an application profile string";
            leaf key {
              type string {
                length "1..16";
              }
            } //key

            leaf app-profile {
              type string {
                length "1..32";
              }
            } //app-profile

          } //list entry

          leaf use-direct-map-as-default {
            type boolean;
            description
                "Enable/disable direct mapping of application profile as default";
          }

        } //container app-profile-map

        container primary {
          description
              "Configure primary identification script";
          container script-url {
            description
                "URL of the primary identification script";
            leaf dhcp-primary-script-url {
              type string {
                length "1..180";
              }
            } //dhcp-primary-script-url

          } //container script-url

          leaf shutdown {
            type boolean;
            description
                "Enable/disable script execution";
          }

        } //container primary

        container secondary {
          description
              "Configure secondary identification script";
          container script-url {
            description
                "URL of the secondary identification script";
            leaf dhcp-secondary-script-url {
              type string {
                length "1..180";
              }
            } //dhcp-secondary-script-url

          } //container script-url

          leaf shutdown {
            type boolean;
            description
                "Enable/disable script execution";
          }

        } //container secondary

        container sla-profile-map {
          description
              "Configure an SLA profile mapping";
          list entry {
            key "key";
            description
                "Configure an SLA profile string";
            leaf key {
              type string;
              description
                  "Attribute profile-string for entry";
            } //key

            leaf sla-profile {
              type string {
                length "1..32";
              }
            } //sla-profile

          } //list entry

          leaf use-direct-map-as-default {
            type boolean;
            description
                "Enable/disable direct mapping of SLA profile as default";
          }

        } //container sla-profile-map

        container sub-profile-map {
          description
              "Configure a subscriber profile mapping";
          list entry {
            key "key";
            description
                "Configure a subscriber profile string";
            leaf key {
              type string;
              description
                  "Attribute profile-string for entry";
            } //key

            leaf sub-profile {
              type string {
                length "1..32";
              }
            } //sub-profile

          } //list entry

          leaf use-direct-map-as-default {
            type boolean;
            description
                "Enable/disable direct mapping of subscriber profile as default";
          }

        } //container sub-profile-map

        container tertiary {
          description
              "Configure tertiary identification script";
          container script-url {
            description
                "URL of the tertiary identification script";
            leaf dhcp-tertiary-script-url {
              type string {
                length "1..180";
              }
            } //dhcp-tertiary-script-url

          } //container script-url

          leaf shutdown {
            type boolean;
            description
                "Enable/disable script execution";
          }

        } //container tertiary

      } //list sub-ident-policy

      list sub-mcac-policy {
        key "sub-mcac-policy-name";
        description
            "Configure a Sub-MCAC policy";
        leaf sub-mcac-policy-name {
          type string {
            length "1..32";
          }
        } //sub-mcac-policy-name

        container description {
          description
              "Description for this subscriber MCAC policy";
          leaf description-string {
            type string {
              length "1..80";
            }
          } //description-string

        } //container description

        leaf shutdown {
          type boolean;
          description
              "Administratively enable/disable the subscriber MCAC policy";
        }

        container unconstrained-bw {
          description
              "Set/reset unconstrained-bw for multicast CAC policy on this subscriber";
          leaf bandwidth {
            type int32 {
              range "0..2147483647";
            }
          } //bandwidth

          leaf mandatory-bw {
            type int32 {
              range "0..2147483647";
            }
          } //mandatory-bw

        } //container unconstrained-bw

      } //list sub-mcac-policy

      list sub-profile {
        key "subscriber-profile-name";
        description
            "Configure a subscriber profile";
        leaf subscriber-profile-name {
          type string {
            length "1..32";
          }
          description
              "[32 chars max] | default";
        } //subscriber-profile-name

        container accounting-policy {
          description
              "Configure accounting-policy to be used";
          leaf acct-policy-id {
            type uint64 {
              range "1..99";
            }
          } //acct-policy-id

        } //container accounting-policy

        container accu-stats-policy {
          description
              "Apply a policy for accumulated statistics";
          leaf policy-name {
            type string;
          } //policy-name

        } //container accu-stats-policy

        leaf collect-stats {
          type boolean;
          description
              "Enable/disable statistics collection";
        }

        container description {
          description
              "Description for this subscriber profile";
          leaf description-string {
            type string {
              length "1..80";
            }
          } //description-string

        } //container description

        container firewall-policy {
          description
              "Apply a firewall policy";
          leaf policy-name {
            type string;
          } //policy-name

        } //container firewall-policy

        container host-tracking-policy {
          description
              "Apply a host tracking policy";
          leaf policy-name {
            type string {
              length "1..32";
            }
          } //policy-name

        } //container host-tracking-policy

        container hs-sla-mode {
          description
              "Configure the HS board's subscriber SLA mode";
          leaf hs-sla-mode-id {
            type enumeration {
              enum expanded;
              enum single;
            }
          } //hs-sla-mode-id

        } //container hs-sla-mode

        container igmp-policy {
          description
              "Apply an IGMP policy";
          leaf policy-name {
            type string {
              length "1..32";
            }
          } //policy-name

        } //container igmp-policy

        container mld-policy {
          description
              "Apply an MLD policy";
          leaf policy-name {
            type string {
              length "1..32";
            }
          } //policy-name

        } //container mld-policy

        container nat-access-mode {
          description
              "Configure the NAT access mode";
          leaf access-mode {
            type enumeration {
              enum auto;
              enum bridged;
            }
          } //access-mode

        } //container nat-access-mode

        container nat-policy {
          description
              "Apply a NAT policy";
          leaf policy-name {
            type string {
              length "1..32";
            }
          } //policy-name

        } //container nat-policy

        container nat-prefix-list {
          description
              "Apply a Layer-2-Aware NAT prefix list";
          leaf name {
            type string {
              length "1..32";
            }
          } //name

        } //container nat-prefix-list

        container pim-policy {
          description
              "Apply a Protocol Independent Multicast (PIM) policy";
          leaf name {
            type string;
          } //name

        } //container pim-policy

        container preference {
          description
              "Preference of this subscriber profile";
          leaf preference {
            type uint8 {
              range "1..10";
            }
            description
                "[1..10] - 1 is lowest, 5 is default";
          } //preference

        } //container preference

        container radius-accounting-policy {
          status "obsolete";
          description
              "Apply a RADIUS accounting policy";
          leaf acct-policy-name {
            type string {
              length "1..32";
            }
          } //acct-policy-name

          leaf duplicate {
            type string {
              length "1..32";
            }
          } //duplicate

        } //container radius-accounting-policy

        leaf secondary-shaper-hashing {
          type boolean;
          description
              "Configure LAG hashing on secondary shaper";
        }

        container sub-mcac-policy {
          description
              "Apply a subscriber MCAC policy";
          leaf policy-name {
            type string {
            }
          } //policy-name

        } //container sub-mcac-policy

        container upnp-policy {
          description
              "Apply a Universal Plug 'n Play (UPnP) policy";
          leaf policy-name {
            type string;
          } //policy-name

        } //container upnp-policy

        container volume-stats-type {
          description
              "Configure whether non-IP headers are included in the accounting-stats";
          leaf volume-stats-type-id {
            type enumeration {
              enum ip;
              enum default;
            }
          } //volume-stats-type-id

        } //container volume-stats-type

        leaf vport-hashing {
          type boolean;
          description
              "Configure LAG hashing on VPort";
        }

        container ancp {
          description
              "Configure Access Node Control Protocol parameters";
          container ancp-policy {
            description
                "configure an ANCP policy for this subscriber profile";
            leaf policy-name {
              type string {
                length "1..32";
              }
            } //policy-name

          } //container ancp-policy

        } //container ancp

        container egress {
          description
              "Configure subscriber profile egress settings";
          container agg-rate-limit {
            description
                "Configure the egress aggregate rate limit";
            leaf agg-rate {
              type string;
              description
                  "[1..800000000|max] Kbps";
            } //agg-rate

            leaf min-resv-bw {
              type uint32 {
                range "0..800000000";
              }
            } //min-resv-bw

            leaf queue-frame-based-accounting {
              type boolean;
              description
                  "keyword";
            } //queue-frame-based-accounting

          } //container agg-rate-limit

          container avg-frame-size {
            status "obsolete";
            description
                "Configure the average frame size";
            leaf bytes {
              type int32 {
                range "64..4096";
              }
            } //bytes

          } //container avg-frame-size

          container encap-offset {
            description
                "Configure the egress encapsulation offset";
            leaf type {
              type enumeration {
                enum pppoa-llc;
                enum pppoa-null;
                enum pppoeoa-llc;
                enum pppoeoa-llc-fcs;
                enum pppoeoa-llc-tagged;
                enum pppoeoa-llc-tagged-fcs;
                enum pppoeoa-null;
                enum pppoeoa-null-fcs;
                enum pppoeoa-null-tagged;
                enum pppoeoa-null-tagged-fcs;
                enum ipoa-llc;
                enum ipoa-null;
                enum ipoeoa-llc;
                enum ipoeoa-llc-fcs;
                enum ipoeoa-llc-tagged;
                enum ipoeoa-llc-tagged-fcs;
                enum ipoeoa-null;
                enum ipoeoa-null-fcs;
                enum ipoeoa-null-tagged;
                enum ipoeoa-null-tagged-fcs;
                enum pppoe;
                enum pppoe-tagged;
                enum ipoe;
                enum ipoe-tagged;
              }
            } //type

          } //container encap-offset

          container hs-agg-rate-limit {
            description
                "Configure the HS egress aggregate rate limit";
            leaf kilobits-per-second {
              type int32 {
                range "1..100000000";
              }
            } //kilobits-per-second

            leaf max {
              type boolean;
              description
                  "keyword";
            } //max

            leaf min-resv-bw {
              type uint32 {
                range "0..100000000";
              }
            } //min-resv-bw

          } //container hs-agg-rate-limit

          container hs-low-burst-max-class {
            description
                "Configure what classes use the low priority burst threshold and what classes 
                 use the high priority burst threshold";
            leaf class {
              type uint32 {
                range "1..6";
              }
            } //class

          } //container hs-low-burst-max-class

          container lag-per-link-hash {
            description
                "Configure LAG per-link-hash class and weight";
            leaf class {
              type enumeration {
                enum 1;
                enum 2;
                enum 3;
              }
            } //class

            leaf weight {
              type uint32 {
                range "1..1024";
              }
            } //weight

          } //container lag-per-link-hash

          container policer-control-policy {
            description
                "Configure Qos Policer control Policy";
            leaf policer-control-policy-name {
              type string {
                length "1..32";
              }
            } //policer-control-policy-name

            container max-rate {
              description
                  "Configure Max Rate in kilobits-per-second";
              leaf rate {
                type string;
                description
                    "[1..2000000000|max] Kbps";
              } //rate

            } //container max-rate

            container priority-mbs-thresholds {
              description
                  "Configure priority mbs thresholds";
              container min-thresh-separation {
                description
                    "configure min threshold separation";
                leaf size {
                  type int32 {
                    range "0..16777216";
                  }
                } //size

                leaf bytes-kilobytes {
                  type enumeration {
                    enum bytes;
                    enum kilobytes;
                  }
                } //bytes-kilobytes

                leaf default {
                  type boolean;
                } //default

              } //container min-thresh-separation

              container priority {
                description
                    "Configure Priority Levels";
                leaf level {
                  type uint32 {
                    range "1..8";
                  }
                } //level

                container mbs-contribution {
                  description
                      "Configure mbs size";
                  leaf size {
                    type string;
                    description
                        "[0..16777216 | default]";
                  } //size

                  leaf bytes-kilobytes {
                    type enumeration {
                      enum bytes;
                      enum kilobytes;
                    }
                  } //bytes-kilobytes

                } //container mbs-contribution

              } //container priority

            } //container priority-mbs-thresholds

          } //container policer-control-policy

          container scheduler-policy {
            description
                "Apply an egress scheduler policy";
            leaf scheduler-policy-name {
              type string {
                length "1..32";
              }
            } //scheduler-policy-name

            list scheduler {
              key "scheduler-name";
              description
                  "Configure scheduler override parameters";
              leaf scheduler-name {
                type string {
                  length "1..32";
                }
              } //scheduler-name

              leaf rate {
                type string;
                description
                    "[1..3200000000|max] Kbps";
              } //rate

              leaf cir {
                type string;
                description
                    "[0..3200000000|sum|max] Kbps";
              } //cir

            } //list scheduler

          } //container scheduler-policy

        } //container egress

        container hsmda {
          description
              "Configure HSMDA queue parameters";
          container egress-qos {
            description
                "Configure HSMDA-2 egress QoS";
            container agg-rate-limit {
              description
                  "Configure HSMDA-2 egress aggregate rate limit";
              leaf kilobits-per-second {
                type string;
                description
                    "[1..100000000|max] Kbps";
              } //kilobits-per-second

              leaf min-resv-bw {
                type uint32 {
                  range "0..100000000";
                }
              } //min-resv-bw

            } //container agg-rate-limit

            container qos {
              description
                  "Configure the SAP egress QoS policy";
              leaf policy-id {
                type string;
                description
                    "[1..65535]|<name:64 char max>";
              } //policy-id

              container packet-byte-offset {
                description
                    "Specify a packet offset for HSMDA-2 queue accounting";
                leaf add {
                  type uint32 {
                    range "0..31";
                  }
                } //add

                leaf subtract {
                  type string;
                  description
                      "Attribute sub-bytes for packet-byte-offset";
                } //subtract

              } //container packet-byte-offset

              container wrr-policy {
                description
                    "Configure the HSMDA-2 weighted round robin policy";
                leaf hsmda-wrr-policy-name {
                  type string {
                    length "1..32";
                  }
                  description
                      "[32 chars max]";
                } //hsmda-wrr-policy-name

              } //container wrr-policy

              list queue {
                key "queue-id";
                description
                    "Configure overrides for a HSMDA-2 egress queue";
                leaf queue-id {
                  type int32 {
                    range "1..8";
                  }
                } //queue-id

                container mbs {
                  description
                      "Specify MBS";
                  leaf mbs-string {
                    type string;
                  } //mbs-string

                  leaf mbs-id-2 {
                    type enumeration {
                      enum bytes;
                      enum kilobytes;
                    }
                  } //mbs-id-2

                } //container mbs

                container rate {
                  description
                      "Specify rates (CIR and PIR)";
                  leaf pir-rate {
                    type string;
                    description
                        "[1..100000000|max] Kbps";
                  } //pir-rate

                } //container rate

                container slope-policy {
                  description
                      "Configure the HSMDA-2 slope policy";
                  leaf hsmda-slope-policy {
                    type string {
                      length "1..32";
                    }
                  } //hsmda-slope-policy

                } //container slope-policy

                container stat-mode {
                  description
                      "Specify Stat Mode for the queue";
                  leaf stat-mode-id {
                    type enumeration {
                      enum v4-v6;
                    }
                  } //stat-mode-id

                } //container stat-mode

                container wrr-weight {
                  description
                      "Configure the HSMDA-2 weighted round robin weight";
                  leaf weight {
                    type uint8 {
                      range "1..32";
                    }
                    description
                        "Attribute weight for wrr-weight";
                  } //weight

                } //container wrr-weight

              } //list queue

            } //container qos

          } //container egress-qos

          container ingress-qos {
            description
                "Configure HSMDA-2 ingress QoS";
            container qos {
              description
                  "Configure the SAP ingress QoS policy";
              leaf policy-id {
                type string;
                description
                    "[1..65535]|<name:64 char max>";
              } //policy-id

              list policer {
                key "policer-id";
                description
                    "Configure overrides for a HSMDA-2 ingress policer";
                leaf policer-id {
                  type uint32 {
                    range "1..63";
                  }
                } //policer-id

                container stat-mode {
                  description
                      "Specify Stat Mode for the policer";
                  leaf stat-mode-id {
                    type enumeration {
                      enum v4-v6;
                    }
                  } //stat-mode-id

                } //container stat-mode

              } //list policer

              list queue {
                key "queue-id";
                description
                    "Configure overrides for a HSMDA-2 ingress queue";
                leaf queue-id {
                  type int32 {
                    range "1..32";
                  }
                } //queue-id

                container stat-mode {
                  description
                      "Specify Stat Mode for the queue";
                  leaf stat-mode-id {
                    type enumeration {
                      enum v4-v6;
                    }
                  } //stat-mode-id

                } //container stat-mode

              } //list queue

            } //container qos

          } //container ingress-qos

        } //container hsmda

        container ingress {
          description
              "Configure subscriber profile ingress settings";
          container policer-control-policy {
            description
                "Configure Qos Policer control Policy";
            leaf policer-control-policy-name {
              type string {
                length "1..32";
              }
            } //policer-control-policy-name

            container max-rate {
              description
                  "Configure Max Rate in kilobits-per-second";
              leaf rate {
                type string;
                description
                    "[1..2000000000|max] Kbps";
              } //rate

            } //container max-rate

            container priority-mbs-thresholds {
              description
                  "Configure priority mbs thresholds";
              container min-thresh-separation {
                description
                    "configure min threshold separation";
                leaf size {
                  type int32 {
                    range "0..16777216";
                  }
                } //size

                leaf bytes-kilobytes {
                  type enumeration {
                    enum bytes;
                    enum kilobytes;
                  }
                } //bytes-kilobytes

                leaf default {
                  type boolean;
                } //default

              } //container min-thresh-separation

              container priority {
                description
                    "Configure Priority Levels";
                leaf level {
                  type uint32 {
                    range "1..8";
                  }
                } //level

                container mbs-contribution {
                  description
                      "Configure mbs size";
                  leaf size {
                    type string;
                    description
                        "[0..16777216 | default]";
                  } //size

                  leaf bytes-kilobytes {
                    type enumeration {
                      enum bytes;
                      enum kilobytes;
                    }
                  } //bytes-kilobytes

                } //container mbs-contribution

              } //container priority

            } //container priority-mbs-thresholds

          } //container policer-control-policy

          container scheduler-policy {
            description
                "Apply an ingress scheduler policy";
            leaf scheduler-policy-name {
              type string {
                length "1..32";
              }
            } //scheduler-policy-name

            list scheduler {
              key "scheduler-name";
              description
                  "Configure scheduler override parameters";
              leaf scheduler-name {
                type string {
                  length "1..32";
                }
              } //scheduler-name

              leaf rate {
                type string;
                description
                    "[1..3200000000|max] Kbps";
              } //rate

              leaf cir {
                type string;
                description
                    "[0..3200000000|sum|max] Kbps";
              } //cir

            } //list scheduler

          } //container scheduler-policy

        } //container ingress

        container radius-accounting {
          description
              "Configure RADIUS accounting settings";
          container policy {
            description
                "Configure one or more RADIUS accounting policies";
            leaf name1 {
              type string {
                length "1..32";
              }
            } //name1

            leaf name2 {
              type string {
                length "1..32";
              }
            } //name2

            leaf name3 {
              type string {
                length "1..32";
              }
            } //name3

            leaf name4 {
              type string {
                length "1..32";
              }
            } //name4

            leaf name5 {
              type string {
                length "1..32";
              }
            } //name5

          } //container policy

          leaf session-optimized-stop {
            type boolean;
            description
                "Enable the optimization for PPPoE session accounting stop behavior";
          }

        } //container radius-accounting

        container sla-profile-map {
          description
              "Configure an SLA profile mapping";
          list entry {
            key "key";
            description
                "Configure an SLA profile string";
            leaf key {
              type string;
              description
                  "Attribute profile-string for entry";
            } //key

            leaf sla-profile {
              type string {
                length "1..32";
              }
            } //sla-profile

          } //list entry

          leaf use-direct-map-as-default {
            type boolean;
            description
                "Enable/disable direct mapping of SLA profile as default";
          }

        } //container sla-profile-map

      } //list sub-profile

      container svlan-statistics {
        description
            "Configure Subscriber VLAN statistics collection";
        leaf shutdown {
          type boolean;
          description
              "Disable or enable collection of Subscriber VLAN statistics";
        }

      } //container svlan-statistics

      container vrgw {
        description
            "Configure Virtual Residential Gateway functionality";
        container brg {
          description
              "Configure Bridged Residential Gateway functionality";
          list brg-profile {
            key "profile-name";
            description
                "Configure a profile for Bridged Residential Gateway devices";
            leaf profile-name {
              type string;
            } //profile-name

            container connectivity-verification {
              description
                  "Configure the BRG connectivity verification";
              leaf count {
                type uint32 {
                  range "1..5";
                }
              } //count

              leaf timeout {
                type uint32 {
                  range "5..60";
                }
              } //timeout

              leaf retry-time {
                type uint32 {
                  range "300..3600";
                }
              } //retry-time

            } //container connectivity-verification

            container description {
              description
                  "Configure a description text";
              leaf description-string {
                type string {
                  length "1..80";
                }
              } //description-string

            } //container description

            container hold-time {
              description
                  "Configure the time to hold on to a BRG that went down";
              leaf seconds {
                type uint32 {
                  range "30..2592000";
                }
              } //seconds

              leaf days {
                type uint32 {
                  range "1..30";
                }
              } //days

              leaf hrs {
                type uint32 {
                  range "1..23";
                }
              } //hrs

              leaf min {
                type uint32 {
                  range "1..59";
                }
              } //min

              leaf sec {
                type uint32 {
                  range "1..59";
                }
              } //sec

            } //container hold-time

            container initial-hold-time {
              description
                  "Configure the time to hold on to a BRG after it appeared";
              leaf seconds {
                type uint32 {
                  range "0..900";
                }
              } //seconds

              leaf min {
                type uint32 {
                  range "1..15";
                }
              } //min

              leaf sec {
                type uint32 {
                  range "1..59";
                }
              } //sec

            } //container initial-hold-time

            list radius-proxy-server {
              key "router name";
              description
                  "Subscribe to a Radius proxy server";
              leaf router {
                type string {
                  length "1..32";
                }
                description
                    "Attribute router-instance for radius-proxy-server";
              } //router

              leaf name {
                type string {
                  length "1..32";
                }
              } //name

            } //list radius-proxy-server

            container sla-profile-string {
              description
                  "Configure the SLA profile string";
              leaf string {
                type string;
              } //string

            } //container sla-profile-string

            container sub-profile-string {
              description
                  "Configure the subscriber profile string";
              leaf string {
                type string;
              } //string

            } //container sub-profile-string

            container uplink-initial-wait {
              description
                  "Configure the time needed in case of a non-routed uplink to block host set-up 
                   while waiting for the uplink to become operational";
              leaf seconds {
                type uint32 {
                  range "10..300";
                }
              } //seconds

            } //container uplink-initial-wait

            container dhcp-pool {
              description
                  "Configure a per-subscriber IPv4 address pool";
              container lease-time {
                description
                    "Configure the lease time";
                leaf seconds {
                  type uint32 {
                    range "300..315446399";
                  }
                } //seconds

                leaf days {
                  type uint32 {
                    range "1..3650";
                  }
                } //days

                leaf hrs {
                  type uint32 {
                    range "1..23";
                  }
                } //hrs

                leaf min {
                  type uint32 {
                    range "1..59";
                  }
                } //min

                leaf sec {
                  type uint32 {
                    range "1..59";
                  }
                } //sec

              } //container lease-time

              container standby-ip-lifetime {
                description
                    "Configure the lifetime of the standby IP addresses";
                leaf seconds {
                  type uint32 {
                    range "300..315446399";
                  }
                } //seconds

                leaf days {
                  type uint32 {
                    range "1..3650";
                  }
                } //days

                leaf hrs {
                  type uint32 {
                    range "1..23";
                  }
                } //hrs

                leaf min {
                  type uint32 {
                    range "1..59";
                  }
                } //min

                leaf sec {
                  type uint32 {
                    range "1..59";
                  }
                } //sec

              } //container standby-ip-lifetime

              container subnet {
                description
                    "Configure the IPv4 address subnet and range";
                leaf ip-prefix-prefix-length {
                  type string;
                  description
                      "ip-prefix - a.b.c.d (host bits must be 0) 
                       ip-prefix-leng - [1..32]";
                } //ip-prefix-prefix-length

                leaf start {
                  type inet:ip-address;
                  description
                      "a.b.c.d";
                } //start

                leaf end {
                  type inet:ip-address;
                  description
                      "ip-address";
                } //end

              } //container subnet

              container options {
                description
                    "Configure DHCP options";
                list custom-option {
                  key "option-number";
                  description
                      "Configure a DHCP option";
                  leaf option-number {
                    type int32 {
                      range "1..254";
                    }
                  } //option-number

                  leaf-list address {
                    type inet:ip-address;
                    max-elements 4;
                  } //address

                  leaf string {
                    type string {
                      length "1..127";
                    }
                  } //string

                  leaf hex {
                    type string {
                    }
                    description
                        "[0x0..0xFFFFFFFF...(max 254 hex nibbles)]";
                  } //hex

                } //list custom-option

              } //container options

            } //container dhcp-pool

            container radius-authentication {
              description
                  "Configure Radius authentication of the BRG";
              container password {
                description
                    "Configure the Radius User-Password";
                leaf password {
                  type string {
                    length "1..500";
                  }
                  description
                      "secret-key - [64 chars max] 
                       hash-key 
                       hash2-key 
                       custom-key";
                } //password

                leaf hash-hash2-custom {
                  type enumeration {
                    enum hash;
                    enum hash2;
                    enum custom;
                  }
                } //hash-hash2-custom

              } //container password

              container radius-server-policy {
                description
                    "Configure the Radius server policy used to authenticate the BRG";
                leaf policy-name {
                  type string;
                } //policy-name

              } //container radius-server-policy

            } //container radius-authentication

          } //list brg-profile

        } //container brg

        container lanext {
          description
              "Configure Home LAN Extension functionality";
          container router-target-as-number {
            description
                "Configure router target AS number";
            leaf as-number {
              type uint16 {
                range "1..65535";
              }
            } //as-number

          } //container router-target-as-number

        } //container lanext

      } //container vrgw

      uses "conf-submgmt-wlangw-r13:alu-conf-submgmt-wlangw-r13";
    } //container subscriber-mgmt

  } //grouping alu-conf-subscrmgmt-r13

} //module  alu-conf-subscrmgmt-r13
