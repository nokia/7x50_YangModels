module alu-conf-router-ogvalid-r13 {
  yang-version "1";

  namespace "urn:alcatel-lucent.com:sros:ns:yang:conf-router-ogvalid-r13";

  prefix "conf-router-ogvalid-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure origin validation on SR OS based 
       routers. 
       
       Copyright 2014-2015 Alcatel-Lucent, 2016 Nokia. All rights reserved. 
       Reproduction of this document is authorized on the condition that the 
       foregoing copyright notice is included. 
       
       This alu-conf-router-ogvalid-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-11-18";

  grouping alu-conf-router-ogvalid-r13 {
    container origin-validation {
      description
          "Configure origin validation";
      list static-entry {
        key "ip-prefix-ip-prefix-length upto origin-as";
        description
            "Configure static entry for this router instance";
        leaf ip-prefix-ip-prefix-length {
          type string;
          description
              "Attribute ip-prefix/ip-prefix-length for static-entry";
        } //ip-prefix-ip-prefix-length

        leaf upto {
          type uint32 {
            range "1..128";
          }
        } //upto

        leaf origin-as {
          type uint32;
        } //origin-as

        leaf valid-invalid {
          type enumeration {
            enum valid;
            enum invalid;
          }
          description
              "keywords";
        } //valid-invalid

      } //list static-entry

      list rpki-session {
        key "ip-address";
        description
            "Configure rpki session for origin-validation.";
        leaf ip-address {
          type string;
          description
              "Attribute ip-address for rpki-session";
        } //ip-address

        container connect-retry {
          description
              "Configure the RPKI Connect Retry timer value";
          leaf seconds {
            type uint32 {
              range "1..65535";
            }
          } //seconds

        } //container connect-retry

        container description {
          description
              "Create a textual description stored in the configuration file";
          leaf description-string {
            type string {
              length "1..80";
            }
          } //description-string

        } //container description

        container local-address {
          description
              "Create/delete RPKI local-address";
          leaf ip-address {
            type string;
            description
                "Attribute ip-address for local-address";
          } //ip-address

        } //container local-address

        container port {
          description
              "Configure RPKI port";
          leaf port-id {
            type string {
            }
            description
                "[0..65535]";
          } //port-id

        } //container port

        container refresh-time {
          description
              "Configure RPKI refresh and hold time";
          leaf seconds {
            type uint32 {
              range "30..32767";
            }
          } //seconds

          leaf hold-time {
            type uint32 {
              range "60..65535";
            }
            default 3600;
          } //hold-time

        } //container refresh-time

        leaf shutdown {
          type boolean;
          description
              "Administratively enable/disable RPKI session.";
        }

        container stale-time {
          description
              "Configure the time a neighbor discovery cache entry can remain stale before 
               being removed";
          leaf seconds {
            type uint32 {
              range "60..3600";
            }
          } //seconds

        } //container stale-time

      } //list rpki-session

    } //container origin-validation

  } //grouping alu-conf-router-ogvalid-r13

} //module  alu-conf-router-ogvalid-r13
