module alu-conf-svc-vprn-ptp-r13 {
  yang-version "1";

  namespace "urn:alcatel-lucent.com:sros:ns:yang:conf-svc-vprn-ptp-r13";

  prefix "conf-svc-vprn-ptp-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure Precision Timing Protocol for VPRN 
       services on SR OS based routers. 
       
       Copyright 2014-2015 Alcatel-Lucent, 2016 Nokia. All rights reserved. 
       Reproduction of this document is authorized on the condition that the 
       foregoing copyright notice is included. 
       
       This alu-conf-svc-vprn-ptp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vprn-ptp-r13 {
    container ptp {
      presence
          "Configure Precision Timing Protocol for VPRN services";
      container peer-limit {
        description
            "Configure the maximum number of PTP slave peers that may be dynamically 
             created on the vprn service";
        leaf limit {
          type string;
          description
              "Attribute limit for peer-limit";
        } //limit

      } //container peer-limit

      leaf shutdown {
        type boolean;
        description
            "Administratively enable or disable the operation of PTP on the VPRN service";
      }

      list peer {
        key "peer-id";
        description
            "Configure a PTP master Peer";
        leaf peer-id {
          type inet:ip-address;
        } //peer-id

        container local-priority {
          description
              "Configure the PTP peer local priority";
          leaf local-priority {
            type uint32 {
              range "1..255";
            }
            default 128;
            description
                "[1..255] - Default: 128";
          } //local-priority

        } //container local-priority

        container log-sync-interval {
          description
              "Configure the PTP peer sync message interval (specified as the logarithm to 
               the base 2 in seconds)";
          leaf log-interval {
            type int32 {
              range "-6..0";
            }
            description
                "Attribute log-interval for log-sync-interval";
          } //log-interval

        } //container log-sync-interval

        leaf shutdown {
          type boolean;
          description
              "Administratively shutdown the PTP peer";
        }

      } //list peer

    } //container ptp

  } //grouping alu-conf-svc-vprn-ptp-r13

} //module  alu-conf-svc-vprn-ptp-r13
