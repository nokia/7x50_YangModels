module alu-conf-mcastmgmt-r13 {
  yang-version "1";

  namespace "urn:alcatel-lucent.com:sros:ns:yang:conf-mcastmgmt-r13";

  prefix "conf-mcastmgmt-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure Multicast Path Management on SR OS 
       based routers. 
       
       Copyright 2014-2015 Alcatel-Lucent, 2016 Nokia. All rights reserved. 
       Reproduction of this document is authorized on the condition that the 
       foregoing copyright notice is included. 
       
       This alu-conf-mcastmgmt-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-07-24";

  grouping alu-conf-mcastmgmt-r13 {
    container mcast-management {
      description
          "Configure Multicast Path Management";
      list bandwidth-policy {
        key "policy-name";
        description
            "Configure multicast bandwidth policy";
        leaf policy-name {
          type string {
            length "1..32";
          }
        } //policy-name

        container admin-bw-threshold {
          description
              "Configure admin bandwidth threshold";
          leaf kilo-bits-per-second {
            type uint32 {
              range "1..40000000";
            }
          } //kilo-bits-per-second

        } //container admin-bw-threshold

        container description {
          description
              "Add/remove description for mcast bandwidth policy";
          leaf description {
            type string {
              length "1..80";
            }
            description
                "[Max 80 chars]";
          } //description

        } //container description

        container falling-percent-reset {
          description
              "Configure falling percent reset";
          leaf percent-of-highest {
            type uint32 {
              range "1..100";
            }
          } //percent-of-highest

        } //container falling-percent-reset

        container mcast-pool {
          description
              "Configure mcast pool parameters";
          leaf percent-of-total {
            type uint32 {
              range "1..50";
            }
          } //percent-of-total

          leaf resv-cbs {
            type uint32 {
              range "1..100";
            }
          } //resv-cbs

          leaf slope-policy {
            type string {
              length "1..32";
            }
            description
                "[Max 32 chars]";
          } //slope-policy

        } //container mcast-pool

        container ancillary-path {
          status "obsolete";
          description
              "Configure ancillary path parameters";
          container path-limit {
            status "obsolete";
            description
                "Configure path limit";
            leaf megabits-per-second {
              type uint32 {
                range "1..5000";
              }
            } //megabits-per-second

          } //container path-limit

          container queue-parameters {
            status "obsolete";
            description
                "Configure queue parameters";
            container cbs {
              status "obsolete";
              description
                  "Configure committed buffer size(cbs)";
              leaf percentage {
                type string;
                description
                    "[0.00..100.00]";
              } //percentage

            } //container cbs

            container hi-priority-only {
              status "obsolete";
              description
                  "Configure percent of queue depth reserved for high congestion priority traffic";
              leaf percent-of-mbs {
                type uint32 {
                  range "0..100";
                }
              } //percent-of-mbs

            } //container hi-priority-only

            container mbs {
              status "obsolete";
              description
                  "Configure maximum buffer size (mbs)";
              leaf percentage {
                type string;
                description
                    "[0.01..100.00]";
              } //percentage

            } //container mbs

          } //container queue-parameters

        } //container ancillary-path

        container primary-path {
          status "obsolete";
          description
              "Configure primary path parameters";
          container path-limit {
            status "obsolete";
            description
                "Configure path limit";
            leaf megabits-per-second {
              type uint32 {
                range "1..2000";
              }
            } //megabits-per-second

          } //container path-limit

          container queue-parameters {
            status "obsolete";
            description
                "Configure queue parameters";
            container cbs {
              status "obsolete";
              description
                  "Configure committed buffer size(cbs)";
              leaf percentage {
                type string;
                description
                    "[0.00..100.00]";
              } //percentage

            } //container cbs

            container hi-priority-only {
              status "obsolete";
              description
                  "Configure percent of queue depth reserved for high congestion priority traffic";
              leaf percent-of-mbs {
                type uint32 {
                  range "0..100";
                }
              } //percent-of-mbs

            } //container hi-priority-only

            container mbs {
              status "obsolete";
              description
                  "Configure maximum buffer size (mbs)";
              leaf percentage {
                type string;
                description
                    "[0.01..100.00]";
              } //percentage

            } //container mbs

          } //container queue-parameters

        } //container primary-path

        container secondary-path {
          status "obsolete";
          description
              "Configure secondary path parameters";
          container path-limit {
            status "obsolete";
            description
                "Configure path limit";
            leaf megabits-per-second {
              type uint32 {
                range "1..2000";
              }
            } //megabits-per-second

          } //container path-limit

          container queue-parameters {
            status "obsolete";
            description
                "Configure queue parameters";
            container cbs {
              status "obsolete";
              description
                  "Configure committed buffer size(cbs)";
              leaf percentage {
                type string;
                description
                    "[0.00..100.00]";
              } //percentage

            } //container cbs

            container hi-priority-only {
              status "obsolete";
              description
                  "Configure percent of queue depth reserved for high congestion priority traffic";
              leaf percent-of-mbs {
                type uint32 {
                  range "0..100";
                }
              } //percent-of-mbs

            } //container hi-priority-only

            container mbs {
              status "obsolete";
              description
                  "Configure maximum buffer size (mbs)";
              leaf percentage {
                type string;
                description
                    "[0.01..100.00]";
              } //percentage

            } //container mbs

          } //container queue-parameters

        } //container secondary-path

        container t2-paths {
          description
              "Context to define t2-paths queuing parameters for primary and secondary paths";
          container primary-path {
            description
                "Configure primary path parameters";
            container queue-parameters {
              description
                  "Configure queue parameters";
              container cbs {
                description
                    "Configure committed buffer size(cbs)";
                leaf percentage {
                  type string;
                  description
                      "[0.00..100.00]";
                } //percentage

              } //container cbs

              container hi-priority-only {
                status "obsolete";
                description
                    "Configure percent of queue depth reserved for high congestion priority traffic";
                leaf percent-of-mbs {
                  type uint32 {
                    range "0..100";
                  }
                } //percent-of-mbs

              } //container hi-priority-only

              container mbs {
                description
                    "Configure maximum buffer size (mbs)";
                leaf percentage {
                  type string;
                  description
                      "[0.01..100.00]";
                } //percentage

              } //container mbs

              container drop-tail {
                description
                    "Configure drop-tail parameters";
                container low {
                  description
                      "Configure low parameters";
                  container percent-reduction-from-mbs {
                    description
                        "Specify low drop tail percent reduction from MBS";
                    leaf percent-or-default {
                      type string;
                      description
                          "[0..100|default]";
                    } //percent-or-default

                  } //container percent-reduction-from-mbs

                } //container low

              } //container drop-tail

            } //container queue-parameters

          } //container primary-path

          container secondary-path {
            description
                "Configure secondary path parameters";
            container number-paths {
              description
                  "Configure number of secondary paths";
              leaf number-of-paths {
                type uint32 {
                  range "1..15";
                }
              } //number-of-paths

              leaf redundant-sfm {
                type uint32 {
                  range "1..15";
                }
                description
                    "number-of-paths";
              } //redundant-sfm

            } //container number-paths

            container queue-parameters {
              description
                  "Configure queue parameters";
              container cbs {
                description
                    "Configure committed buffer size(cbs)";
                leaf percentage {
                  type string;
                  description
                      "[0.00..100.00]";
                } //percentage

              } //container cbs

              container hi-priority-only {
                status "obsolete";
                description
                    "Configure percent of queue depth reserved for high congestion priority traffic";
                leaf percent-of-mbs {
                  type uint32 {
                    range "0..100";
                  }
                } //percent-of-mbs

              } //container hi-priority-only

              container mbs {
                description
                    "Configure maximum buffer size (mbs)";
                leaf percentage {
                  type string;
                  description
                      "[0.01..100.00]";
                } //percentage

              } //container mbs

              container drop-tail {
                description
                    "Configure drop-tail parameters";
                container low {
                  description
                      "Configure low parameters";
                  container percent-reduction-from-mbs {
                    description
                        "Specify low drop tail percent reduction from MBS";
                    leaf percent-or-default {
                      type string;
                      description
                          "[0..100|default]";
                    } //percent-or-default

                  } //container percent-reduction-from-mbs

                } //container low

              } //container drop-tail

            } //container queue-parameters

          } //container secondary-path

        } //container t2-paths

      } //list bandwidth-policy

      container chassis-level {
        description
            "Configure multicast plane limit";
        leaf mmrp-impm-override {
          type boolean;
          description
              "Enable/Disable managing MMRP traffic by IMPM";
        }

        leaf round-robin-inactive-records {
          type boolean;
          description
              "Enable/Disable Round Robin of Inactive Records";
        }

        container per-mcast-plane-capacity {
          presence
              "Configure multicast plane bandwidth";
          container mcast-capacity {
            description
                "Configure bandwidth used when not all switch cards are functional";
            leaf primary-percentage {
              type string;
              description
                  "[0.01..100]";
            } //primary-percentage

            leaf secondary {
              type string;
              description
                  "[0.01..100]";
            } //secondary

          } //container mcast-capacity

          container redundant-mcast-capacity {
            description
                "Configure bandwidth used when all switch cards are functional";
            leaf primary-percentage {
              type string;
              description
                  "[0.01..100]";
            } //primary-percentage

            leaf secondary {
              type string;
              description
                  "[0.01..100]";
            } //secondary

          } //container redundant-mcast-capacity

          container total-capacity {
            description
                "Configure total multicast plane bandwidth";
            leaf capacity {
              type enumeration {
                enum 2000;
                enum 4000;
                enum 5250;
                enum 8250;
                enum 15000;
                enum 16500;
                enum 17000;
                enum 19000;
                enum dynamic;
              }
              description
                  "2000|4000|5250|8250|15000|17000|19000|dynamic";
            } //capacity

          } //container total-capacity

        } //container per-mcast-plane-capacity

      } //container chassis-level

      list mcast-reporting-dest {
        key "mcast-reporting-dest-name";
        description
            "Configure mcast reporting destination";
        leaf mcast-reporting-dest-name {
          type string {
            length "1..32";
          }
        } //mcast-reporting-dest-name

        container description {
          description
              "Add/remove description for mcast reporting destination";
          leaf description {
            type string {
              length "1..80";
            }
          } //description

        } //container description

        container dest-ip-addr {
          description
              "Configure destination IP address";
          leaf ip-address {
            type inet:ip-address;
          } //ip-address

        } //container dest-ip-addr

        container max-tx-delay {
          description
              "Configure maximum transmit delay";
          leaf deci-seconds {
            type uint32 {
              range "0..100";
            }
          } //deci-seconds

        } //container max-tx-delay

        leaf shutdown {
          type boolean;
          description
              "Administratively enable/disable the mcast reporting destination";
        }

        container udp-dst-port {
          description
              "Configure destination UDP port";
          leaf port {
            type uint16 {
              range "1..65535";
            }
          } //port

        } //container udp-dst-port

      } //list mcast-reporting-dest

      list multicast-info-policy {
        key "policy-name";
        description
            "Configure Multicast Info Policy Parameters";
        leaf policy-name {
          type string {
            length "1..32";
          }
          description
              "[Max 32 chars]";
        } //policy-name

        container description {
          description
              "Add/remove description for mcast info policy";
          leaf description {
            type string {
              length "1..80";
            }
            description
                "[Max 80 chars]";
          } //description

        } //container description

        list bundle {
          key "bundle-name";
          description
              "Add/remove bundle for mcast info policy (maximum of 31 unique user-defined 
               bundles can be specified)";
          leaf bundle-name {
            type string {
              length "1..32";
            }
          } //bundle-name

          container admin-bw {
            description
                "Configure admin bandwidth";
            leaf kbps {
              type uint32 {
                range "1..40000000";
              }
            } //kbps

          } //container admin-bw

          container bw-activity {
            description
                "Configure bw activity";
            leaf use-admin-bw {
              type boolean;
            } //use-admin-bw

            leaf dynamic {
              type boolean;
            } //dynamic

            leaf falling-delay {
              type uint32 {
                range "10..3600";
              }
            } //falling-delay

            leaf black-hole-rate {
              type uint32 {
                range "1..40000000";
              }
            } //black-hole-rate

          } //container bw-activity

          container cong-priority-threshold {
            description
                "Configure cong-priority-threshold";
            leaf preference-level {
              type uint32 {
                range "0..7";
              }
            } //preference-level

          } //container cong-priority-threshold

          container description {
            description
                "Add/remove description for bundle";
            leaf description {
              type string {
                length "1..80";
              }
              description
                  "max 80 chars";
            } //description

          } //container description

          container ecmp-opt-threshold {
            description
                "Configure ecmp-opt-threshold";
            leaf preference-level {
              type uint32 {
                range "0..7";
              }
            } //preference-level

          } //container ecmp-opt-threshold

          container explicit-sf-path {
            description
                "Configure explicit sf path";
            leaf primary {
              type boolean;
            } //primary

            leaf secondary {
              type boolean;
            } //secondary

            leaf ancillary {
              type boolean;
              status "obsolete";
            } //ancillary

          } //container explicit-sf-path

          container keepalive-override {
            description
                "Configure keepalive timer override.";
            leaf seconds {
              type uint32 {
                range "10..86000";
              }
            } //seconds

          } //container keepalive-override

          container preference {
            description
                "Configure preference";
            leaf preference-level {
              type uint32 {
                range "1..7";
              }
            } //preference-level

          } //container preference

          container primary-tunnel-interface {
            description
                "Configure tunnel interfaces";
            leaf rsvp-p2mp {
              type string;
              description
                  "Attribute lsp-name for primary-tunnel-interface";
            } //rsvp-p2mp

            leaf ldp-p2mp {
              type uint32;
              description
                  "[1..4294967295]";
            } //ldp-p2mp

            leaf sender {
              type inet:ip-address;
            } //sender

          } //container primary-tunnel-interface

          list channel {
            key "ip-address ip-address-1";
            description
                "Add/remove mc-group address as a channel within a bundle";
            leaf ip-address {
              type string;
              description
                  "Attribute ip-address for channel";
            } //ip-address

            leaf ip-address-1 {
              type string;
            } //ip-address-1

            container admin-bw {
              description
                  "Configure admin bandwidth";
              leaf kbps {
                type uint32 {
                  range "1..40000000";
                }
              } //kbps

            } //container admin-bw

            container bw-activity {
              description
                  "Configure bw activity";
              leaf use-admin-bw {
                type boolean;
              } //use-admin-bw

              leaf dynamic {
                type boolean;
              } //dynamic

              leaf falling-delay {
                type uint32 {
                  range "10..3600";
                }
              } //falling-delay

              leaf black-hole-rate {
                type uint32 {
                  range "0..40000000";
                }
              } //black-hole-rate

            } //container bw-activity

            container explicit-sf-path {
              description
                  "Configure explicit sf path";
              leaf primary {
                type boolean;
              } //primary

              leaf secondary {
                type boolean;
              } //secondary

              leaf ancillary {
                type boolean;
                status "obsolete";
              } //ancillary

            } //container explicit-sf-path

            container keepalive-override {
              description
                  "Configure keepalive timer override.";
              leaf seconds {
                type uint32 {
                  range "10..86000";
                }
              } //seconds

            } //container keepalive-override

            container preference {
              description
                  "Configure preference";
              leaf preference-level {
                type uint32 {
                  range "1..7";
                }
              } //preference-level

            } //container preference

            container primary-tunnel-interface {
              description
                  "Configure tunnel interfaces";
              leaf rsvp-p2mp {
                type string;
                description
                    "Attribute lsp-name for primary-tunnel-interface";
              } //rsvp-p2mp

              leaf ldp-p2mp {
                type uint32 {
                  range "1..4294967295";
                }
                description
                    "[1..4294967295]";
              } //ldp-p2mp

              leaf sender {
                type inet:ip-address;
              } //sender

            } //container primary-tunnel-interface

            list source-override {
              key "ip-address";
              description
                  "Add/remove mc-group address as a specific multicast sender for the channel 
                   within a bundle";
              leaf ip-address {
                type string;
                description
                    "Attribute ip-address for source-override";
              } //ip-address

              container admin-bw {
                description
                    "Configure admin bandwidth";
                leaf kbps {
                  type uint32 {
                    range "1..40000000";
                  }
                } //kbps

              } //container admin-bw

              container bw-activity {
                description
                    "Configure bw activity";
                leaf use-admin-bw {
                  type boolean;
                } //use-admin-bw

                leaf dynamic {
                  type boolean;
                } //dynamic

                leaf falling-delay {
                  type uint32 {
                    range "10..3600";
                  }
                } //falling-delay

                leaf black-hole-rate {
                  type uint32 {
                    range "0..40000000";
                  }
                } //black-hole-rate

              } //container bw-activity

              container explicit-sf-path {
                description
                    "Configure explicit sf path";
                leaf primary {
                  type boolean;
                } //primary

                leaf secondary {
                  type boolean;
                } //secondary

                leaf ancillary {
                  type boolean;
                  status "obsolete";
                } //ancillary

              } //container explicit-sf-path

              container keepalive-override {
                description
                    "Configure keepalive timer override.";
                leaf seconds {
                  type uint32 {
                    range "10..86000";
                  }
                } //seconds

              } //container keepalive-override

              container preference {
                description
                    "Configure preference";
                leaf preference-level {
                  type uint32 {
                    range "1..7";
                  }
                } //preference-level

              } //container preference

              container primary-tunnel-interface {
                description
                    "Configure primary tunnel interfaces";
                leaf rsvp-p2mp {
                  type string {
                    length "1..32";
                  }
                  description
                      "[Max 32 chars]";
                } //rsvp-p2mp

                leaf ldp-p2mp {
                  type uint32 {
                    range "1..4294967295";
                  }
                  description
                      "[1..4294967295]";
                } //ldp-p2mp

                leaf sender {
                  type inet:ip-address;
                } //sender

              } //container primary-tunnel-interface

              container video {
                description
                    "Add/remove video parameters";
                container fcc-channel-type {
                  description
                      "Configure video channel type";
                  leaf hd-sd-pip {
                    type enumeration {
                      enum hd;
                      enum sd;
                      enum pip;
                    }
                    description
                        "keywords";
                  } //hd-sd-pip

                } //container fcc-channel-type

                container fcc-min-duration {
                  description
                      "Configure FCC burst minimum duration";
                  leaf time {
                    type uint32 {
                      range "300..8000";
                    }
                    description
                        "[300..8000] milliseconds";
                  } //time

                } //container fcc-min-duration

                container fcc-server {
                  description
                      "Enable/disable FCC server";
                  leaf disable {
                    type boolean;
                  } //disable

                } //container fcc-server

                container local-rt-server {
                  description
                      "Enable/disable local RT server";
                  leaf disable {
                    type boolean;
                  } //disable

                } //container local-rt-server

                container reorder-audio {
                  description
                      "Configure audio reordering";
                  leaf time {
                    type uint32 {
                      range "100..1000";
                    }
                    description
                        "[100..1000] milliseconds";
                  } //time

                } //container reorder-audio

                container rt-buffer-size {
                  description
                      "Configure the buffer size to store channel packets";
                  leaf rt-buffer-size {
                    type uint32 {
                      range "300..8000";
                    }
                  } //rt-buffer-size

                } //container rt-buffer-size

                container rt-server {
                  description
                      "Configure RT server";
                  leaf ip-address {
                    type inet:ip-address;
                  } //ip-address

                  leaf port {
                    type string;
                    description
                        "[1024..5999] | [6251..65535]";
                  } //port

                  leaf disable {
                    type boolean;
                  } //disable

                } //container rt-server

                container stream-selection {
                  description
                      "Configure stream-selection";
                  leaf source1 {
                    type inet:ip-address;
                    description
                        "a.b.c.d";
                  } //source1

                  leaf intf1 {
                    type string {
                      length "1..32";
                    }
                    description
                        "[32 chars max] (must start with a letter)";
                  } //intf1

                  leaf source2 {
                    type inet:ip-address;
                  } //source2

                  leaf intf2 {
                    type string {
                      length "1..32";
                    }
                  } //intf2

                } //container stream-selection

                container video-group {
                  description
                      "Configure the video group";
                  leaf video-group-id {
                    type uint32 {
                      range "1..4";
                    }
                  } //video-group-id

                  leaf disable {
                    type boolean;
                  } //disable

                } //container video-group

                container analyzer {
                  presence
                      "Configure analyzer";
                  container description {
                    description
                        "Configure description for analyzer";
                    leaf description {
                      type string {
                      }
                      description
                          "[Max 80 chars]";
                    } //description

                  } //container description

                  container alarms {
                    description
                        "Configure alarms for analyzer";
                    leaf cc-error {
                      type boolean;
                      description
                          "Configure cc-error for analyzer";
                    }

                    container non-vid-pid-absent {
                      description
                          "Configure non-vid-pid-absent for analyzer";
                      leaf milli-seconds {
                        type uint32 {
                          range "100..5000";
                        }
                        description
                            "[100..5000]";
                      } //milli-seconds

                    } //container non-vid-pid-absent

                    container pat-repetition {
                      description
                          "Configure pat-repetition for analyzer";
                      leaf tnc {
                        type string;
                        description
                            "[100..800] in multiples of 100 only";
                      } //tnc

                      leaf qos {
                        type string;
                        description
                            "[200..900] in multiples of 100 only and higher than tnc";
                      } //qos

                      leaf poa {
                        type string;
                        description
                            "[300..1000] in multiples of 100 only and higher than qos";
                      } //poa

                    } //container pat-repetition

                    leaf pat-syntax {
                      type boolean;
                      description
                          "Configure pat-syntax for analyzer";
                    }

                    container pcr-repetition {
                      description
                          "Configure pcr-repetition for analyzer";
                      leaf tnc {
                        type string;
                        description
                            "[100..800] in multiples of 100 only";
                      } //tnc

                      leaf qos {
                        type string;
                        description
                            "[200..900] in multiples of 100 only and higher than tnc";
                      } //qos

                      leaf poa {
                        type string;
                        description
                            "[300..1000] in multiples of 100 only and higher than qos";
                      } //poa

                    } //container pcr-repetition

                    leaf pid-pmt-unref {
                      type boolean;
                      description
                          "Configure pid-pmt-unref for analyzer";
                    }

                    container pmt-repetition {
                      description
                          "Configure pmt-repetition for analyzer";
                      leaf tnc {
                        type string;
                        description
                            "[100..4800] in multiples of 100 only";
                      } //tnc

                      leaf qos {
                        type string;
                        description
                            "[200..4900] in multiples of 100 only and higher than tnc";
                      } //qos

                      leaf poa {
                        type string;
                        description
                            "[300..5000] in multiples of 100 only and higher than qos";
                      } //poa

                    } //container pmt-repetition

                    leaf pmt-syntax {
                      type boolean;
                      description
                          "Configure pmt-syntax for analyzer";
                    }

                    container report-alarm {
                      description
                          "Configure report-alarm for analyzer";
                      leaf severity {
                        type enumeration {
                          enum tnc;
                          enum qos;
                          enum poa;
                        }
                        description
                            "keywords";
                      } //severity

                    } //container report-alarm

                    leaf tei-set {
                      type boolean;
                      description
                          "Configure tei-set for analyzer";
                    }

                    leaf ts-sync-loss {
                      type boolean;
                      description
                          "Configure ts-sync-loss for analyzer";
                    }

                    container vid-pid-absent {
                      description
                          "Configure vid-pid-absent for analyzer";
                      leaf milli-seconds {
                        type uint32 {
                          range "100..5000";
                        }
                        description
                            "[100..5000]";
                      } //milli-seconds

                    } //container vid-pid-absent

                  } //container alarms

                } //container analyzer

              } //container video

            } //list source-override

            container video {
              description
                  "Add/remove video parameters for the channel within a bundle";
              container fcc-channel-type {
                description
                    "Configure video channel type";
                leaf hd-sd-pip {
                  type enumeration {
                    enum hd;
                    enum sd;
                    enum pip;
                  }
                  description
                      "keywords";
                } //hd-sd-pip

              } //container fcc-channel-type

              container fcc-min-duration {
                description
                    "Configure FCC burst minimum duration";
                leaf time {
                  type uint32 {
                    range "300..8000";
                  }
                  description
                      "[300..8000] milliseconds";
                } //time

              } //container fcc-min-duration

              container fcc-server {
                description
                    "Enable/disable FCC server";
                leaf disable {
                  type boolean;
                } //disable

              } //container fcc-server

              container local-rt-server {
                description
                    "Enable/disable local RT server";
                leaf disable {
                  type boolean;
                } //disable

              } //container local-rt-server

              container reorder-audio {
                description
                    "Configure audio reordering";
                leaf time {
                  type uint32 {
                    range "100..1000";
                  }
                  description
                      "[100..1000] milliseconds";
                } //time

              } //container reorder-audio

              container rt-buffer-size {
                description
                    "Configure the buffer size to store channel packets";
                leaf rt-buffer-size {
                  type uint32 {
                    range "300..8000";
                  }
                } //rt-buffer-size

              } //container rt-buffer-size

              container rt-server {
                description
                    "Configure RT server";
                leaf ip-address {
                  type inet:ip-address;
                } //ip-address

                leaf port {
                  type string;
                  description
                      "[1024..5999] | [6251..65535]";
                } //port

                leaf disable {
                  type boolean;
                } //disable

              } //container rt-server

              container stream-selection {
                description
                    "Configure stream-selection";
                leaf source1 {
                  type inet:ip-address;
                  description
                      "a.b.c.d";
                } //source1

                leaf intf1 {
                  type string {
                    length "1..32";
                  }
                  description
                      "[32 chars max] (must start with a letter)";
                } //intf1

                leaf source2 {
                  type inet:ip-address;
                } //source2

                leaf intf2 {
                  type string {
                    length "1..32";
                  }
                } //intf2

              } //container stream-selection

              container video-group {
                description
                    "Configure the video group";
                leaf video-group-id {
                  type uint32 {
                    range "1..4";
                  }
                } //video-group-id

                leaf disable {
                  type boolean;
                } //disable

              } //container video-group

              container analyzer {
                presence
                    "Configure analyzer";
                container description {
                  description
                      "Configure description for analyzer";
                  leaf description {
                    type string {
                    }
                    description
                        "[Max 80 chars]";
                  } //description

                } //container description

                container alarms {
                  description
                      "Configure alarms for analyzer";
                  leaf cc-error {
                    type boolean;
                    description
                        "Configure cc-error for analyzer";
                  }

                  container non-vid-pid-absent {
                    description
                        "Configure non-vid-pid-absent for analyzer";
                    leaf milli-seconds {
                      type uint32 {
                        range "100..5000";
                      }
                      description
                          "[100..5000]";
                    } //milli-seconds

                  } //container non-vid-pid-absent

                  container pat-repetition {
                    description
                        "Configure pat-repetition for analyzer";
                    leaf tnc {
                      type string;
                      description
                          "[100..800] in multiples of 100 only";
                    } //tnc

                    leaf qos {
                      type string;
                      description
                          "[200..900] in multiples of 100 only and higher than tnc";
                    } //qos

                    leaf poa {
                      type string;
                      description
                          "[300..1000] in multiples of 100 only and higher than qos";
                    } //poa

                  } //container pat-repetition

                  leaf pat-syntax {
                    type boolean;
                    description
                        "Configure pat-syntax for analyzer";
                  }

                  container pcr-repetition {
                    description
                        "Configure pcr-repetition for analyzer";
                    leaf tnc {
                      type string;
                      description
                          "[100..800] in multiples of 100 only";
                    } //tnc

                    leaf qos {
                      type string;
                      description
                          "[200..900] in multiples of 100 only and higher than tnc";
                    } //qos

                    leaf poa {
                      type string;
                      description
                          "[300..1000] in multiples of 100 only and higher than qos";
                    } //poa

                  } //container pcr-repetition

                  leaf pid-pmt-unref {
                    type boolean;
                    description
                        "Configure pid-pmt-unref for analyzer";
                  }

                  container pmt-repetition {
                    description
                        "Configure pmt-repetition for analyzer";
                    leaf tnc {
                      type string;
                      description
                          "[100..4800] in multiples of 100 only";
                    } //tnc

                    leaf qos {
                      type string;
                      description
                          "[200..4900] in multiples of 100 only and higher than tnc";
                    } //qos

                    leaf poa {
                      type string;
                      description
                          "[300..5000] in multiples of 100 only and higher than qos";
                    } //poa

                  } //container pmt-repetition

                  leaf pmt-syntax {
                    type boolean;
                    description
                        "Configure pmt-syntax for analyzer";
                  }

                  container report-alarm {
                    description
                        "Configure report-alarm for analyzer";
                    leaf severity {
                      type enumeration {
                        enum tnc;
                        enum qos;
                        enum poa;
                      }
                      description
                          "keywords";
                    } //severity

                  } //container report-alarm

                  leaf tei-set {
                    type boolean;
                    description
                        "Configure tei-set for analyzer";
                  }

                  leaf ts-sync-loss {
                    type boolean;
                    description
                        "Configure ts-sync-loss for analyzer";
                  }

                  container vid-pid-absent {
                    description
                        "Configure vid-pid-absent for analyzer";
                    leaf milli-seconds {
                      type uint32 {
                        range "100..5000";
                      }
                      description
                          "[100..5000]";
                    } //milli-seconds

                  } //container vid-pid-absent

                } //container alarms

              } //container analyzer

            } //container video

          } //list channel

          container video {
            description
                "Add/remove video parameters for the bundle";
            container fcc-channel-type {
              description
                  "Configure video channel type";
              leaf hd-sd-pip {
                type enumeration {
                  enum hd;
                  enum sd;
                  enum pip;
                }
                description
                    "keywords";
              } //hd-sd-pip

            } //container fcc-channel-type

            container fcc-min-duration {
              description
                  "Configure FCC burst minimum duration";
              leaf time {
                type uint32 {
                  range "300..8000";
                }
                description
                    "[300..8000] milliseconds";
              } //time

            } //container fcc-min-duration

            leaf fcc-server {
              type boolean;
              description
                  "Enable/disable FCC server on the bundle";
            }

            container local-fcc-port {
              description
                  "Configure local port for FCC requests";
              leaf port-num {
                type string;
                description
                    "[1024..5999] | [6251..65535]";
              } //port-num

            } //container local-fcc-port

            container local-rt-port {
              description
                  "Configure local port for RT requests";
              leaf port-num {
                type string;
                description
                    "[1024..5999] | [6251..65535]";
              } //port-num

            } //container local-rt-port

            leaf local-rt-server {
              type boolean;
              description
                  "Enable/disable local RT server on the bundle";
            }

            container reorder-audio {
              description
                  "Configure audio reordering";
              leaf time {
                type uint32 {
                  range "100..1000";
                }
                description
                    "[100..1000] milliseconds";
              } //time

            } //container reorder-audio

            container rt-buffer-size {
              description
                  "Configure the buffer size to store channel packets";
              leaf rt-buffer-size {
                type uint32 {
                  range "300..8000";
                }
              } //rt-buffer-size

            } //container rt-buffer-size

            container rt-server {
              description
                  "Configure RT server";
              leaf ip-address {
                type inet:ip-address;
              } //ip-address

              leaf port {
                type string;
                description
                    "[1024..5999] | [6251..65535]";
              } //port

            } //container rt-server

            container stream-selection {
              description
                  "Configure stream-selection";
              leaf source1 {
                type inet:ip-address;
                description
                    "a.b.c.d";
              } //source1

              leaf intf1 {
                type string {
                  length "1..32";
                }
                description
                    "[32 chars max] (must start with a letter)";
              } //intf1

              leaf source2 {
                type inet:ip-address;
              } //source2

              leaf intf2 {
                type string {
                  length "1..32";
                }
              } //intf2

            } //container stream-selection

            container video-group {
              description
                  "Configure the video group for this bundle";
              leaf video-group-id {
                type uint32 {
                  range "1..4";
                }
              } //video-group-id

            } //container video-group

            container analyzer {
              presence
                  "Configure analyzer";
              container description {
                description
                    "Configure description for analyzer";
                leaf description {
                  type string {
                  }
                  description
                      "[Max 80 chars]";
                } //description

              } //container description

              container alarms {
                description
                    "Configure alarms for analyzer";
                leaf cc-error {
                  type boolean;
                  description
                      "Configure cc-error for analyzer";
                }

                container non-vid-pid-absent {
                  description
                      "Configure non-vid-pid-absent for analyzer";
                  leaf milli-seconds {
                    type uint32 {
                      range "100..5000";
                    }
                    description
                        "[100..5000]";
                  } //milli-seconds

                } //container non-vid-pid-absent

                container pat-repetition {
                  description
                      "Configure pat-repetition for analyzer";
                  leaf tnc {
                    type string;
                    description
                        "[100..800] in multiples of 100 only";
                  } //tnc

                  leaf qos {
                    type string;
                    description
                        "[200..900] in multiples of 100 only and higher than tnc";
                  } //qos

                  leaf poa {
                    type string;
                    description
                        "[300..1000] in multiples of 100 only and higher than qos";
                  } //poa

                } //container pat-repetition

                leaf pat-syntax {
                  type boolean;
                  description
                      "Configure pat-syntax for analyzer";
                }

                container pcr-repetition {
                  description
                      "Configure pcr-repetition for analyzer";
                  leaf tnc {
                    type string;
                    description
                        "[100..800] in multiples of 100 only";
                  } //tnc

                  leaf qos {
                    type string;
                    description
                        "[200..900] in multiples of 100 only and higher than tnc";
                  } //qos

                  leaf poa {
                    type string;
                    description
                        "[300..1000] in multiples of 100 only and higher than qos";
                  } //poa

                } //container pcr-repetition

                leaf pid-pmt-unref {
                  type boolean;
                  description
                      "Configure pid-pmt-unref for analyzer";
                }

                container pmt-repetition {
                  description
                      "Configure pmt-repetition for analyzer";
                  leaf tnc {
                    type string;
                    description
                        "[100..4800] in multiples of 100 only";
                  } //tnc

                  leaf qos {
                    type string;
                    description
                        "[200..4900] in multiples of 100 only and higher than tnc";
                  } //qos

                  leaf poa {
                    type string;
                    description
                        "[300..5000] in multiples of 100 only and higher than qos";
                  } //poa

                } //container pmt-repetition

                leaf pmt-syntax {
                  type boolean;
                  description
                      "Configure pmt-syntax for analyzer";
                }

                container report-alarm {
                  description
                      "Configure report-alarm for analyzer";
                  leaf severity {
                    type enumeration {
                      enum tnc;
                      enum qos;
                      enum poa;
                    }
                    description
                        "keywords";
                  } //severity

                } //container report-alarm

                leaf tei-set {
                  type boolean;
                  description
                      "Configure tei-set for analyzer";
                }

                leaf ts-sync-loss {
                  type boolean;
                  description
                      "Configure ts-sync-loss for analyzer";
                }

                container vid-pid-absent {
                  description
                      "Configure vid-pid-absent for analyzer";
                  leaf milli-seconds {
                    type uint32 {
                      range "100..5000";
                    }
                    description
                        "[100..5000]";
                  } //milli-seconds

                } //container vid-pid-absent

              } //container alarms

            } //container analyzer

          } //container video

        } //list bundle

        container video-policy {
          description
              "Configure video policy";
          list video-interface {
            key "ip-address";
            description
                "Configure video policy";
            leaf ip-address {
              type inet:ip-address;
            } //ip-address

            container fcc-session-timeout {
              description
                  "Configure FCC session timeout";
              leaf seconds {
                type int32 {
                  range "5..300";
                }
              } //seconds

            } //container fcc-session-timeout

            container max-igmp-latency {
              description
                  "Configure per-client maximum igmp latency";
              leaf milli-seconds {
                type uint32 {
                  range "0..60000";
                }
                description
                    "[10..1000]";
              } //milli-seconds

            } //container max-igmp-latency

            container max-sessions {
              description
                  "Configure per-client maximum number of sessions";
              leaf sessions {
                type int32 {
                  range "1..65536";
                }
              } //sessions

            } //container max-sessions

            container ret-session-timeout {
              description
                  "Configure RET session timeout";
              leaf seconds {
                type int32 {
                  range "5..300";
                }
              } //seconds

            } //container ret-session-timeout

            container rt-payload-type {
              description
                  "Configure payload type";
              leaf payload-type {
                type string;
                description
                    "33 or [96..127]";
              } //payload-type

            } //container rt-payload-type

            container rt-rate {
              description
                  "Configure rate at which RT packets are sent to client";
              leaf rt-burst-percentage {
                type uint32 {
                  range "1..100";
                }
              } //rt-burst-percentage

            } //container rt-rate

            container subscriber-bw-limit {
              description
                  "Configure per-subscriber bandwidth limit";
              leaf bandwidth {
                type uint32 {
                  range "1..4294967295";
                }
                description
                    "[1..4294967295] kbps";
              } //bandwidth

            } //container subscriber-bw-limit

            container hd {
              description
                  "Configure video policy parameters for hd channels";
              container dent-threshold {
                description
                    "Configure FCC dent threshold";
                leaf threshold {
                  type int32 {
                    range "1..31";
                  }
                } //threshold

              } //container dent-threshold

              container fcc-burst {
                description
                    "Configure FCC burst rate";
                leaf burst-percentage {
                  type int32 {
                    range "0..600";
                  }
                } //burst-percentage

              } //container fcc-burst

              container fcc-server {
                description
                    "Enable/disable FCC server";
                leaf mode {
                  type enumeration {
                    enum burst;
                    enum dent;
                    enum hybrid;
                  }
                  description
                      "keywords";
                } //mode

              } //container fcc-server

              leaf local-rt-server {
                type boolean;
                description
                    "Enable/disable local RT server";
              }

              container mc-handover {
                description
                    "Configure FCC server rate during handover";
                leaf percentage {
                  type uint32 {
                    range "0..100";
                  }
                } //percentage

              } //container mc-handover

              container rt-rate {
                description
                    "Configure rate at which RT packets are sent to client";
                leaf rt-burst-percentage {
                  type uint32 {
                    range "1..100";
                  }
                } //rt-burst-percentage

              } //container rt-rate

            } //container hd

            container pip {
              description
                  "Configure video policy parameters for pip channels";
              container dent-threshold {
                description
                    "Configure FCC dent threshold";
                leaf threshold {
                  type int32 {
                    range "1..31";
                  }
                } //threshold

              } //container dent-threshold

              container fcc-burst {
                description
                    "Configure FCC burst rate";
                leaf burst-percentage {
                  type int32 {
                    range "0..600";
                  }
                } //burst-percentage

              } //container fcc-burst

              container fcc-server {
                description
                    "Enable/disable FCC server";
                leaf mode {
                  type enumeration {
                    enum burst;
                    enum dent;
                    enum hybrid;
                  }
                  description
                      "keywords";
                } //mode

              } //container fcc-server

              leaf local-rt-server {
                type boolean;
                description
                    "Enable/disable local RT server";
              }

              container mc-handover {
                description
                    "Configure FCC server rate during handover";
                leaf percentage {
                  type uint32 {
                    range "0..600";
                  }
                } //percentage

              } //container mc-handover

              container rt-rate {
                description
                    "Configure rate at which RT packets are sent to client";
                leaf rt-burst-percentage {
                  type uint32 {
                    range "1..100";
                  }
                } //rt-burst-percentage

              } //container rt-rate

            } //container pip

            container sd {
              description
                  "Configure video policy parameters for sd channels";
              container dent-threshold {
                description
                    "Configure FCC dent threshold";
                leaf threshold {
                  type int32 {
                    range "1..31";
                  }
                } //threshold

              } //container dent-threshold

              container fcc-burst {
                description
                    "Configure FCC burst rate";
                leaf burst-percentage {
                  type int32 {
                    range "0..600";
                  }
                } //burst-percentage

              } //container fcc-burst

              container fcc-server {
                description
                    "Enable/disable FCC server";
                leaf mode {
                  type enumeration {
                    enum burst;
                    enum dent;
                    enum hybrid;
                  }
                  description
                      "keywords";
                } //mode

              } //container fcc-server

              leaf local-rt-server {
                type boolean;
                description
                    "Enable/disable local RT server";
              }

              container mc-handover {
                description
                    "Configure FCC server rate during handover";
                leaf percentage {
                  type uint32 {
                    range "0..600";
                  }
                } //percentage

              } //container mc-handover

              container rt-rate {
                description
                    "Configure rate at which RT packets are sent to client";
                leaf rt-burst-percentage {
                  type uint32 {
                    range "1..100";
                  }
                } //rt-burst-percentage

              } //container rt-rate

            } //container sd

          } //list video-interface

        } //container video-policy

      } //list multicast-info-policy

    } //container mcast-management

  } //grouping alu-conf-mcastmgmt-r13

} //module  alu-conf-mcastmgmt-r13
