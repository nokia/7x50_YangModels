module alu-conf-router-ldp-r13 {
  yang-version "1";

  namespace "urn:alcatel-lucent.com:sros:ns:yang:conf-router-ldp-r13";

  prefix "conf-router-ldp-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure LDP on SR OS based routers. 
       
       Copyright 2014-2015 Alcatel-Lucent, 2016 Nokia. All rights reserved. 
       Reproduction of this document is authorized on the condition that the 
       foregoing copyright notice is included. 
       
       This alu-conf-router-ldp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-05-15";

  grouping alu-conf-router-ldp-r13 {
    container ldp {
      presence
          "Configure LDP";
      container class-forwarding {
        description
            "Enables/Disables class based forwarding for LDP-over-RSVP";
        leaf cbf-mode {
          type enumeration {
            enum lsr;
            enum ler;
            enum lsr-and-ler;
          }
        } //cbf-mode

      } //container class-forwarding

      leaf consider-system-ip-in-gep {
        type boolean;
        description
            "Enable/disable whether system IP FEC creation is affected by the LDP global 
             export policy";
      }

      leaf entropy-label-capability {
        type boolean;
        description
            "Enable/disable the entropy label capability on LDP instance";
      }

      container export {
        description
            "Apply export policies to filter label bindings advertised to all peers";
        leaf-list policy-name {
          type string {
            length "1..32";
          }
          max-elements 5;
        } //policy-name

      } //container export

      container export-tunnel-table {
        description
            "Apply Tunnel table export policies to filter label bindings advertised to all 
             peers";
        leaf-list policy-name {
          type string {
            length "1..32";
          }
          max-elements 5;
          description
              "[32 chars max]";
        } //policy-name

      } //container export-tunnel-table

      container fast-reroute {
        description
            "Enable/Disable fast re-route of ldp tunnel";
        leaf backup-sr-tunnel {
          type boolean;
        } //backup-sr-tunnel

      } //container fast-reroute

      list fec-originate {
        key "ip-address-mask";
        description
            "Configure a static prefix FEC";
        leaf ip-address-mask {
          type string;
          description
              "Attribute ip-address/mask for fec-originate";
        } //ip-address-mask

        leaf advertised-label {
          type string;
          description
              "Attribute in-label for fec-originate";
        } //advertised-label

        leaf next-hop {
          type string;
          description
              "Attribute ip-address for fec-originate";
        } //next-hop

        leaf swap-label {
          type uint32 {
            range "16..1048575";
          }
        } //swap-label

        leaf pop {
          type boolean;
        } //pop

        leaf interface {
          type string {
            length "1..32";
          }
        } //interface

      } //list fec-originate

      leaf generate-basic-fec-only {
        type boolean;
        description
            "Enable/disable generation of recursive FEC";
      }

      leaf implicit-null-label {
        type boolean;
        description
            "Enable/disable signalling of implicit null label for all prefix fecs";
      }

      container import {
        description
            "Apply import policies to filter label bindings received from all peers";
        leaf-list policy-name {
          type string {
            length "1..32";
          }
          max-elements 5;
        } //policy-name

      } //container import

      container import-mcast-policy {
        description
            "Configure import multicast policy used for controlling which multicast FECs 
             are accepted from downstream peers for resolution";
        leaf-list policy-name {
          type string {
            length "1..32";
          }
          max-elements 5;
        } //policy-name

      } //container import-mcast-policy

      container import-tunnel-table {
        description
            "Apply import policies for controlling the insertion of non-host prefixes 
             resolved by LDP into the tunnel table";
        leaf-list policy-name {
          type string {
            length "1..32";
          }
          max-elements 5;
        } //policy-name

      } //container import-tunnel-table

      container label-withdrawal-delay {
        description
            "configure ldp label-withdrawal-delay";
        leaf seconds {
          type uint32 {
            range "3..120";
          }
          description
              "[3..120]";
        } //seconds

      } //container label-withdrawal-delay

      leaf legacy-ipv4-lsr-interop {
        type boolean;
        description
            "Configure/de-configure interoperability with legacy IPv4 LSR implementations";
      }

      container max-ecmp-routes {
        description
            "Configure the maximum ECMP value for LDP";
        leaf max-ecmp-routes-id {
          type uint32 {
            range "1..64";
          }
        } //max-ecmp-routes-id

      } //container max-ecmp-routes

      leaf mcast-upstream-asbr-frr {
        type boolean;
        description
            "Enable/disable ASBR MoFRR";
      }

      leaf mcast-upstream-frr {
        type boolean;
        description
            "Configure mLDP fast upstream switchover";
      }

      container mp-mbb-time {
        description
            "Configure MP MBB time";
        leaf interval {
          type uint32 {
            range "0..10";
          }
          description
              "[0..10] seconds";
        } //interval

      } //container mp-mbb-time

      leaf prefer-tunnel-in-tunnel {
        type boolean;
        description
            "Configure preference of tunnel-in-tunnel for prefix LDP tunnels";
      }

      container resolve-root-using {
        description
            "Configure RTM table to use for P2MP tunnel root resolution";
        leaf resolve-root-using-id {
          type enumeration {
            enum ucast-rtm;
            enum mcast-rtm;
          }
        } //resolve-root-using-id

      } //container resolve-root-using

      leaf shortcut-local-ttl-propagate {
        type boolean;
        description
            "Enable/disable TTL propagation over LSP shortcut for local packets";
      }

      leaf shortcut-transit-ttl-propagate {
        type boolean;
        description
            "Enable/disable TTL propagation over LSP shortcut for transit packets";
      }

      leaf shutdown {
        type boolean;
        description
            "Administratively enable/disable LDP instance";
      }

      container tunnel-down-damp-time {
        description
            "Configure the time interval that LDP damps a tunnel down event before posting 
             to the Route Table Manager (RTM)";
        leaf seconds {
          type uint32 {
            range "0..20";
          }
        } //seconds

      } //container tunnel-down-damp-time

      leaf weighted-ecmp {
        type boolean;
        description
            "Enable/disable weighted ecmp on LDP instance";
      }

      container aggregate-prefix-match {
        presence
            "Enable/Disable aggregate prefix match procedures";
        container prefix-exclude {
          description
              "Configure policy name containing the prefixes to be excluded from the 
               aggregate prefix match procedures";
          leaf-list policy-name {
            type string {
              length "1..32";
            }
            max-elements 5;
          } //policy-name

        } //container prefix-exclude

        leaf shutdown {
          type boolean;
          description
              "Administratively enable/disable use of aggregate prefix match procedures by 
               LDP instance";
        }

      } //container aggregate-prefix-match

      container egress-statistics {
        description
            "Configure LDP Egress statistics";
        list fec-prefix {
          key "ip-prefix-ip-prefix-length";
          description
              "Configure FEC prefix";
          leaf ip-prefix-ip-prefix-length {
            type string;
            description
                "Attribute ip-prefix/ip-prefix-length for fec-prefix";
          } //ip-prefix-ip-prefix-length

          container accounting-policy {
            description
                "Configure accounting policy id";
            leaf policy-id {
              type uint32 {
                range "1..99";
              }
            } //policy-id

          } //container accounting-policy

          leaf collect-stats {
            type boolean;
            description
                "Enable/Disable collection of statistics";
          }

          leaf shutdown {
            type boolean;
            description
                "Administratively enable/disable LDP egress statistics";
          }

        } //list fec-prefix

      } //container egress-statistics

      container graceful-restart {
        presence
            "Configure graceful restart helper";
        container maximum-recovery-time {
          description
              "Configures the local maximum recovery time";
          leaf interval {
            type uint32 {
              range "15..1800";
            }
            description
                "[15..1800] seconds";
          } //interval

        } //container maximum-recovery-time

        container neighbor-liveness-time {
          description
              "Configures neighbor-liveness time";
          leaf interval {
            type uint32 {
              range "5..300";
            }
            description
                "[5..300] seconds";
          } //interval

        } //container neighbor-liveness-time

      } //container graceful-restart

      container import-pmsi-routes {
        description
            "Configure import of BGP PMSI routes";
        leaf mvpn {
          type boolean;
          description
              "Enable/disable import of BGP MVPN inter-AS routes";
        }

        leaf mvpn-no-export-community {
          type boolean;
          description
              "Enable/disable import of BGP MVPN intra-AS routes";
        }

      } //container import-pmsi-routes

      container interface-parameters {
        description
            "Context to configure LDP interfaces and parameters applied to LDP interfaces";
        list interface {
          key "ip-int-name";
          description
              "Configure LDP on an IP interface";
          leaf ip-int-name {
            type string {
              length "1..32";
            }
          } //ip-int-name

          leaf dual-stack {
            type boolean;
            description
                "If this keyword is provided then IPv4 sub-interface is not created";
          } //dual-stack

          container bfd-enable {
            description
                "Enable/Disable BFD tracking of LDP Session for the interface";
            leaf ipv4 {
              type boolean;
            } //ipv4

            leaf ipv6 {
              type boolean;
            } //ipv6

          } //container bfd-enable

          container load-balancing-weight {
            description
                "Configure ECMP load-balancing-weight for the interface";
            leaf load-balancing-weight-id {
              type uint32;
            } //load-balancing-weight-id

          } //container load-balancing-weight

          leaf shutdown {
            type boolean;
            description
                "Administratively enable/disable LDP on the interface";
          }

          container ipv4 {
            presence
                "Context to configure ipv4 LDP parameters for the interface";
            container hello {
              description
                  "Configure the hello timeout and factor for the LDP interface";
              leaf timeout {
                type string;
                description
                    "[3..65535]";
              } //timeout

              leaf factor {
                type uint32 {
                  range "1..255";
                }
              } //factor

            } //container hello

            container keepalive {
              description
                  "Configure the keep-alive timeout and factor for the LDP interface";
              leaf timeout {
                type string;
                description
                    "[3..65535]";
              } //timeout

              leaf factor {
                type uint32 {
                  range "1..255";
                }
              } //factor

            } //container keepalive

            container local-lsr-id {
              description
                  "Configure the local-lsr-id for the LDP interface";
              leaf local-lsr-id-id {
                type enumeration {
                  enum system;
                  enum interface;
                }
              } //local-lsr-id-id

              leaf interface-name {
                type string {
                }
              } //interface-name

            } //container local-lsr-id

            leaf shutdown {
              type boolean;
              description
                  "Administratively enable/disable ipv4 LDP on the interface";
            }

            container transport-address {
              description
                  "Configure the transport address used to set up LDP TCP sessions on the LDP 
                   interface";
              leaf system-interface {
                type enumeration {
                  enum system;
                  enum interface;
                }
              } //system-interface

            } //container transport-address

            container fec-type-capability {
              description
                  "Configure fec capabilities on the LDP interface";
              container p2mp-ipv4 {
                description
                    "Enable/Disable ipv4 p2mp fec capability on the interface";
                leaf p2mp-ipv4-id {
                  type enumeration {
                    enum enable;
                    enum disable;
                  }
                } //p2mp-ipv4-id

              } //container p2mp-ipv4

              container p2mp-ipv6 {
                description
                    "Enable/Disable ipv6 p2mp fec capability on the interface";
                leaf p2mp-ipv6-id {
                  type enumeration {
                    enum enable;
                    enum disable;
                  }
                } //p2mp-ipv6-id

              } //container p2mp-ipv6

              container prefix-ipv4 {
                description
                    "Enable/Disable ipv4 prefix fec capability on the interface";
                leaf prefix-ipv4-id {
                  type enumeration {
                    enum enable;
                    enum disable;
                  }
                } //prefix-ipv4-id

              } //container prefix-ipv4

              container prefix-ipv6 {
                description
                    "Enable/Disable ipv6 prefix fec capability on the interface";
                leaf prefix-ipv6-id {
                  type enumeration {
                    enum enable;
                    enum disable;
                  }
                } //prefix-ipv6-id

              } //container prefix-ipv6

            } //container fec-type-capability

          } //container ipv4

          container ipv6 {
            presence
                "Context to configure ipv6 LDP parameters for the interface";
            container hello {
              description
                  "Configure the hello timeout and factor for the LDP interface";
              leaf timeout {
                type string;
                description
                    "[3..65535]";
              } //timeout

              leaf factor {
                type uint32 {
                  range "1..255";
                }
              } //factor

            } //container hello

            container keepalive {
              description
                  "Configure the keep-alive timeout and factor for the LDP interface";
              leaf timeout {
                type string;
                description
                    "[3..65535]";
              } //timeout

              leaf factor {
                type uint32 {
                  range "1..255";
                }
              } //factor

            } //container keepalive

            container local-lsr-id {
              description
                  "Configure the local-lsr-id for the LDP interface";
              leaf local-lsr-id-id {
                type enumeration {
                  enum system;
                  enum interface;
                }
              } //local-lsr-id-id

              leaf interface-name {
                type string {
                }
              } //interface-name

              leaf t32bit-format {
                type boolean;
              } //t32bit-format

            } //container local-lsr-id

            leaf shutdown {
              type boolean;
              description
                  "Administratively enable/disable ipv6 LDP on the interface";
            }

            container transport-address {
              description
                  "Configure the transport address used to set up LDP TCP sessions on the LDP 
                   interface";
              leaf system-interface {
                type enumeration {
                  enum system;
                  enum interface;
                }
              } //system-interface

            } //container transport-address

            container fec-type-capability {
              description
                  "Configure fec capabilities on the interface";
              container p2mp-ipv4 {
                description
                    "Enable/Disable ipv4 p2mp fec capability on the interface";
                leaf p2mp-ipv4-id {
                  type enumeration {
                    enum enable;
                    enum disable;
                  }
                } //p2mp-ipv4-id

              } //container p2mp-ipv4

              container p2mp-ipv6 {
                description
                    "Enable/Disable ipv6 p2mp fec capability on the interface";
                leaf p2mp-ipv6-id {
                  type enumeration {
                    enum enable;
                    enum disable;
                  }
                } //p2mp-ipv6-id

              } //container p2mp-ipv6

              container prefix-ipv4 {
                description
                    "Enable/Disable ipv4 prefix fec capability on the interface";
                leaf prefix-ipv4-id {
                  type enumeration {
                    enum enable;
                    enum disable;
                  }
                } //prefix-ipv4-id

              } //container prefix-ipv4

              container prefix-ipv6 {
                description
                    "Enable/Disable ipv6 prefix fec capability on the interface";
                leaf prefix-ipv6-id {
                  type enumeration {
                    enum enable;
                    enum disable;
                  }
                } //prefix-ipv6-id

              } //container prefix-ipv6

            } //container fec-type-capability

          } //container ipv6

        } //list interface

        container ipv4 {
          description
              "Context to configure ipv4 LDP interfaces and parameters applied to LDP 
               interfaces";
          container hello {
            description
                "Configure the hello timeout and factor for LDP interfaces";
            leaf timeout {
              type string;
              description
                  "[3..65535]";
            } //timeout

            leaf factor {
              type uint32 {
                range "1..255";
              }
            } //factor

          } //container hello

          container keepalive {
            description
                "Configure the keepalive timeout and factor for LDP interfaces";
            leaf timeout {
              type string;
              description
                  "[3..65535]";
            } //timeout

            leaf factor {
              type uint32 {
                range "1..255";
              }
            } //factor

          } //container keepalive

          container transport-address {
            description
                "Configure the transport address used to set up LDP TCP sessions on LDP 
                 interfaces";
            leaf system-interface {
              type enumeration {
                enum system;
                enum interface;
              }
              description
                  "keywords";
            } //system-interface

          } //container transport-address

        } //container ipv4

        container ipv6 {
          description
              "Context to configure ipv6 LDP interfaces and parameters applied to LDP 
               interfaces";
          container hello {
            description
                "Configure the hello timeout and factor for LDP interfaces";
            leaf timeout {
              type string;
              description
                  "[3..65535]";
            } //timeout

            leaf factor {
              type uint32 {
                range "1..255";
              }
            } //factor

          } //container hello

          container keepalive {
            description
                "Configure the keepalive timeout and factor for LDP interfaces";
            leaf timeout {
              type string;
              description
                  "[3..65535]";
            } //timeout

            leaf factor {
              type uint32 {
                range "1..255";
              }
            } //factor

          } //container keepalive

          container transport-address {
            description
                "Configure the transport address used to set up LDP TCP sessions on LDP 
                 interfaces";
            leaf system-interface {
              type enumeration {
                enum system;
                enum interface;
              }
              description
                  "keywords";
            } //system-interface

          } //container transport-address

        } //container ipv6

      } //container interface-parameters

      list lsp-bfd {
        key "prefix-list-name";
        description
            "Configure Bidirectional Forwarding Detection (BFD) parameters for a policy 
             options prefix list";
        leaf prefix-list-name {
          type string {
            length "1..32";
          }
        } //prefix-list-name

        leaf bfd-enable {
          type boolean;
          description
              "Configure whether or not to enable BFD sessions for the prefix list";
        }

        container bfd-template {
          description
              "Configure the BFD template for the prefix list";
          leaf bfd-template-name {
            type string {
              length "1..32";
            }
          } //bfd-template-name

        } //container bfd-template

        container failure-action {
          description
              "Configure the reaction to a BFD session failure for the prefix list";
          leaf down {
            type enumeration {
              enum down;
            }
            description
                "keyword - make the LSP unavailable to user traffic";
          } //down

        } //container failure-action

        container lsp-ping-interval {
          description
              "Configure the transmit interval for LSP ping packets used for periodic 
               verification";
          leaf seconds {
            type string;
            description
                "0 | 60..300 - Default: 60";
          } //seconds

        } //container lsp-ping-interval

        container priority {
          description
              "Configure the priority of the prefix list, to control the search order used 
               when searching for a prefix in the set of prefix lists";
          leaf priority-level {
            type uint32 {
              range "1..99";
            }
            default 1;
            description
                "[1..99] - Default: 1";
          } //priority-level

        } //container priority

        container source-address {
          description
              "Configure the source address to be used in LSP ping packets and BFD control 
               packets for BFD sessions configured using the prefix list";
          leaf ip-address {
            type string;
            description
                "Attribute ip-address for source-address";
          } //ip-address

        } //container source-address

      } //list lsp-bfd

      container session-parameters {
        description
            "Context to configure peer specific parameters";
        list peer {
          key "ip-address";
          description
              "Configure parameters for an LDP peer";
          leaf ip-address {
            type string;
            description
                "Attribute ip-address for peer";
          } //ip-address

          leaf adv-adj-addr-only {
            type boolean;
            description
                "Enable/Disable to distribute only the local addresses used by the hello 
                 adjacencies with this peer.";
          }

          leaf adv-local-lsr-id {
            type boolean;
            description
                "Enable/disable advertise local lsr id";
          }

          container community {
            description
                "community string associated with a session to a given peer";
            leaf community-name {
              type string {
                length "1..32";
              }
            } //community-name

          } //container community

          leaf dod-label-distribution {
            type boolean;
            description
                "Enable/disable downstream on demand label distribution";
          }

          container export-addresses {
            description
                "Apply export prefix policies to local addresses advertised to this peer";
            leaf-list policy-name {
              type string {
                length "1..32";
              }
              max-elements 5;
            } //policy-name

          } //container export-addresses

          container export-prefixes {
            description
                "Apply export prefix policies to filter label bindings advertised to this peer";
            leaf-list policy-name {
              type string {
                length "1..32";
              }
              max-elements 5;
            } //policy-name

          } //container export-prefixes

          container fec-limit {
            description
                "Configure the max number of FECs which an LSR will accept from a given peer";
            leaf limit {
              type uint32 {
                range "1..4294967295";
              }
            } //limit

            leaf log-only {
              type boolean;
            } //log-only

            leaf threshold {
              type uint32 {
                range "1..100";
              }
            } //threshold

          } //container fec-limit

          leaf fec129-cisco-interop {
            type boolean;
            description
                "Enable/Disable support for providing translation between non-compliant FEC129 
                 formats of Cisco.";
          }

          container import-prefixes {
            description
                "Apply import prefix policies to filter label bindings received from this peer";
            leaf-list policy-name {
              type string {
                length "1..32";
              }
              max-elements 5;
            } //policy-name

          } //container import-prefixes

          leaf pe-id-mac-flush-interop {
            type boolean;
            description
                "Specifies if LDP will react to and send the non-standard PE-ID TLV in an 
                 address withdraw message to effect 'flush-all-from-me' behavior";
          }

          container fec-type-capability {
            description
                "Configure session level capabilities for all FEC types";
            container p2mp {
              description
                  "Enable/Disable p2mp fec capability for the session";
              leaf p2mp-id {
                type enumeration {
                  enum enable;
                  enum disable;
                }
              } //p2mp-id

            } //container p2mp

            container prefix-ipv4 {
              description
                  "Enable/Disable ipv4 prefix fec capability for the session";
              leaf prefix-ipv4-id {
                type enumeration {
                  enum enable;
                  enum disable;
                }
              } //prefix-ipv4-id

            } //container prefix-ipv4

            container prefix-ipv6 {
              description
                  "Enable/Disable ipv6 prefix fec capability for the session";
              leaf prefix-ipv6-id {
                type enumeration {
                  enum enable;
                  enum disable;
                }
              } //prefix-ipv6-id

            } //container prefix-ipv6

          } //container fec-type-capability

        } //list peer

      } //container session-parameters

      container targeted-session {
        description
            "Context to configure LDP targeted peers and parameters applied to targeted 
             sessions";
        leaf disable-targeted-session {
          type boolean;
          description
              "Enable/disable auto-creation of targeted sessions by SDP";
        }

        container export-prefixes {
          description
              "Configure export route policy used to determine which routes are exported to 
               this targeted LDP session";
          leaf-list policy-name {
            type string {
              length "1..32";
            }
            max-elements 5;
          } //policy-name

        } //container export-prefixes

        container import-prefixes {
          description
              "Configure the import route policy to determine which routes are accepted from 
               targeted LDP neighbors";
          leaf-list policy-name {
            type string {
              length "1..32";
            }
            max-elements 5;
          } //policy-name

        } //container import-prefixes

        list peer-template-map {
          key "peer-template";
          description
              "Configure targeted peer-template mapping to peer policies";
          leaf peer-template {
            type string {
              length "1..32";
            }
          } //peer-template

          leaf-list policy {
            type string {
              length "1..32";
            }
            max-elements 5;
          } //policy

        } //list peer-template-map

        container ipv4 {
          description
              "Context to configure ipv4 LDP targeted peers and parameters applied to 
               targeted sessions";
          container hello {
            description
                "Configure the hello timeout and factor for targeted LDP sessions";
            leaf timeout {
              type string;
              description
                  "[3..65535]";
            } //timeout

            leaf factor {
              type uint32 {
                range "1..255";
              }
            } //factor

          } //container hello

          container hello-reduction {
            description
                "Configure hello reduction for targeted LDP Sessions with a dampening factor";
            leaf enable {
              type uint32 {
                range "3..20";
              }
            } //enable

            leaf disable {
              type boolean;
            } //disable

          } //container hello-reduction

          container keepalive {
            description
                "Configure the keepalive timeout and factor for targeted LDP sessions";
            leaf timeout {
              type string;
              description
                  "[3..65535]";
            } //timeout

            leaf factor {
              type uint32 {
                range "1..255";
              }
            } //factor

          } //container keepalive

        } //container ipv4

        container ipv6 {
          description
              "Context to configure ipv6 LDP targeted peers and parameters applied to 
               targeted sessions";
          container hello {
            description
                "Configure the hello timeout and factor for targeted LDP sessions";
            leaf timeout {
              type string;
              description
                  "[3..65535]";
            } //timeout

            leaf factor {
              type uint32 {
                range "1..255";
              }
            } //factor

          } //container hello

          container hello-reduction {
            description
                "Configure hello reduction for targeted LDP Sessions with a dampening factor";
            leaf enable {
              type uint32 {
                range "3..20";
              }
            } //enable

            leaf disable {
              type boolean;
            } //disable

          } //container hello-reduction

          container keepalive {
            description
                "Configure the keepalive timeout and factor for targeted LDP sessions";
            leaf timeout {
              type string;
              description
                  "[3..65535]";
            } //timeout

            leaf factor {
              type uint32 {
                range "1..255";
              }
            } //factor

          } //container keepalive

        } //container ipv6

        list peer {
          key "ip-address";
          description
              "Configure a targeted peer for LDP";
          leaf ip-address {
            type inet:ip-address;
            description
                "Attribute ip-address for peer";
          } //ip-address

          leaf bfd-enable {
            type boolean;
            description
                "Enable/Disable BFD tracking of LDP Session for the peer";
          }

          container hello {
            description
                "Configure the hello timeout and factor for the peer";
            leaf timeout {
              type string;
              description
                  "[3..65535]";
            } //timeout

            leaf factor {
              type uint32 {
                range "1..255";
              }
            } //factor

          } //container hello

          container hello-reduction {
            description
                "Configure hello reduction for the peer with a dampening factor";
            leaf enable {
              type uint32 {
                range "3..20";
              }
            } //enable

            leaf disable {
              type boolean;
            } //disable

          } //container hello-reduction

          container keepalive {
            description
                "Configure the keepalive timeout and factor for the peer";
            leaf timeout {
              type string;
              description
                  "[3..65535]";
            } //timeout

            leaf factor {
              type uint32 {
                range "1..255";
              }
            } //factor

          } //container keepalive

          container local-lsr-id {
            description
                "Configure local lsr-id";
            leaf interface-name {
              type string {
                length "1..32";
              }
            } //interface-name

            leaf t32bit-format {
              type boolean;
            } //t32bit-format

          } //container local-lsr-id

          leaf shutdown {
            type boolean;
            description
                "Administratively enable/disable the peer";
          }

          container tunneling {
            presence
                "Enable/Disable tunneling of unicast LDP FECs over tunnels";
            list lsp {
              key "lsp-name";
              description
                  "Configure the lsp associated with this peer";
              leaf lsp-name {
                type string;
                description
                    "Attribute lsp-name for lsp";
              } //lsp-name

            } //list lsp

          } //container tunneling

        } //list peer

        list peer-template {
          key "template-name";
          description
              "Configure a peer-template for LDP";
          leaf template-name {
            type string {
              length "1..32";
            }
          } //template-name

          leaf adv-local-lsr-id {
            type boolean;
            description
                "Enable/disable advertise local lsr id";
          }

          leaf bfd-enable {
            type boolean;
            description
                "Enable/Disable BFD tracking of LDP Session for the peer-template";
          }

          container community {
            description
                "community string associated with a session to a given peer";
            leaf community {
              type string {
                length "1..32";
              }
            } //community

          } //container community

          container hello {
            description
                "Configure the hello timeout and factor for the peer-template";
            leaf timeout {
              type string;
              description
                  "[3..65535]";
            } //timeout

            leaf factor {
              type uint32 {
                range "1..255";
              }
            } //factor

          } //container hello

          container hello-reduction {
            description
                "Configure hello reduction for the peer-template with a dampening factor";
            leaf enable {
              type uint32 {
                range "3..20";
              }
            } //enable

            leaf disable {
              type boolean;
            } //disable

          } //container hello-reduction

          container keepalive {
            description
                "Configure the keepalive timeout and factor for the peer-template";
            leaf timeout {
              type string;
              description
                  "[3..65535]";
            } //timeout

            leaf factor {
              type uint32 {
                range "1..255";
              }
            } //factor

          } //container keepalive

          container local-lsr-id {
            description
                "Configure local lsr-id";
            leaf interface-name {
              type string {
                length "1..32";
              }
            } //interface-name

          } //container local-lsr-id

          leaf shutdown {
            type boolean;
            description
                "Administratively enable/disable the peer-template";
          }

          leaf tunneling {
            type boolean;
            description
                "Enable/Disable tunneling of LDP over prefix LDP tunnels";
          }

        } //list peer-template

      } //container targeted-session

      container tcp-session-parameters {
        description
            "Context to configure parameters applicable to TCP transport session of an LDP 
             session to remote peer";
        list peer-transport {
          key "ip-address";
          description
              "Configure parameters for an LDP peer";
          leaf ip-address {
            type string;
            description
                "Attribute ip-address for peer-transport";
          } //ip-address

          container auth-keychain {
            description
                "Configure TCP authentication keychain to use for the session";
            leaf name {
              type string {
                length "1..32";
              }
              description
                  "keychain-name (32 char max)";
            } //name

          } //container auth-keychain

          container authentication-key {
            description
                "Configure the authentication key used for the peer";
            leaf authentication-key-hash-key {
              type string {
                length "1..500";
              }
              description
                  "authentication-key - [16 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          leaf path-mtu-discovery {
            type boolean;
            description
                "Enable/Disable Path MTU Discovery";
          }

          container ttl-security {
            description
                "Configure TTL security parameters for incoming packet";
            leaf min-ttl-value {
              type int32 {
                range "1..255";
              }
              description
                  "[1..255], minimum TTL value";
            } //min-ttl-value

          } //container ttl-security

        } //list peer-transport

      } //container tcp-session-parameters

    } //container ldp

  } //grouping alu-conf-router-ldp-r13

} //module  alu-conf-router-ldp-r13
