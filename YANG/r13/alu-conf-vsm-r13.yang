module alu-conf-vsm-r13 {
  yang-version "1";

  namespace "urn:alcatel-lucent.com:sros:ns:yang:conf-vsm-r13";

  prefix "conf-vsm-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Versatile Service Modules on SR OS 
       based routers. 
       
       Copyright 2014-2015 Alcatel-Lucent, 2016 Nokia. All rights reserved. 
       Reproduction of this document is authorized on the condition that the 
       foregoing copyright notice is included. 
       
       This alu-conf-vsm-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-vsm-r13 {
    container vsm {
      status "obsolete";
      description
          "Configure Versatile Service Modules";
      list ccag {
        key "ccag-id";
        status "obsolete";
        description
            "Configure a Cross Connect Agg Grp";
        leaf ccag-id {
          type uint32 {
            range "1..8";
          }
        } //ccag-id

        leaf force {
          type boolean;
        } //force

        container cca-rate {
          status "obsolete";
          description
              "Configure CCA rate";
          leaf kilo-bits-per-second {
            type string {
            }
            description
                "[0..100000000|max]";
          } //kilo-bits-per-second

        } //container cca-rate

        container description {
          status "obsolete";
          description
              "Description for this CCAG";
          leaf description-string {
            type string {
              length "1..255";
            }
          } //description-string

        } //container description

        list member-cca {
          key "card-slot-mda-number";
          status "obsolete";
          description
              "MDAs that are part of this CCAG (up to 8 total)";
          leaf card-slot-mda-number {
            type string {
            }
            description
                "[1..10/1..2]";
          } //card-slot-mda-number

        } //list member-cca

        leaf shutdown {
          type boolean;
          status "obsolete";
          description
              "Configure the admin state";
        }

        container access {
          status "obsolete";
          description
              "Configure access params";
          container adapt-qos {
            status "obsolete";
            description
                "Configure Qos Adaptation";
            leaf adapt-qos-id {
              type enumeration {
                enum link;
                enum distribute;
                enum port-fair;
              }
            } //adapt-qos-id

          } //container adapt-qos

        } //container access

        container path {
          status "obsolete";
          description
              "Configure a path on this CCAG";
          leaf path-id {
            type enumeration {
              enum a;
              enum b;
            }
            description
                "[a|b]";
          } //path-id

          container rate {
            status "obsolete";
            description
                "Configure the path rate";
            leaf kilo-bits-per-second {
              type string {
              }
              description
                  "[0..100000000|max]";
            } //kilo-bits-per-second

            leaf aggregate-cca {
              type enumeration {
                enum aggregate;
                enum cca;
              }
              description
                  "keywords";
            } //aggregate-cca

          } //container rate

          container weight {
            status "obsolete";
            description
                "configure the path weight";
            leaf path-weight {
              type uint32 {
                range "1..100";
              }
            } //path-weight

          } //container weight

          container net-sap {
            status "obsolete";
            description
                "net to sap cross connection";
            container accounting-policy {
              status "obsolete";
              description
                  "Configure the accounting policy";
              leaf policy-id {
                type uint32 {
                  range "1..99";
                }
              } //policy-id

            } //container accounting-policy

            leaf collect-stats {
              type boolean;
              status "obsolete";
              description
                  "collect stats";
            }

            container mac {
              status "obsolete";
              description
                  "Assign a specific MAC address";
              leaf ieee-address {
                type alu:ieee-address;
                description
                    "xx:xx:xx:xx:xx:xx or xx-xx-xx-xx-xx-xx";
              } //ieee-address

            } //container mac

            container mtu {
              status "obsolete";
              description
                  "Configure the maximum payload MTU size";
              leaf mtu-bytes {
                type uint32 {
                  range "512..9212";
                }
                description
                    "[512..9212] bytes";
              } //mtu-bytes

            } //container mtu

            container queue-policy {
              status "obsolete";
              description
                  "Configure the queue policy";
              leaf queue-policy-name {
                type string {
                  length "1..32";
                }
              } //queue-policy-name

            } //container queue-policy

            container egress {
              status "obsolete";
              description
                  "egress";
              container pool {
                status "obsolete";
                description
                    "Configure the egress pool";
                container resv-cbs {
                  status "obsolete";
                  description
                      "configure resv-cbs";
                  leaf percent-or-default {
                    type string;
                    description
                        "[0..100|default]";
                  } //percent-or-default

                } //container resv-cbs

                container slope-policy {
                  status "obsolete";
                  description
                      "configure slope policy";
                  leaf slope-policy-name {
                    type string {
                      length "1..32";
                    }
                  } //slope-policy-name

                } //container slope-policy

              } //container pool

            } //container egress

          } //container net-sap

          container sap-net {
            status "obsolete";
            description
                "sap to net cross connection";
            container mac {
              status "obsolete";
              description
                  "Assign a specific MAC address";
              leaf ieee-address {
                type alu:ieee-address;
                description
                    "xx:xx:xx:xx:xx:xx or xx-xx-xx-xx-xx-xx";
              } //ieee-address

            } //container mac

            container mtu {
              status "obsolete";
              description
                  "Configure the maximum payload MTU size";
              leaf mtu-bytes {
                type uint32 {
                  range "512..9212";
                }
                description
                    "[512..9212] bytes";
              } //mtu-bytes

            } //container mtu

            container egress {
              status "obsolete";
              description
                  "egress";
              container pool {
                status "obsolete";
                description
                    "Configure the egress pool";
                container resv-cbs {
                  status "obsolete";
                  description
                      "configure resv-cbs";
                  leaf percent-or-default {
                    type string;
                    description
                        "[0..100|default]";
                  } //percent-or-default

                } //container resv-cbs

                container slope-policy {
                  status "obsolete";
                  description
                      "configure slope policy";
                  leaf slope-policy-name {
                    type string {
                      length "1..32";
                    }
                  } //slope-policy-name

                } //container slope-policy

              } //container pool

            } //container egress

            container ingress {
              status "obsolete";
              description
                  "ingress";
              container pool {
                status "obsolete";
                description
                    "Configure the ingress pool";
                container resv-cbs {
                  status "obsolete";
                  description
                      "configure resv-cbs";
                  leaf percent-or-default {
                    type string;
                    description
                        "[0..100|default]";
                  } //percent-or-default

                } //container resv-cbs

                container slope-policy {
                  status "obsolete";
                  description
                      "configure slope policy";
                  leaf slope-policy-name {
                    type string {
                      length "1..32";
                    }
                  } //slope-policy-name

                } //container slope-policy

              } //container pool

            } //container ingress

          } //container sap-net

          container sap-sap {
            status "obsolete";
            description
                "sap to sap cross connection";
            container mac {
              status "obsolete";
              description
                  "Assign a specific MAC address";
              leaf ieee-address {
                type alu:ieee-address;
                description
                    "xx:xx:xx:xx:xx:xx or xx-xx-xx-xx-xx-xx";
              } //ieee-address

            } //container mac

            container mtu {
              status "obsolete";
              description
                  "Configure the maximum payload MTU size";
              leaf mtu-bytes {
                type uint32 {
                  range "512..9212";
                }
                description
                    "[512..9212] bytes";
              } //mtu-bytes

            } //container mtu

            container egress {
              status "obsolete";
              description
                  "egress";
              container pool {
                status "obsolete";
                description
                    "Configure the egress pool";
                container resv-cbs {
                  status "obsolete";
                  description
                      "configure resv-cbs";
                  leaf percent-or-default {
                    type string;
                    description
                        "[0..100|default]";
                  } //percent-or-default

                } //container resv-cbs

                container slope-policy {
                  status "obsolete";
                  description
                      "configure slope policy";
                  leaf slope-policy-name {
                    type string {
                      length "1..32";
                    }
                  } //slope-policy-name

                } //container slope-policy

              } //container pool

            } //container egress

            container ingress {
              status "obsolete";
              description
                  "ingress";
              container pool {
                status "obsolete";
                description
                    "Configure the ingress pool";
                container resv-cbs {
                  status "obsolete";
                  description
                      "configure resv-cbs";
                  leaf percent-or-default {
                    type string;
                    description
                        "[0..100|default]";
                  } //percent-or-default

                } //container resv-cbs

                container slope-policy {
                  status "obsolete";
                  description
                      "configure slope policy";
                  leaf slope-policy-name {
                    type string {
                      length "1..32";
                    }
                  } //slope-policy-name

                } //container slope-policy

              } //container pool

            } //container ingress

          } //container sap-sap

        } //container path

      } //list ccag

    } //container vsm

  } //grouping alu-conf-vsm-r13

} //module  alu-conf-vsm-r13
