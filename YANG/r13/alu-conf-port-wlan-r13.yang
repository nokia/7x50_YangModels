module alu-conf-port-wlan-r13 {
  yang-version "1";

  namespace "urn:alcatel-lucent.com:sros:ns:yang:conf-port-wlan-r13";

  prefix "conf-port-wlan-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure WLAN parameters for a port on SR 
       OS based routers. 
       
       Copyright 2014-2015 Alcatel-Lucent, 2016 Nokia. All rights reserved. 
       Reproduction of this document is authorized on the condition that the 
       foregoing copyright notice is included. 
       
       This alu-conf-port-wlan-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-05-11";

  grouping alu-conf-port-wlan-r13 {
    container wlan {
      description
          "Configure WLAN parameters for a port";
      container access-point {
        description
            "Configure WLAN access-point parameters";
        leaf broadcast-ssid {
          type boolean;
          description
              "Broadcast SSID in beacon";
        }

        container client-limit {
          description
              "Limit connected clients to this access-point";
          leaf clients {
            type uint32 {
              range "1..24";
            }
            description
                "[1..24]";
          } //clients

        } //container client-limit

        container client-timeout {
          description
              "Timeout of idle clients";
          leaf seconds {
            type uint32 {
              range "60..86400";
            }
            description
                "[60..86400]";
          } //seconds

        } //container client-timeout

        container dhcp {
          description
              "Configure access point DHCP parameters";
          leaf shutdown {
            type boolean;
            description
                "Adminstratively enable/disable DHCP snooping";
          }

        } //container dhcp

        container dot1x {
          description
              "Configure 802.1x Authentication Parameters";
          container radius-plcy {
            description
                "Configure an authentication server policy";
            leaf name {
              type string {
                length "1..32";
              }
              description
                  "[32 chars max]";
            } //name

          } //container radius-plcy

          container re-auth-period {
            description
                "Configure re-authentication period for clients";
            leaf seconds {
              type uint32 {
                range "1..9000";
              }
              description
                  "[1..9000]";
            } //seconds

          } //container re-auth-period

        } //container dot1x

      } //container access-point

      list network {
        key "network-id";
        description
            "Configure WLAN network parameters";
        leaf network-id {
          type uint32 {
          }
        } //network-id

        leaf ssid {
          type string {
            length "1..32";
          }
        } //ssid

        container wlan-security {
          description
              "Configure network security for SSID";
          leaf type {
            type enumeration {
              enum wpa2-psk;
              enum wpa2-enterprise;
            }
            description
                "keyword";
          } //type

          container wpa-encryption {
            description
                "Configure WPA/WPA2 encryption";
            leaf tkip-aes {
              type enumeration {
                enum tkip;
                enum aes;
              }
            } //tkip-aes

          } //container wpa-encryption

          container wpa-passphrase {
            description
                "Configure WPA/WPA2 pre-shared passphrase";
            leaf passphrase {
              type string {
                length "1..500";
              }
              description
                  "[63 chars max]";
            } //passphrase

            leaf hash-hash2-custom {
              type enumeration {
                enum hash;
                enum hash2;
                enum custom;
              }
            } //hash-hash2-custom

          } //container wpa-passphrase

        } //container wlan-security

      } //list network

    } //container wlan

  } //grouping alu-conf-port-wlan-r13

} //module  alu-conf-port-wlan-r13
