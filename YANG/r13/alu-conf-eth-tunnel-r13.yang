module alu-conf-eth-tunnel-r13 {
  yang-version "1";

  namespace "urn:alcatel-lucent.com:sros:ns:yang:conf-eth-tunnel-r13";

  prefix "conf-eth-tunnel-r13";

  import alu-types {
    prefix "alu";
  }
  import ietf-yang-types {
    prefix "yang";
  }

  alu:alu-major-release "rel19";

  organization "Alcatel-Lucent";

  contact
      "Alcatel-Lucent SR OS Support 
       Web: <http://www.alcatel-lucent.com>";

  description
      "Alcatel-Lucent YANG Data model to configure Ethernet Tunnel Groups on SR OS 
       based routers. 
       
       Copyright 2014-2015 Alcatel-Lucent, 2016 Nokia. All rights reserved. 
       Reproduction of this document is authorized on the condition that the 
       foregoing copyright notice is included. 
       
       This alu-conf-eth-tunnel-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2018-12-28";

  grouping alu-conf-eth-tunnel-r13 {
    list eth-tunnel {
      key "tunnel-index";
      description
          "Configure Ethernet Tunnel Groups";
      leaf tunnel-index {
        type string;
        description
            "Attribute tunnel-index for eth-tunnel";
      } //tunnel-index

      container ccm-hold-time {
        description
            "Configure eth-tunnel CCM dampening timers";
        leaf down {
          type uint32 {
            range "0..1000";
          }
          default 0;
          description
              "[0..1000] in 100ths of seconds - Default: 0";
        } //down

        leaf up {
          type uint32 {
            range "0..5000";
          }
          default 20;
          description
              "[0..5000] in 10ths of seconds - Default: 20";
        } //up

      } //container ccm-hold-time

      container description {
        description
            "Add/remove a text description for the eth-tunnel";
        leaf long-description-string {
          type string {
            length "1..160";
          }
        } //long-description-string

      } //container description

      container protection-type {
        description
            "Configure the protection type for the eth-tunnel";
        leaf protection-type-id {
          type enumeration {
            enum g8031-1to1;
            enum loadsharing;
          }
        } //protection-type-id

      } //container protection-type

      container revert-time {
        description
            "Configure how long to wait before switching back to the working circuit after 
             it has been restored to eth-tunnel";
        leaf time {
          type uint32 {
            range "1..720";
          }
          description
              "[1..720] seconds";
        } //time

      } //container revert-time

      leaf shutdown {
        type boolean;
        description
            "Administratively enable/disable the eth-tunnel";
      }

      container ethernet {
        description
            "Configure the ethernet parameters";
        container encap-type {
          description
              "Configure encapsulation method";
          leaf encap-type-id {
            type enumeration {
              enum dot1q;
              enum qinq;
            }
          } //encap-type-id

        } //container encap-type

        container mac {
          description
              "Assign a specific MAC address to the eth-tunnel";
          leaf ieee-address {
            type alu:ieee-address;
            description
                "xx:xx:xx:xx:xx:xx or xx-xx-xx-xx-xx-xx";
          } //ieee-address

        } //container mac

      } //container ethernet

      container lag-emulation {
        description
            "Configure eth-tunnel loadsharing parameters";
        container path-threshold {
          description
              "Configure the behavior for the eth-tunnel if the number of operational members 
               is equal to or below a threshold level";
          leaf num-paths {
            type string;
            description
                "Attribute num-paths for path-threshold";
          } //num-paths

        } //container path-threshold

        container access {
          description
              "Configure eth-tunnel loadsharing access parameters";
          container adapt-qos {
            description
                "Configure eth-tunnel QoS adaptation";
            leaf adapt-qos-id {
              type enumeration {
                enum distribute;
                enum link;
                enum port-fair;
              }
            } //adapt-qos-id

          } //container adapt-qos

          leaf per-fp-ing-queuing {
            type boolean;
            description
                "Configure Per FP Ingress Queuing";
          }

        } //container access

      } //container lag-emulation

      list path {
        key "path-index";
        description
            "Configure an eth-tunnel path";
        leaf path-index {
          type string;
          description
              "Attribute path-index for path";
        } //path-index

        container control-tag {
          description
              "Configure the path control tag";
          leaf qtag.qtag {
            type string;
            description
                "[0..4094|*]";
          } //qtag.qtag

        } //container control-tag

        container description {
          description
              "Add/remove a text description for the path";
          leaf description-string {
            type string {
              length "1..80";
            }
            description
                "[80 chars max]";
          } //description-string

        } //container description

        container member {
          description
              "Configure the path member";
          leaf port-id {
            type string {
            }
            description
                "Attribute port-id for member";
          } //port-id

        } //container member

        container precedence {
          description
              "Configure the path precedence";
          leaf primary-secondary {
            type enumeration {
              enum primary;
              enum secondary;
            }
            default "secondary";
            description
                "keywords - primary|secondary - Default: secondary";
          } //primary-secondary

        } //container precedence

        leaf shutdown {
          type boolean;
          description
              "Administratively enable/disable the eth-tunnel path";
        }

        container eth-cfm {
          description
              "Configure CFM parameters";
          list mep {
            key "mep-id domain association";
            description
                "Configure a CFM Maintenance Endpoint";
            leaf mep-id {
              type int16 {
                range "1..8191";
              }
            } //mep-id

            leaf domain {
              type uint32 {
                range "1..4294967295";
              }
            } //domain

            leaf association {
              type uint32 {
                range "1..4294967295";
              }
            } //association

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            leaf control-mep {
              type boolean;
              description
                  "Enable/disable propagation of CC state to eth-tunnel";
            }

            container description {
              description
                  "Add/remove a text description for the MEP";
              leaf description-string {
                type string {
                }
                description
                    "[80 chars max]";
              } //description-string

            } //container description

            container low-priority-defect {
              description
                  "Configure the Lowest Priority Defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the MAC Address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

      } //list path

    } //list eth-tunnel

  } //grouping alu-conf-eth-tunnel-r13

} //module  alu-conf-eth-tunnel-r13
