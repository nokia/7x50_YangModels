module alu-conf-svc-vprn-wlan-r13 {
  yang-version "1";

  namespace "urn:alcatel-lucent.com:sros:ns:yang:conf-svc-vprn-wlan-r13";

  prefix "conf-svc-vprn-wlan-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure WLAN Gateway functionality for 
       VPRN services on SR OS based routers. 
       
       Copyright 2014-2015 Alcatel-Lucent, 2016 Nokia. All rights reserved. 
       Reproduction of this document is authorized on the condition that the 
       foregoing copyright notice is included. 
       
       This alu-conf-svc-vprn-wlan-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vprn-wlan-r13 {
    container wlan-gw {
      presence
          "Configure WLAN Gateway functionality for VPRN services";
      container apn {
        status "obsolete";
        description
            "Configure the Network Identifier part of the APN";
        leaf apn {
          type string {
            length "1..80";
          }
        } //apn

      } //container apn

      container pdn-type {
        status "obsolete";
        description
            "Configure the default 3GPP-PDN type";
        leaf pdn-type-id {
          type enumeration {
            enum ipv4;
            enum ipv6;
            enum ipv4v6;
          }
        } //pdn-type-id

      } //container pdn-type

      container distributed-sub-mgmt {
        description
            "Configure distributed subscriber management";
        container ipv6-tcp-mss-adjust {
          description
              "Configure the value to adjust the TCP Maximum Segment Size (MSS) option";
          leaf segment-size {
            type uint32 {
              range "160..10240";
            }
          } //segment-size

        } //container ipv6-tcp-mss-adjust

      } //container distributed-sub-mgmt

      container mgw-map {
        status "obsolete";
        description
            "Configure a Mobile Gateway map";
        list address {
          key "ip-prefix-ip-prefix-length";
          status "obsolete";
          description
              "Configure a Mobile Gateway map address";
          leaf ip-prefix-ip-prefix-length {
            type string;
            description
                "Attribute ip-prefix/ip-prefix-length for address";
          } //ip-prefix-ip-prefix-length

          leaf mgw-profile {
            type string {
              length "1..32";
            }
          } //mgw-profile

        } //list address

      } //container mgw-map

      container mobility-triggered-acct {
        description
            "Configure interim accounting updates triggered by mobility";
        container interim-update {
          description
              "Enable/disable sending mobility-triggered accounting interim updates";
          leaf include-counters {
            type boolean;
          } //include-counters

          leaf hold-down {
            type uint32 {
              range "60..86400";
            }
          } //hold-down

        } //container interim-update

      } //container mobility-triggered-acct

      container xconnect {
        description
            "Configure the cross-connect";
        leaf shutdown {
          type boolean;
          description
              "Enable/disable the WLAN-GW cross-connect";
        }

        container tunnel-source-ip {
          description
              "Configure the IPv6 address/prefix for the tunnel source";
          leaf ipv6-address-prefix-length {
            type string;
            description
                "ipv6-address x:x:x:x:x:x:x:x (eight 16-bit pieces) 
                 x:x:x:x:x:x:d.d.d.d 
                 x [0..FFFF]H 
                 d [0..255]D 
                 (no link-local address) 
                 prefix-length [64] 
                 ";
          } //ipv6-address-prefix-length

        } //container tunnel-source-ip

        container wlan-gw-group {
          description
              "Configure the ISA WLAN-GW group";
          leaf nat-group-id {
            type uint32 {
              range "1..4";
            }
          } //nat-group-id

        } //container wlan-gw-group

      } //container xconnect

    } //container wlan-gw

  } //grouping alu-conf-svc-vprn-wlan-r13

} //module  alu-conf-svc-vprn-wlan-r13
