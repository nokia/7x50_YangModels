module alu-conf-svc-vprn-ospf-r13 {
  yang-version "1";

  namespace "urn:alcatel-lucent.com:sros:ns:yang:conf-svc-vprn-ospf-r13";

  prefix "conf-svc-vprn-ospf-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure OSPF for VPRN services on SR OS 
       based routers. 
       
       Copyright 2014-2015 Alcatel-Lucent, 2016 Nokia. All rights reserved. 
       Reproduction of this document is authorized on the condition that the 
       foregoing copyright notice is included. 
       
       This alu-conf-svc-vprn-ospf-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-08-18";

  grouping alu-conf-svc-vprn-ospf-r13 {
    container ospf {
      description
          "Configure OSPF for VPRN services";
      leaf router-id-create {
        type inet:ip-address;
        description
            "<ip-address>";
      } //router-id-create

      container advertise-router-capability {
        description
            "Enable/disable router advertisement capabilities";
        leaf advertise-router-capability-id {
          type enumeration {
            enum link;
            enum area;
            enum as;
          }
        } //advertise-router-capability-id

      } //container advertise-router-capability

      leaf compatible-rfc1583 {
        type boolean;
        description
            "Enable/disable OSPF summary and external route calculations in compliance with 
             RFC1583 and earlier";
      }

      container export {
        description
            "Configure export route policies to determine which routes are exported from 
             the route table";
        leaf-list policy-name {
          type string {
            length "1..32";
          }
          max-elements 5;
        } //policy-name

      } //container export

      container export-limit {
        description
            "Maximum number of routes (prefixes) that can be exported into OSPF from the 
             route table.";
        leaf number {
          type uint32 {
            range "1..4294967295";
          }
        } //number

        leaf log {
          type uint16 {
            range "1..100";
          }
        } //log

      } //container export-limit

      container external-db-overflow {
        description
            "Limit on number of AS-external-LSAs in LSDB and wait time before processing 
             these if limit is exceeded";
        leaf limit {
          type int64 {
            range "-1..2147483647";
          }
          description
              "[0..2147483647]";
        } //limit

        leaf interval {
          type int32 {
            range "0..2147483647";
          }
          description
              "[0..2147483647] seconds";
        } //interval

      } //container external-db-overflow

      container external-preference {
        description
            "Preference for OSPF external routes";
        leaf preference {
          type uint16 {
            range "1..255";
          }
          default 150;
        } //preference

      } //container external-preference

      leaf ignore-dn-bit {
        type boolean;
        description
            "Enable/disable whether this instance of OSPF will ignore the DN bit for OSPF 
             LSA packets";
      }

      container import {
        description
            "Configure import route policies to determine which routes are imported into 
             the route table";
        leaf-list policy-name {
          type string {
            length "1..32";
          }
          max-elements 5;
        } //policy-name

      } //container import

      leaf loopfree-alternate {
        type boolean;
        status "obsolete";
        description
            "Enable/disable loopfree-alternate for OSPF";
      }

      container loopfree-alternate-exclude {
        status "obsolete";
        description
            "Configure LFA exclude policies";
        leaf-list prefix-policy {
          type string {
            length "1..32";
          }
          max-elements 5;
        } //prefix-policy

      } //container loopfree-alternate-exclude

      leaf multicast-import {
        type boolean;
        description
            "Enable/disable submission of routes into the multicast Route Table Manager by 
             OSPF";
      }

      container overload {
        description
            "Configure the local router so that it appears to be overloaded";
        leaf timeout {
          type uint32 {
            range "60..1800";
          }
        } //timeout

      } //container overload

      leaf overload-include-ext-1 {
        type boolean;
        description
            "Enable/disable OSPF maximum metric usage for external type-1 routes in case of 
             overload";
      }

      leaf overload-include-ext-2 {
        type boolean;
        description
            "Enable/disable OSPF maximum metric usage for external type-2 routes in case of 
             overload";
      }

      leaf overload-include-stub {
        type boolean;
        description
            "Enable/disable OSPF maximum metric usage for stub advertisement in case of 
             overload";
      }

      container overload-on-boot {
        description
            "Configure the local router so that it appears to be overloaded at boot up";
        leaf timeout {
          type uint32 {
            range "60..1800";
          }
        } //timeout

      } //container overload-on-boot

      container preference {
        description
            "Preference for OSPF internal routes";
        leaf preference {
          type uint16 {
            range "1..255";
          }
          default 10;
        } //preference

      } //container preference

      container reference-bandwidth {
        description
            "Reference bandwidth that provides a reference for the default costing of 
             interfaces";
        leaf bandwidth-in-kbps {
          type uint32 {
            range "1..4000000000";
          }
        } //bandwidth-in-kbps

        leaf bandwidth-in-kbps-1 {
          type string;
          description
              "Attribute bandwidth-in-kbps for reference-bandwidth";
        } //bandwidth-in-kbps-1

        leaf zbps {
          type uint32 {
            range "1..18";
          }
        } //zbps

        leaf ebps {
          type uint32 {
            range "1..999";
          }
        } //ebps

        leaf pbps {
          type uint32 {
            range "1..999";
          }
        } //pbps

        leaf tbps {
          type string;
          description
              "Attribute Tera-bps for reference-bandwidth";
        } //tbps

        leaf gbps {
          type uint32 {
            range "1..999";
          }
        } //gbps

        leaf mbps {
          type uint32 {
            range "1..999";
          }
        } //mbps

        leaf kbps {
          type uint32 {
            range "1..999";
          }
        } //kbps

      } //container reference-bandwidth

      list rib-priority {
        key "high";
        description
            "Configure RIB priority for OSPF";
        leaf high {
          type boolean;
        } //high

        leaf prefix-list-name {
          type string {
            length "1..32";
          }
        } //prefix-list-name

      } //list rib-priority

      container router-id {
        description
            "Configure router-id for OSPF";
        leaf ip-address {
          type inet:ip-address;
        } //ip-address

      } //container router-id

      container rtr-adv-lsa-limit {
        description
            "Configure max LSA's we accept from 1 advertising router";
        leaf rtr-adv-lsa-limit-id {
          type uint32 {
            range "1..4294967295";
          }
        } //rtr-adv-lsa-limit-id

        leaf log-only {
          type boolean;
        } //log-only

        leaf threshold {
          type uint32 {
            range "0..100";
          }
        } //threshold

        leaf overload-timeout {
          type boolean;
        } //overload-timeout

        leaf seconds {
          type uint32 {
            range "1..1800";
          }
        } //seconds

        leaf forever {
          type boolean;
        } //forever

      } //container rtr-adv-lsa-limit

      leaf shutdown {
        type boolean;
        description
            "Administratively enable/disable the OSPF instance";
      }

      leaf super-backbone {
        type boolean;
        description
            "Enable/disable super-backbone functionality";
      }

      leaf suppress-dn-bit {
        type boolean;
        description
            "Enable/disable whether this instance of OSPF will suppress setting the DN bit 
             for OSPF LSA packets";
      }

      leaf unicast-import-disable {
        type boolean;
        description
            "Enable/disable submission of routes into the unicast Route Table Manager by 
             OSPF";
      }

      container vpn-domain {
        description
            "Configure OSPF VPN domain";
        leaf id {
          type string;
          description
              "6 octets vpn-domain identifier (xxxx.xxxx.xxxx)";
        } //id

        leaf t0005-0105-0205-8005 {
          type enumeration {
            enum 0005;
            enum 0105;
            enum 0205;
            enum 8005;
          }
          description
              "keywords - specify vpn-domain type";
        } //t0005-0105-0205-8005

      } //container vpn-domain

      container vpn-tag {
        description
            "Configure OSPF VPN tag";
        leaf vpn-tag {
          type uint32;
        } //vpn-tag

      } //container vpn-tag

      list area {
        key "area-id";
        description
            "Configure an OSPF area";
        leaf area-id {
          type string;
          description
              "<ip-address> | [0..4294967295]";
        } //area-id

        container advertise-ne-profile {
          description
              "Configure network element profile to be advertised";
          leaf name {
            type string;
          } //name

        } //container advertise-ne-profile

        leaf advertise-router-capability {
          type boolean;
          description
              "Enable/disable router advertisement capabilities";
        }

        list area-range {
          key "ip-prefix-mask";
          description
              "Create/delete address ranges on an ABR for route summarization or suppression";
          leaf ip-prefix-mask {
            type inet:ip-prefix;
            description
                "ip-prefix a.b.c.d (host bits must be 0) 
                 mask [0..32]";
          } //ip-prefix-mask

          leaf advertise-not-advertise {
            type enumeration {
              enum advertise;
              enum not-advertise;
            }
            description
                "keywords";
          } //advertise-not-advertise

        } //list area-range

        leaf blackhole-aggregate {
          type boolean;
          description
              "Add/Remove low priority blackhole route to avoid loops";
        }

        container export {
          description
              "Configure export policies to determine whether a route is exported as summary 
               type 3/inter-area-prefix-LSA from this Area to another Area";
          leaf-list policy-name {
            type string {
              length "1..32";
            }
            max-elements 5;
          } //policy-name

        } //container export

        container import {
          description
              "Configure import policies to determine whether a route is imported as summary 
               type 3/inter-area-prefix-LSA from another Area into this Area";
          leaf-list policy-name {
            type string {
              length "1..32";
            }
            max-elements 5;
          } //policy-name

        } //container import

        leaf loopfree-alternate-exclude {
          type boolean;
          description
              "Enable/disable IP fast re-route capability for OSPF at area level";
        }

        list interface {
          key "ip-int-name";
          description
              "Configure OSPF on an IP interface";
          leaf ip-int-name {
            type string {
              length "1..32";
            }
          } //ip-int-name

          leaf secondary {
            type boolean;
          } //secondary

          leaf advertise-router-capability {
            type boolean;
            description
                "Enable/disable router advertisement capabilities";
          }

          leaf advertise-subnet {
            type boolean;
            description
                "Enable/disable advertising point-to-point interfaces as subnet routes";
          }

          container auth-keychain {
            description
                "Configure TCP authentication keychain to use for the session";
            leaf name {
              type string {
                length "1..32";
              }
              description
                  "keychain-name (32 char max)";
            } //name

          } //container auth-keychain

          container authentication-key {
            description
                "Password used by the interface to send and receive OSPF protocol packets";
            leaf authentication-key-hash-key {
              type string {
                length "1..500";
              }
              description
                  "authentication-key - [8 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          container authentication-type {
            description
                "Enable/disable authentication and specify authentication type to be used on 
                 the interface";
            leaf password-message-digest {
              type enumeration {
                enum password;
                enum message-digest;
              }
              description
                  "keywords - specify authentication method";
            } //password-message-digest

          } //container authentication-type

          container bfd-enable {
            description
                "Enable BFD";
            leaf remain-down-on-failure {
              type boolean;
              description
                  "keyword - Forces adjacency down on BFD failure";
            } //remain-down-on-failure

          } //container bfd-enable

          container dead-interval {
            description
                "Time OSPF waits without receiving hello packets before declaring a neighbor 
                 down";
            leaf seconds {
              type uint32 {
                range "2..65535";
              }
            } //seconds

          } //container dead-interval

          container hello-interval {
            description
                "Time interval between OSPF hellos issued on the interface";
            leaf seconds {
              type uint32 {
                range "1..65535";
              }
            } //seconds

          } //container hello-interval

          container interface-type {
            description
                "Configure the interface type to be either broadcast or point-to-point";
            leaf interface-type-id {
              type enumeration {
                enum broadcast;
                enum point-to-point;
                enum non-broadcast;
              }
            } //interface-type-id

          } //container interface-type

          container lfa-policy-map {
            description
                "Configure a route-next-hop template";
            leaf route-nh-template {
              type string {
                length "1..32";
              }
            } //route-nh-template

          } //container lfa-policy-map

          container load-balancing-weight {
            description
                "Configure load-balancing-weight";
            leaf load-balancing-weight-id {
              type uint32 {
                range "1..4294967295";
              }
            } //load-balancing-weight-id

          } //container load-balancing-weight

          leaf loopfree-alternate-exclude {
            type boolean;
            description
                "Enable/disable IP fast re-route capability for OSPF at interface level (only 
                 valid for primary interface)";
          }

          container lsa-filter-out {
            description
                "Configure LSA flooding reduction";
            leaf all-except-own-rtrlsa-except-own-rtrlsa-and-defaults {
              type enumeration {
                enum all;
                enum except-own-rtrlsa;
                enum except-own-rtrlsa-and-defaults;
              }
            } //all-except-own-rtrlsa-except-own-rtrlsa-and-defaults

          } //container lsa-filter-out

          list message-digest-key {
            key "key-id";
            description
                "Configure a message digest key when MD5 authentication is enabled on the 
                 interface";
            leaf key-id {
              type uint16 {
                range "1..255";
              }
            } //key-id

            leaf md5 {
              type string {
                length "1..500";
              }
              description
                  "key - [16 chars max] 
                   hash-key (for hash scheme) 
                   hash2-key (for hash2 scheme) 
                   custom-key (for custom hash scheme)";
            } //md5

            leaf hash-hash2-custom {
              type enumeration {
                enum hash;
                enum hash2;
                enum custom;
              }
              description
                  "keywords - specify hashing scheme";
            } //hash-hash2-custom

          } //list message-digest-key

          container metric {
            description
                "Configure an explicit route cost metric for the interface";
            leaf metric {
              type uint32 {
                range "1..65535";
              }
            } //metric

          } //container metric

          container mtu {
            description
                "Enter the mtu to be used by OSPF for this logical interface";
            leaf mtu-bytes {
              type string;
              description
                  "Attribute mtu-bytes for mtu";
            } //mtu-bytes

          } //container mtu

          list neighbor {
            key "ipv4-address";
            description
                "Configure neighbor addresses for the interface";
            leaf ipv4-address {
              type inet:ip-address;
            } //ipv4-address

          } //list neighbor

          leaf passive {
            type boolean;
            description
                "Add/remove the passive property to/from the interface";
          }

          container poll-interval {
            description
                "Configure the poll-interval for this interface";
            leaf poll-interval-id {
              type uint32;
            } //poll-interval-id

          } //container poll-interval

          container priority {
            description
                "Priority of the interface that is used in the designated router election on 
                 the subnet";
            leaf number {
              type uint16 {
                range "0..255";
              }
            } //number

          } //container priority

          container retransmit-interval {
            description
                "Time OSPF will wait before retransmitting an unacknowledged LSA to a neighbor";
            leaf seconds {
              type uint32 {
                range "1..1800";
              }
            } //seconds

          } //container retransmit-interval

          container rib-priority {
            description
                "Configure RIB priority for OSPF";
            leaf high {
              type boolean;
            } //high

          } //container rib-priority

          leaf shutdown {
            type boolean;
            description
                "Administratively enable/disable OSPF on the interface";
          }

          container transit-delay {
            description
                "Time that it takes to transmit an LSA on the interface";
            leaf seconds {
              type uint32 {
                range "1..1800";
              }
            } //seconds

          } //container transit-delay

        } //list interface

        container nssa {
          presence
              "Configure an OSPF Not So Stubby Area (NSSA)";
          list area-range {
            key "ip-prefix-mask";
            description
                "Create/delete address ranges for route summarization or suppression";
            leaf ip-prefix-mask {
              type inet:ip-prefix;
              description
                  "ip-prefix a.b.c.d (host bits must be 0) 
                   mask [0..32]";
            } //ip-prefix-mask

            leaf advertise-not-advertise {
              type enumeration {
                enum advertise;
                enum not-advertise;
              }
              description
                  "keywords";
            } //advertise-not-advertise

          } //list area-range

          container originate-default-route {
            description
                "Enable/disable generation of default route and its LSA type (3 or 7) into the 
                 NSSA";
            leaf type-7 {
              type boolean;
            } //type-7

            leaf adjacency-check {
              type boolean;
            } //adjacency-check

          } //container originate-default-route

          leaf redistribute-external {
            type boolean;
            description
                "Enable/disable redistribution of external routes into the NSSA";
          }

          leaf summaries {
            type boolean;
            description
                "Enable/disable sending summary (type 3) LSAs into the NSSA";
          }

        } //container nssa

        list sham-link {
          key "ip-int-name ip-address";
          description
              "Configure OSPF on the sham-link";
          leaf ip-int-name {
            type string {
              length "1..32";
            }
          } //ip-int-name

          leaf ip-address {
            type inet:ip-address;
            description
                "[a.b.c.d] remote neighbor ip-address";
          } //ip-address

          container auth-keychain {
            description
                "Configure TCP authentication keychain to use for the session";
            leaf name {
              type string {
                length "1..32";
              }
              description
                  "keychain-name (32 char max)";
            } //name

          } //container auth-keychain

          container authentication-key {
            description
                "Password used by the interface to send and receive OSPF protocol packets";
            leaf authentication-key-hash-key {
              type string {
                length "1..500";
              }
              description
                  "authentication-key - [8 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          container authentication-type {
            description
                "Enable/disable authentication and specify authentication type to be used on 
                 the sham-link";
            leaf password-message-digest {
              type enumeration {
                enum password;
                enum message-digest;
              }
              description
                  "keywords - specify authentication method";
            } //password-message-digest

          } //container authentication-type

          container dead-interval {
            description
                "Time OSPF waits without receiving hello packets before declaring a sham-link 
                 neighbor down";
            leaf seconds {
              type uint32 {
                range "2..65535";
              }
            } //seconds

          } //container dead-interval

          container hello-interval {
            description
                "Time interval between OSPF hellos issued on the sham-link";
            leaf seconds {
              type uint32 {
                range "1..65535";
              }
            } //seconds

          } //container hello-interval

          list message-digest-key {
            key "key-id";
            description
                "Configure a message digest key when MD5 authentication is enabled on the 
                 sham-link";
            leaf key-id {
              type uint16 {
                range "1..255";
              }
            } //key-id

            leaf md5 {
              type string {
                length "1..500";
              }
              description
                  "key - [16 chars max] 
                   hash-key (for hash scheme) 
                   hash2-key (for hash2 scheme) 
                   custom-key (for custom hash scheme)";
            } //md5

            leaf hash-hash2-custom {
              type enumeration {
                enum hash;
                enum hash2;
                enum custom;
              }
              description
                  "keywords - specify hashing scheme";
            } //hash-hash2-custom

          } //list message-digest-key

          container metric {
            description
                "Configure an explicit route cost metric for the sham-link";
            leaf metric {
              type uint32 {
                range "1..65535";
              }
            } //metric

          } //container metric

          container retransmit-interval {
            description
                "Time OSPF will wait before retransmitting an unacknowledged LSA to a sham-link 
                 neighbor";
            leaf seconds {
              type uint32 {
                range "1..1800";
              }
            } //seconds

          } //container retransmit-interval

          leaf shutdown {
            type boolean;
            description
                "Administratively enable/disable OSPF on the sham-link";
          }

          container transit-delay {
            description
                "Time that it takes to transmit an LSA on the sham-link";
            leaf seconds {
              type uint32 {
                range "1..1800";
              }
            } //seconds

          } //container transit-delay

        } //list sham-link

        container stub {
          presence
              "Configure an OSPF stub area";
          container default-metric {
            description
                "Metric used by the ABR for the default route into the stub area";
            leaf metric {
              type uint32 {
                range "1..16777215";
              }
              description
                  "1..16777214";
            } //metric

          } //container default-metric

          leaf summaries {
            type boolean;
            description
                "Enable/disable sending summary (type 3) LSAs into the stub area";
          }

        } //container stub

        list virtual-link {
          key "router-id transit-area";
          description
              "Configure an OSPF virtual-link";
          leaf router-id {
            type inet:ip-address;
          } //router-id

          leaf transit-area {
            type string;
            description
                "<ip-address> | [0..4294967295]";
          } //transit-area

          container auth-keychain {
            description
                "Configure TCP authentication keychain to use for the session";
            leaf name {
              type string {
                length "1..32";
              }
              description
                  "keychain-name (32 char max)";
            } //name

          } //container auth-keychain

          container authentication-key {
            description
                "Password used by the interface to send and receive OSPF protocol packets";
            leaf authentication-key-hash-key {
              type string {
                length "1..500";
              }
              description
                  "authentication-key - [8 chars max] 
                   hash-key 
                   hash2-key 
                   custom-key";
            } //authentication-key-hash-key

            leaf hash-hash2-custom {
              type enumeration {
                enum hash;
                enum hash2;
                enum custom;
              }
              description
                  "keywords - specify hashing scheme";
            } //hash-hash2-custom

          } //container authentication-key

          container authentication-type {
            description
                "Enable/disable authentication and specify authentication type to be used on 
                 the virtual-link";
            leaf password-message-digest {
              type enumeration {
                enum password;
                enum message-digest;
              }
              description
                  "keywords - specify authentication method";
            } //password-message-digest

          } //container authentication-type

          container dead-interval {
            description
                "Time OSPF waits without receiving hello packets before declaring a 
                 virtual-neighbor down";
            leaf seconds {
              type uint32 {
                range "2..65535";
              }
              default 60;
            } //seconds

          } //container dead-interval

          container hello-interval {
            description
                "Time interval between OSPF hellos issued on the virtual-link";
            leaf seconds {
              type uint32 {
                range "1..65535";
              }
            } //seconds

          } //container hello-interval

          list message-digest-key {
            key "key-id";
            description
                "Configure a message digest key when MD5 authentication is enabled on the 
                 virtual-link";
            leaf key-id {
              type uint16 {
                range "1..255";
              }
            } //key-id

            leaf md5 {
              type string {
                length "1..500";
              }
              description
                  "key - [16 chars max] 
                   hash-key (for hash scheme) 
                   hash2-key (for hash2 scheme) 
                   custom-key (for custom hash scheme)";
            } //md5

            leaf hash-hash2-custom {
              type enumeration {
                enum hash;
                enum hash2;
                enum custom;
              }
              description
                  "keywords - specify hashing scheme";
            } //hash-hash2-custom

          } //list message-digest-key

          container retransmit-interval {
            description
                "Time OSPF will wait before retransmitting an unacknowledged LSA to a 
                 virtual-neighbor";
            leaf seconds {
              type uint32 {
                range "1..1800";
              }
            } //seconds

          } //container retransmit-interval

          leaf shutdown {
            type boolean;
            description
                "Administratively enable/disable OSPF on the virtual-link";
          }

          container transit-delay {
            description
                "Time that it takes to transmit an LSA on the virtual-link";
            leaf seconds {
              type uint32 {
                range "1..1800";
              }
              default 1;
            } //seconds

          } //container transit-delay

        } //list virtual-link

      } //list area

      container graceful-restart {
        presence
            "Enable/disable graceful-restart for OSPF";
        leaf helper-disable {
          type boolean;
          description
              "Enable/disable graceful restart helper mode for OSPF";
        }

        leaf strict-lsa-checking {
          type boolean;
          description
              "Enable/disable strict LSA checking during OSPF graceful restart";
        }

      } //container graceful-restart

      container loopfree-alternates {
        presence
            "Enable/disable loopfree-alternate for OSPF";
        container exclude {
          description
              "Configure LFA exclude policies";
          container prefix-policy {
            description
                "Configure LFA exclude prefix policies";
            leaf-list prefix-policy {
              type string {
                length "1..32";
              }
              max-elements 5;
            } //prefix-policy

          } //container prefix-policy

        } //container exclude

      } //container loopfree-alternates

      container timers {
        description
            "Configure OSPF timers";
        container incremental-spf-wait {
          description
              "Configure the delay before an incremental SPF calculation is started";
          leaf incremental-spf-wait {
            type uint32 {
              range "0..1000";
            }
            description
                "[0..1000] in milliseconds";
          } //incremental-spf-wait

        } //container incremental-spf-wait

        container lsa-accumulate {
          description
              "Configure the delay to accumulate multiple LSAs before advertising them to 
               neighbors";
          leaf lsa-accumulate {
            type uint32 {
              range "0..1000";
            }
            description
                "[0..1000] in milliseconds";
          } //lsa-accumulate

        } //container lsa-accumulate

        container lsa-arrival {
          description
              "Configure the minimum delay that must pass between receipt of the same LSAs 
               arriving from neighbors";
          leaf lsa-arrival-time {
            type uint32 {
              range "0..600000";
            }
            description
                "[0..600000] in milliseconds";
          } //lsa-arrival-time

        } //container lsa-arrival

        container lsa-generate {
          description
              "Configure the throttling of OSPF LSA-generation";
          leaf max-lsa-wait {
            type uint32 {
              range "10..600000";
            }
            description
                "[10..600000] in milliseconds";
          } //max-lsa-wait

          leaf lsa-initial-wait {
            type uint32 {
              range "10..600000";
            }
            status "obsolete";
            description
                "[10..600000] in milliseconds";
          } //lsa-initial-wait

          leaf lsa-second-wait {
            type uint32 {
              range "10..600000";
            }
            status "obsolete";
            description
                "[10..600000] in milliseconds";
          } //lsa-second-wait

          leaf lsa-initial-wait-1 {
            type uint32 {
              range "10..600000";
            }
            description
                "[10..600000] in milliseconds";
          } //lsa-initial-wait-1

          leaf lsa-second-wait-2 {
            type uint32 {
              range "10..600000";
            }
            description
                "[10..600000] in milliseconds";
          } //lsa-second-wait-2

        } //container lsa-generate

        container redistribute-delay {
          description
              "Configure the hold down timer for external routes being redistributed in OSPF";
          leaf redistribute-delay {
            type uint32 {
              range "0..1000";
            }
            description
                "[0..1000] in milliseconds";
          } //redistribute-delay

        } //container redistribute-delay

        container spf-wait {
          description
              "Configure the maximum interval between two consecutive SPF calculations";
          leaf max-spf-wait {
            type uint32 {
              range "10..120000";
            }
            description
                "[10..120000] in milliseconds";
          } //max-spf-wait

          leaf spf-wait-id {
            type uint32 {
              range "10..100000";
            }
            status "obsolete";
          } //spf-wait-id

          leaf spf-wait-id-2 {
            type uint32 {
              range "10..100000";
            }
            status "obsolete";
          } //spf-wait-id-2

          leaf spf-initial-wait {
            type uint32 {
              range "10..100000";
            }
            description
                "[10..100000] in milliseconds";
          } //spf-initial-wait

          leaf spf-second-wait {
            type uint32 {
              range "10..100000";
            }
            description
                "[10..100000] in milliseconds";
          } //spf-second-wait

        } //container spf-wait

      } //container timers

    } //container ospf

  } //grouping alu-conf-svc-vprn-ospf-r13

} //module  alu-conf-svc-vprn-ospf-r13
