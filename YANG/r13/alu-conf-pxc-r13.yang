module alu-conf-pxc-r13 {
  yang-version "1";

  namespace "urn:alcatel-lucent.com:sros:ns:yang:conf-pxc-r13";

  prefix "conf-pxc-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Port Cross-Connects on SR OS based 
       routers. 
       
       Copyright 2014-2015 Alcatel-Lucent, 2016 Nokia. All rights reserved. 
       Reproduction of this document is authorized on the condition that the 
       foregoing copyright notice is included. 
       
       This alu-conf-pxc-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-pxc-r13 {
    container port-xc {
      description
          "Configure Port Cross-Connects";
      list pxc {
        key "pxc-id";
        description
            "Configure the port cross-connect (PXC) parameters";
        leaf pxc-id {
          type uint32 {
            range "1..64";
          }
        } //pxc-id

        container description {
          description
              "Configure the description of the PXC";
          leaf description-string {
            type string {
              length "1..80";
            }
          } //description-string

        } //container description

        container port {
          description
              "Configure the port of the PXC";
          leaf port-id {
            type string;
            description
                "slot/mda/port";
          } //port-id

        } //container port

        leaf shutdown {
          type boolean;
          description
              "Administratively enable/disable the PXC";
        }

      } //list pxc

    } //container port-xc

  } //grouping alu-conf-pxc-r13

} //module  alu-conf-pxc-r13
