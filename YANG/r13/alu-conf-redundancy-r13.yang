module alu-conf-redundancy-r13 {
  yang-version "1";

  namespace "urn:alcatel-lucent.com:sros:ns:yang:conf-redundancy-r13";

  prefix "conf-redundancy-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure redundancy on SR OS based routers. 
       
       Copyright 2014-2015 Alcatel-Lucent, 2016 Nokia. All rights reserved. 
       Reproduction of this document is authorized on the condition that the 
       foregoing copyright notice is included. 
       
       This alu-conf-redundancy-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-03-05";

  grouping alu-conf-redundancy-r13 {
    container redundancy {
      description
          "Configure redundancy";
      leaf cert-sync {
        type boolean;
        description
            "Configure redundancy certificate synchronization";
      }

      container mgmt-ethernet {
        description
            "Configure management ethernet redundancy";
        leaf revert {
          type uint32 {
            range "1..300";
          }
          default 5;
          description
              "[1..300] - Default: 5";
        } //revert

      } //container mgmt-ethernet

      leaf rollback-sync {
        type boolean;
        description
            "Configure redundancy rollback synchronization parameters";
      }

      container synchronize {
        description
            "Configure redundancy synchronization parameters";
        leaf boot-env-config {
          type enumeration {
            enum boot-env;
            enum config;
          }
          description
              "keywords";
        } //boot-env-config

      } //container synchronize

      container bgp-evpn-multi-homing {
        description
            "Configure BGP EVPN multi-homing paramaters";
        container boot-timer {
          description
              "Configure BGP multi-homing boot-timer";
          leaf seconds {
            type int32 {
              range "0..600";
            }
            description
                "[0..600]:default 10";
          } //seconds

        } //container boot-timer

        container es-activation-timer {
          description
              "Configure BGP multi-homing ES activation timer";
          leaf seconds {
            type int32 {
              range "0..100";
            }
            description
                "[0..100]:default 3";
          } //seconds

        } //container es-activation-timer

      } //container bgp-evpn-multi-homing

      container bgp-multi-homing {
        description
            "Configure BGP multi-homing paramaters";
        container boot-timer {
          description
              "Configure BGP multi-homing boot-timer";
          leaf seconds {
            type int32 {
              range "0..600";
            }
          } //seconds

        } //container boot-timer

        container site-activation-timer {
          description
              "Configure BGP multi-homing site activation timer";
          leaf seconds {
            type int32 {
              range "0..100";
            }
          } //seconds

        } //container site-activation-timer

        container site-min-down-timer {
          description
              "Configure minimum down timer for the site";
          leaf seconds {
            type int32 {
              range "1..100";
            }
          } //seconds

        } //container site-min-down-timer

      } //container bgp-multi-homing

      container multi-chassis {
        description
            "Configure multi-chassis parameters";
        list peer {
          key "ip-address";
          description
              "Configure a multi-chassis redundancy peer";
          leaf ip-address {
            type string;
            description
                "Attribute ip-address for peer";
          } //ip-address

          container authentication-key {
            description
                "Configure the authentication key";
            leaf authentication-key-hash-key {
              type string {
                length "1..500";
              }
              description
                  "Attribute authentication-key|hash-key for authentication-key";
            } //authentication-key-hash-key

            leaf hash-hash2-custom {
              type enumeration {
                enum hash;
                enum hash2;
                enum custom;
              }
              description
                  "keywords - specify hashing scheme";
            } //hash-hash2-custom

          } //container authentication-key

          container description {
            description
                "Configure the description";
            leaf description-string {
              type string {
                length "1..80";
              }
            } //description-string

          } //container description

          container peer-name {
            description
                "Configure a name";
            leaf name {
              type string {
                length "1..32";
              }
              description
                  "32 char max";
            } //name

          } //container peer-name

          leaf shutdown {
            type boolean;
            description
                "Administratively enable/disable the multi-chassis peer";
          }

          container source-address {
            description
                "Configure the source address";
            leaf ip-address {
              type string;
              description
                  "Attribute ip-address for source-address";
            } //ip-address

          } //container source-address

          leaf warm-standby {
            type boolean;
            description
                "Configure this peer as warm standby";
          }

          container mc-endpoint {
            presence
                "Configure Multi-Chassis Endpoint";
            leaf bfd-enable {
              type boolean;
              description
                  "Configure BFD";
            }

            container boot-timer {
              description
                  "Configure boot timer interval";
              leaf interval {
                type uint32 {
                  range "1..600";
                }
              } //interval

            } //container boot-timer

            container hold-on-neighbor-failure {
              description
                  "Configure hold time applied on neighbor failure";
              leaf multiplier {
                type uint32 {
                  range "2..25";
                }
              } //multiplier

            } //container hold-on-neighbor-failure

            container keep-alive-interval {
              description
                  "Configure keep alive interval for this MC-Endpoint";
              leaf interval {
                type uint32 {
                  range "5..500";
                }
                description
                    "[5..500] tenths of a second";
              } //interval

            } //container keep-alive-interval

            leaf passive-mode {
              type boolean;
              description
                  "Configure passive-mode";
            }

            leaf shutdown {
              type boolean;
              description
                  "Administratively enable/disable the multi-chassis peer end-point";
            }

            container system-priority {
              description
                  "Configure system priority";
              leaf value {
                type uint32 {
                  range "1..255";
                }
              } //value

            } //container system-priority

          } //container mc-endpoint

          container mc-ipsec {
            presence
                "Configure multi-chassis ipsec information";
            leaf bfd-enable {
              type boolean;
              description
                  "Configure a BFD interface";
            }

            container discovery-interval {
              description
                  "Configure discovery-interval information";
              leaf interval-secs {
                type uint32 {
                  range "1..1800";
                }
              } //interval-secs

              leaf boot {
                type uint32 {
                  range "1..1800";
                }
              } //boot

            } //container discovery-interval

            container hold-on-neighbor-failure {
              description
                  "Configure hold time applied on neighbor failure";
              leaf multiplier {
                type uint32 {
                  range "2..25";
                }
              } //multiplier

            } //container hold-on-neighbor-failure

            container keep-alive-interval {
              description
                  "Configure keep alive interval";
              leaf interval {
                type uint32 {
                  range "5..500";
                }
                description
                    "[5..500] tenths of a second";
              } //interval

            } //container keep-alive-interval

            list tunnel-group {
              key "tunnel-group-id";
              description
                  "Configure tunnel group information";
              leaf tunnel-group-id {
                type uint32 {
                  range "1..16";
                }
              } //tunnel-group-id

              container peer-group {
                description
                    "Configure peer tunnel-group";
                leaf tunnel-group-id {
                  type uint32 {
                    range "1..16";
                  }
                } //tunnel-group-id

              } //container peer-group

              container priority {
                description
                    "Configure tunnel-group priority";
                leaf priority {
                  type uint32 {
                    range "0..255";
                  }
                } //priority

              } //container priority

              leaf shutdown {
                type boolean;
                description
                    "Enable/Disable tunnel-group";
              }

            } //list tunnel-group

          } //container mc-ipsec

          container mc-lag {
            presence
                "Configure a Multi-Chassis LAG";
            container hold-on-neighbor-failure {
              description
                  "Configure hold time applied on neighbor failure";
              leaf multiplier {
                type uint32 {
                  range "2..25";
                }
              } //multiplier

            } //container hold-on-neighbor-failure

            container keep-alive-interval {
              description
                  "Configure keep alive interval for this MC-LAG";
              leaf interval {
                type uint32 {
                  range "5..500";
                }
                description
                    "[5..500] tenths of a second";
              } //interval

            } //container keep-alive-interval

            list lag {
              key "lag-id";
              description
                  "Configure a LAG pair forming a MC-LAG with this peer";
              leaf lag-id {
                type string;
                description
                    "Attribute lag-id for lag";
              } //lag-id

              leaf lacp-key {
                type uint32 {
                  range "1..65535";
                }
              } //lacp-key

              leaf system-id {
                type string;
                description
                    "xx:xx:xx:xx:xx:xx - xx [00..FF]";
              } //system-id

              leaf remote-lag {
                type uint32 {
                  range "1..800";
                }
              } //remote-lag

              leaf system-priority {
                type uint32 {
                  range "1..65535";
                }
              } //system-priority

              leaf source-bmac-lsb {
                type boolean;
              } //source-bmac-lsb

              leaf use-lacp-key {
                type boolean;
              } //use-lacp-key

              leaf MAC-Lsb {
                type string;
                description
                    "[1..65535] or xx-xx or xx:xx";
              } //MAC-Lsb

            } //list lag

            leaf shutdown {
              type boolean;
              description
                  "Administratively enable/disable the MC-LAG";
            }

          } //container mc-lag

          container mc-ring {
            description
                "Configure the Multi-Chassis rings";
            list l3-ring {
              key "name";
              description
                  "Configure a layer-3 Multi-Chassis ring";
              leaf name {
                type string {
                  length "1..32";
                }
              } //name

              leaf shutdown {
                type boolean;
                description
                    "Enable/disable the mcr layer-3 ring";
              }

              list srrp-instance {
                key "srrp-id";
                description
                    "Configure SRRP instance for layer-3 ring";
                leaf srrp-id {
                  type uint32 {
                    range "1..4294967295";
                  }
                } //srrp-id

              } //list srrp-instance

              container in-band-control-path {
                description
                    "Configure a mcr inband control path";
                leaf debounce {
                  type boolean;
                  description
                      "Enable/disable the inband control path debouncing";
                }

                container dst-ip {
                  description
                      "Configure the inband control path dst-ip";
                  leaf ip-address {
                    type inet:ip-address;
                    description
                        "ip-address a.b.c.d (no multicast address)";
                  } //ip-address

                } //container dst-ip

                container interface {
                  description
                      "Configure the inband control path itf";
                  leaf ip-int-name {
                    type string {
                      length "1..32";
                    }
                    description
                        "[32 chars max] (must start with a letter)";
                  } //ip-int-name

                } //container interface

                container max-debounce-time {
                  description
                      "Configure the inband control path maximum debounce time";
                  leaf max-debounce-time {
                    type uint32 {
                      range "5..200";
                    }
                    description
                        "[5..200] seconds";
                  } //max-debounce-time

                } //container max-debounce-time

                container service-id {
                  description
                      "Configure the inband control path service";
                  leaf service-id {
                    type string;
                    description
                        "Attribute service-id for service-id";
                  } //service-id

                } //container service-id

                container service-name {
                  description
                      "Configure the name of the VPRN service containing the interface";
                  leaf svc-name {
                    type string {
                      length "1..64";
                    }
                  } //svc-name

                } //container service-name

              } //container in-band-control-path

              list ring-node {
                key "ring-node-name";
                description
                    "Configure a mcr access node";
                leaf ring-node-name {
                  type string {
                    length "1..32";
                  }
                } //ring-node-name

                container connectivity-verify {
                  description
                      "Configure the node connectivity check";
                  container dst-ip {
                    description
                        "Configure the node cc dst-ip";
                    leaf ip-address {
                      type inet:ip-address;
                      description
                          "ip-address a.b.c.d (no multicast address)";
                    } //ip-address

                  } //container dst-ip

                  container interval {
                    description
                        "Configure the node cc interval";
                    leaf interval {
                      type uint64 {
                        range "1..6000";
                      }
                      description
                          "[1..6000] minutes";
                    } //interval

                  } //container interval

                  container service-id {
                    description
                        "Configure the node cc service id";
                    leaf service-id {
                      type string;
                      description
                          "Attribute service-id for service-id";
                    } //service-id

                  } //container service-id

                  container service-name {
                    description
                        "Configure the name of the node cc service";
                    leaf svc-id {
                      type string {
                        length "1..64";
                      }
                    } //svc-id

                  } //container service-name

                  leaf shutdown {
                    type boolean;
                    description
                        "Enable/disable the connectivity check";
                  }

                  container src-ip {
                    description
                        "Configure the node cc src-ip";
                    leaf ip-address {
                      type inet:ip-address;
                      description
                          "ip-address a.b.c.d (no multicast address)";
                    } //ip-address

                  } //container src-ip

                  container src-mac {
                    description
                        "Configure the node cc src-mac";
                    leaf ieee-address {
                      type string;
                      description
                          "xx:xx:xx:xx:xx:xx or xx-xx-xx-xx-xx-xx";
                    } //ieee-address

                  } //container src-mac

                  container vlan {
                    description
                        "Configure the node cc vlan id";
                    leaf vlan-encap {
                      type string {
                        length "1..9";
                      }
                      description
                          "Attribute vlan-encap for vlan";
                    } //vlan-encap

                  } //container vlan

                } //container connectivity-verify

              } //list ring-node

            } //list l3-ring

            list ring {
              key "sync-tag";
              description
                  "Configure a Multi-Chassis ring";
              leaf sync-tag {
                type string {
                  length "1..32";
                }
              } //sync-tag

              leaf shutdown {
                type boolean;
                description
                    "Enable/disable the mcr ring";
              }

              container in-band-control-path {
                description
                    "Configure a mcr inband control path";
                leaf debounce {
                  type boolean;
                  description
                      "Enable/disable the inband control path debouncing";
                }

                container dst-ip {
                  description
                      "Configure the inband control path dst-ip";
                  leaf ip-address {
                    type inet:ip-address;
                    description
                        "ip-address a.b.c.d (no multicast address)";
                  } //ip-address

                } //container dst-ip

                container interface {
                  description
                      "Configure the inband control path itf";
                  leaf ip-int-name {
                    type string {
                      length "1..32";
                    }
                    description
                        "[32 chars max] (must start with a letter)";
                  } //ip-int-name

                } //container interface

                container max-debounce-time {
                  description
                      "Configure the inband control path maximum debounce time";
                  leaf max-debounce-time {
                    type uint32 {
                      range "5..200";
                    }
                    description
                        "[5..200] seconds";
                  } //max-debounce-time

                } //container max-debounce-time

                container service-id {
                  description
                      "Configure the inband control path service";
                  leaf service-id {
                    type string;
                    description
                        "Attribute service-id for service-id";
                  } //service-id

                } //container service-id

                container service-name {
                  description
                      "Configure the name of the VPRN service containing the interface";
                  leaf svc-name {
                    type string {
                      length "1..64";
                    }
                  } //svc-name

                } //container service-name

              } //container in-band-control-path

              container path-b {
                presence
                    "Configure a mcr b-path";
                list range {
                  key "vlan-range";
                  description
                      "Configure a mcr b-path vlan range";
                  leaf vlan-range {
                    type string {
                      length "1..64";
                    }
                    description
                        "[0..4094] - [0..4094] 
                         [0..4094] - * 
                         * - *";
                  } //vlan-range

                } //list range

              } //container path-b

              container path-excl {
                presence
                    "Configure a mcr excl-path";
                list range {
                  key "vlan-range";
                  description
                      "Configure a mcr excl-path vlan range";
                  leaf vlan-range {
                    type string {
                      length "1..64";
                    }
                    description
                        "[0..4094] - [0..4094] 
                         [0..4094] - * 
                         * - *";
                  } //vlan-range

                } //list range

              } //container path-excl

              list ring-node {
                key "ring-node-name";
                description
                    "Configure a mcr access node";
                leaf ring-node-name {
                  type string {
                    length "1..32";
                  }
                } //ring-node-name

                container connectivity-verify {
                  description
                      "Configure the node connectivity check";
                  container dst-ip {
                    description
                        "Configure the node cc dst-ip";
                    leaf ip-address {
                      type inet:ip-address;
                      description
                          "ip-address a.b.c.d (no multicast address)";
                    } //ip-address

                  } //container dst-ip

                  container interval {
                    description
                        "Configure the node cc interval";
                    leaf interval {
                      type uint64 {
                        range "1..6000";
                      }
                      description
                          "[1..6000] minutes";
                    } //interval

                  } //container interval

                  container service-id {
                    description
                        "Configure the node cc service id";
                    leaf service-id {
                      type string;
                      description
                          "Attribute service-id for service-id";
                    } //service-id

                  } //container service-id

                  container service-name {
                    description
                        "Configure the name of the node cc service";
                    leaf svc-name {
                      type string {
                        length "1..64";
                      }
                    } //svc-name

                  } //container service-name

                  leaf shutdown {
                    type boolean;
                    description
                        "Enable/disable the connectivity check";
                  }

                  container src-ip {
                    description
                        "Configure the node cc src-ip";
                    leaf ip-address {
                      type inet:ip-address;
                      description
                          "ip-address a.b.c.d (no multicast address)";
                    } //ip-address

                  } //container src-ip

                  container src-mac {
                    description
                        "Configure the node cc src-mac";
                    leaf ieee-address {
                      type string;
                      description
                          "xx:xx:xx:xx:xx:xx or xx-xx-xx-xx-xx-xx";
                    } //ieee-address

                  } //container src-mac

                  container vlan {
                    description
                        "Configure the node cc vlan id";
                    leaf vlan-encap {
                      type string {
                        length "1..9";
                      }
                      description
                          "Attribute vlan-encap for vlan";
                    } //vlan-encap

                  } //container vlan

                } //container connectivity-verify

              } //list ring-node

            } //list ring

          } //container mc-ring

          container sync {
            presence
                "Configure synchronization";
            leaf diameter-proxy {
              type boolean;
              description
                  "Synchronize Diameter Proxy";
            }

            leaf igmp {
              type boolean;
              description
                  "Synchronize IGMP information";
            }

            leaf igmp-snooping {
              type boolean;
              description
                  "Synchronize IGMP Snooping information";
            }

            leaf ipsec {
              type boolean;
              description
                  "Synchronize IPsec information";
            }

            leaf l2tp {
              type boolean;
              description
                  "Synchronize L2TP";
            }

            leaf local-dhcp-server {
              type boolean;
              description
                  "Synchronize DHCP Server information";
            }

            leaf mc-ring {
              type boolean;
              description
                  "Synchronize ring information";
            }

            leaf mld {
              type boolean;
              description
                  "Synchronize MLD information";
            }

            leaf mld-snooping {
              type boolean;
              description
                  "Synchronize MLD Snooping information";
            }

            container pim-snooping {
              description
                  "Synchronize PIM snooping";
              leaf saps {
                type boolean;
              } //saps

              leaf spoke-sdps {
                type boolean;
              } //spoke-sdps

            } //container pim-snooping

            leaf python {
              type boolean;
              description
                  "Synchronize Python";
            }

            leaf shutdown {
              type boolean;
              description
                  "Administratively enable/disable synchronization";
            }

            leaf srrp {
              type boolean;
              description
                  "Synchronize SRRP information";
            }

            leaf sub-host-trk {
              type boolean;
              description
                  "Synchronize subscriber host tracking information";
            }

            container sub-mgmt {
              description
                  "Synchronize Subscriber Management information";
              leaf ipoe {
                type boolean;
              } //ipoe

              leaf pppoe {
                type boolean;
              } //pppoe

            } //container sub-mgmt

            list tunnel-group {
              key "tunnel-group-id";
              description
                  "Configure multi-active tunnel group for sync";
              leaf tunnel-group-id {
                type uint32 {
                  range "1..16";
                }
              } //tunnel-group-id

              leaf sync-tag {
                type string {
                  length "1..32";
                }
              } //sync-tag

            } //list tunnel-group

            container diameter-node {
              presence
                  "Synchronize Diameter nodes";
              list node {
                key "host-name";
                description
                    "Configure a Diameter node to synchronize";
                leaf host-name {
                  type string {
                    length "1..80";
                  }
                } //host-name

                leaf sync-tag {
                  type string {
                    length "1..32";
                  }
                } //sync-tag

              } //list node

            } //container diameter-node

            list port {
              key "port-id";
              description
                  "Configure a port to synchronize";
              leaf port-id {
                type string {
                  length "1..17";
                }
                description
                    "Attribute port-id for port";
              } //port-id

              leaf sync-tag {
                type string {
                  length "1..32";
                }
              } //sync-tag

              list range {
                key "encap-range";
                description
                    "Configure a range of encapsulation values";
                leaf encap-range {
                  type string {
                    length "1..20";
                  }
                  description
                      "Dot1Q - <start-qtag>-<end-qtag> 
                       start-qtag [0..4094] 
                       end-qtag [0..4094] 
                       QinQ - <qtag1>.<start-qtag2>-<qtag1>.<end-qtag2> 
                       - <start-qtag1>.*-<end-qtag1>.* 
                       qtag1 [1..4094] 
                       start-qtag1 [1..4094] 
                       end-qtag1 [1..4094] 
                       start-qtag2 [0..4094] 
                       end-qtag2 [0..4094] 
                       ";
                } //encap-range

                leaf sync-tag {
                  type string {
                    length "1..32";
                  }
                } //sync-tag

              } //list range

            } //list port

            list sdp {
              key "sdp-id";
              description
                  "Configure an SDP to synchronize";
              leaf sdp-id {
                type uint32 {
                  range "1..32767";
                }
              } //sdp-id

              leaf sync-tag {
                type string {
                  length "1..32";
                }
              } //sync-tag

              list range {
                key "vc-id-range";
                description
                    "Configure a range of vc-id values";
                leaf vc-id-range {
                  type string {
                    length "1..21";
                  }
                  description
                      "<start-vc-id>-<end-vc-id> 
                       start-vc-id [1..4294967295] 
                       end-vc-id [1..4294967295] 
                       ";
                } //vc-id-range

                leaf sync-tag {
                  type string {
                    length "1..32";
                  }
                } //sync-tag

              } //list range

            } //list sdp

            container track-srrp-instances {
              description
                  "Configure tracked SRRP instances";
              list track-srrp {
                key "track-srrp-id";
                description
                    "Configure a tracked SRRP instance";
                leaf track-srrp-id {
                  type uint32 {
                    range "1..4294967295";
                  }
                } //track-srrp-id

                container l2tp-tunnel-id-range {
                  description
                      "Configure the range of L2TP tunnel identifiers";
                  leaf start {
                    type uint32 {
                      range "1..16383";
                    }
                  } //start

                  leaf end {
                    type uint32 {
                      range "1..16383";
                    }
                    description
                        "l2tp-tunnel-id";
                  } //end

                } //container l2tp-tunnel-id-range

              } //list track-srrp

            } //container track-srrp-instances

          } //container sync

        } //list peer

      } //container multi-chassis

    } //container redundancy

  } //grouping alu-conf-redundancy-r13

} //module  alu-conf-redundancy-r13
