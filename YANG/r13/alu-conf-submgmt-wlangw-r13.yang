module alu-conf-submgmt-wlangw-r13 {
  yang-version "1";

  namespace "urn:alcatel-lucent.com:sros:ns:yang:conf-submgmt-wlangw-r13";

  prefix "conf-submgmt-wlangw-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure WLAN Gateway functions on SR OS 
       based routers. 
       
       Copyright 2014-2015 Alcatel-Lucent, 2016 Nokia. All rights reserved. 
       Reproduction of this document is authorized on the condition that the 
       foregoing copyright notice is included. 
       
       This alu-conf-submgmt-wlangw-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-09-30";

  grouping alu-conf-submgmt-wlangw-r13 {
    container wlan-gw {
      description
          "Configure WLAN Gateway functions";
      container max-held-sessions {
        status "obsolete";
        description
            "Configure the maximum number of GTP sessions to be held while their UE are 
             disconnected";
        leaf max-held-sessions {
          type uint32 {
            range "0..500000";
          }
          description
              "Attribute max-held-sessions for max-held-sessions";
        } //max-held-sessions

      } //container max-held-sessions

      container serving-network {
        status "obsolete";
        description
            "Configure the Operator Identifier part of the APN";
        leaf mcc {
          type string {
            length "1..3";
          }
          description
              "3 digits";
        } //mcc

        leaf mnc {
          type string {
            length "1..3";
          }
          description
              "2 or 3 digits";
        } //mnc

      } //container serving-network

      container virtual-chassis-identifier {
        description
            "Configure WLAN Gateway virtual chassis identifier or dual homing key";
        leaf dual-homing-key {
          type string {
            length "1..16";
          }
        } //dual-homing-key

      } //container virtual-chassis-identifier

      container distributed-sub-mgmt {
        description
            "Configure WLAN Gateway distributed subscriber management";
        list dsm-ip-filter {
          key "name";
          status "obsolete";
          description
              "Configure a distributed-sub-mgmt IP filter";
          leaf name {
            type string;
          } //name

          container default-action {
            description
                "Configure the action to take when no specific filter entry match is found";
            leaf default-action-id {
              type enumeration {
                enum drop;
                enum forward;
              }
            } //default-action-id

          } //container default-action

          container description {
            description
                "Configure a description for the distributed-sub-mgmt IP filter";
            leaf description-string {
              type string {
                length "1..80";
              }
            } //description-string

          } //container description

          list entry {
            key "entry-id";
            description
                "Configure a distributed-sub-mgmt filter entry";
            leaf entry-id {
              type uint32 {
                range "1..1024";
              }
            } //entry-id

            container action {
              description
                  "Configure the action to take when a packet matches this filter entry match";
              leaf action-id {
                type enumeration {
                  enum drop;
                  enum forward;
                  enum http-redirect;
                  enum gtp-local-breakout;
                  enum none;
                }
              } //action-id

            } //container action

            container description {
              description
                  "Configure a description for the lightweight filter entry";
              leaf description-string {
                type string {
                  length "1..80";
                }
              } //description-string

            } //container description

            container match {
              description
                  "Configure match criteria for this lightweight filter entry";
              leaf protocol {
                type enumeration {
                  enum any;
                  enum icmp;
                  enum tcp;
                  enum udp;
                  enum gre;
                }
              } //protocol

              container dst-ip {
                description
                    "Configure the destination IP prefix to match";
                leaf ip-prefix-length {
                  type inet:ip-prefix;
                  description
                      "ip-prefix a.b.c.d (host bits must be 0) 
                       length [0..32]";
                } //ip-prefix-length

              } //container dst-ip

              container dst-port {
                description
                    "Configure the destination IP port to match";
                leaf operator {
                  type enumeration {
                    enum eq;
                  }
                } //operator

                leaf port-number {
                  type uint16;
                } //port-number

              } //container dst-port

            } //container match

          } //list entry

          container ipv6 {
            container default-action {
              description
                  "Configure the action to take when no specific filter entry match is found";
              leaf default-action-id {
                type enumeration {
                  enum drop;
                  enum forward;
                }
              } //default-action-id

            } //container default-action

            list entry {
              key "entry-id";
              description
                  "Configure a distributed-sub-mgmt IPv6 filter entry";
              leaf entry-id {
                type uint32 {
                  range "1..1024";
                }
              } //entry-id

              container action {
                description
                    "Configure the action to take when a packet matches this filter entry match";
                leaf action-id {
                  type enumeration {
                    enum drop;
                    enum forward;
                    enum http-redirect;
                    enum gtp-local-breakout;
                    enum none;
                  }
                } //action-id

              } //container action

              container description {
                description
                    "Configure a description for the dsm-ipv6-filter entry";
                leaf description-string {
                  type string {
                    length "1..80";
                  }
                } //description-string

              } //container description

              container match {
                description
                    "Configure match criteria for this dsm filter entry";
                leaf protocol {
                  type enumeration {
                    enum any;
                    enum icmp;
                    enum tcp;
                    enum udp;
                    enum gre;
                  }
                } //protocol

                container dst-ip {
                  description
                      "Configure the IPv6 destination IP-address for the DSM IPv6 filter";
                  leaf ipv6-address-prefix-length {
                    type string {
                      length "1..64";
                    }
                    description
                        "IPv6-address x:x:x:x:x:x:x:x (eight 16-bit pieces) 
                         length [0..128]";
                  } //ipv6-address-prefix-length

                } //container dst-ip

                container dst-port {
                  description
                      "Configure the destination IP port to match";
                  leaf operator {
                    type enumeration {
                      enum eq;
                    }
                  } //operator

                  leaf port-number {
                    type uint16;
                  } //port-number

                } //container dst-port

              } //container match

            } //list entry

          } //container ipv6

        } //list dsm-ip-filter

        list dsm-policer {
          key "policer-name";
          status "obsolete";
          description
              "Configure a distributed-sub-mgmt policer";
          leaf policer-name {
            type string;
          } //policer-name

          leaf type {
            type enumeration {
              enum single-bucket-bandwidth;
              enum dual-bucket-bandwidth;
            }
          } //type

          container action {
            description
                "Configure what to do with in-profile and out-of-profile packets";
            leaf action-id {
              type enumeration {
                enum permit-deny;
                enum priority-mark;
              }
            } //action-id

          } //container action

          container adaptation-rule {
            description
                "Configure the rules to compute the operational rates";
            leaf pir {
              type enumeration {
                enum max;
                enum min;
                enum closest;
              }
            } //pir

            leaf cir {
              type enumeration {
                enum max;
                enum min;
                enum closest;
              }
              description
                  "adaptation-rule";
            } //cir

          } //container adaptation-rule

          container cbs {
            description
                "Configure the Committed Burst Size (kilobytes)";
            leaf burst-size {
              type uint32 {
                range "0..131071";
              }
            } //burst-size

          } //container cbs

          container description {
            description
                "Configure a description";
            leaf description-string {
              type string {
                length "1..80";
              }
            } //description-string

          } //container description

          container mbs {
            description
                "Configure the Maximum Burst Size (kilobytes)";
            leaf burst-size {
              type uint32 {
                range "0..131071";
              }
            } //burst-size

          } //container mbs

          container rate {
            description
                "Configure the peak and committed rates for the policer";
            leaf rate {
              type string;
              description
                  "[1..100000000|max] Kbps";
            } //rate

            leaf cir {
              type string;
              description
                  "rate";
            } //cir

          } //container rate

        } //list dsm-policer

      } //container distributed-sub-mgmt

      list mgw-profile {
        key "profile-name";
        status "obsolete";
        description
            "Configure a Mobile Gateway profile";
        leaf profile-name {
          type string {
            length "1..32";
          }
        } //profile-name

        container description {
          status "obsolete";
          description
              "Configure a description";
          leaf description-string {
            type string {
              length "1..80";
            }
          } //description-string

        } //container description

        container interface-type {
          status "obsolete";
          description
              "Configure the 3GPP interface type";
          leaf interface-type-id {
            type enumeration {
              enum gn;
              enum s2a;
              enum s2b;
              enum s11;
            }
          } //interface-type-id

        } //container interface-type

        container ip-ttl {
          status "obsolete";
          description
              "Configure the IP Time-To-Live";
          leaf hops {
            type uint16 {
              range "1..255";
            }
          } //hops

        } //container ip-ttl

        container keep-alive {
          status "obsolete";
          description
              "Configure the Echo-Request messages";
          leaf interval {
            type uint32 {
              range "0..180";
            }
            description
                "0|[60..180]";
          } //interval

          leaf retry-count {
            type uint32 {
              range "1..15";
            }
          } //retry-count

          leaf timeout {
            type uint32 {
              range "1..20";
            }
          } //timeout

        } //container keep-alive

        container message-retransmit {
          status "obsolete";
          description
              "Configure the retransmission of signalling request messages";
          leaf timeout {
            type uint32 {
              range "1..30";
            }
          } //timeout

          leaf retry-count {
            type uint32 {
              range "1..8";
            }
          } //retry-count

        } //container message-retransmit

        container protocol-configuration-options {
          status "obsolete";
          description
              "Configure the Information Element to use for the Protocol Configuration 
               Options";
          leaf protocol-configuration-options-id {
            type enumeration {
              enum apco;
              enum pco;
            }
          } //protocol-configuration-options-id

        } //container protocol-configuration-options

        container python-policy {
          status "obsolete";
          description
              "Configure the Python policy used to process GTP messages";
          leaf name {
            type string;
          } //name

        } //container python-policy

        container rat-type {
          status "obsolete";
          description
              "Configure the default Radio Access Technology type signaled during GTP set-up";
          leaf type {
            type string {
            }
            description
                "utran|geran|wlan|gan|hspa|eutran|virtual|<0..255>";
          } //type

        } //container rat-type

        leaf report-wlan-location {
          type boolean;
          status "obsolete";
          description
              "Enable/disable reporting the WLAN location of the UE during session set-up";
        }

        container session-hold-time {
          status "obsolete";
          description
              "Configure the time to hold a GTP session after its UE is disconnected";
          leaf seconds {
            type uint32 {
              range "0..3600";
            }
          } //seconds

          leaf remaining-lease-time {
            type boolean;
          } //remaining-lease-time

        } //container session-hold-time

        container charging-characteristics {
          status "obsolete";
          description
              "Configure the charging characteristics";
          container home {
            status "obsolete";
            description
                "Configure the charging characteristics for home UE";
            leaf-list bit {
              type enumeration {
                enum bit0;
                enum bit1;
                enum bit2;
                enum bit3;
                enum bit4;
                enum bit5;
                enum bit6;
                enum bit7;
                enum bit8;
                enum bit9;
                enum bit10;
                enum bit11;
                enum bit12;
                enum bit13;
                enum bit14;
                enum bit15;
              }
              max-elements 16;
            } //bit

          } //container home

          container roaming {
            status "obsolete";
            description
                "Configure the charging characteristics for roaming UE";
            leaf-list bit {
              type enumeration {
                enum bit0;
                enum bit1;
                enum bit2;
                enum bit3;
                enum bit4;
                enum bit5;
                enum bit6;
                enum bit7;
                enum bit8;
                enum bit9;
                enum bit10;
                enum bit11;
                enum bit12;
                enum bit13;
                enum bit14;
                enum bit15;
              }
              max-elements 16;
            } //bit

          } //container roaming

        } //container charging-characteristics

        container ggsn {
          status "obsolete";
          description
              "Configure the communication with a GGSN Mobile Gateway";
          container qos {
            status "obsolete";
            description
                "Configure the QoS for a GGSN Mobile Gateway";
            container ambr {
              status "obsolete";
              description
                  "Configure the Aggregated Maximum Bit Rate (AMBR) to be used in the GTP 
                   messages as APN-AMBR IE";
              leaf down-link {
                type uint32 {
                  range "0..10000000";
                }
              } //down-link

              leaf up-link {
                type uint32 {
                  range "0..10000000";
                }
                description
                    "kbps";
              } //up-link

            } //container ambr

            container arp {
              status "obsolete";
              description
                  "Configure the Allocation/Retention Priority";
              leaf arp-value {
                type uint32 {
                  range "1..3";
                }
              } //arp-value

            } //container arp

            container down-link {
              status "obsolete";
              description
                  "Configure the down-link bitrate in Kbps to be used in the GTP messages";
              leaf gbr {
                type uint32 {
                  range "0..100000";
                }
                description
                    "rate";
              } //gbr

              leaf mbr {
                type uint32 {
                  range "0..100000";
                }
              } //mbr

            } //container down-link

            container up-link {
              status "obsolete";
              description
                  "Configure the up-link bitrate in Kbps to be used in the GTP messages";
              leaf gbr {
                type uint32 {
                  range "0..100000";
                }
              } //gbr

              leaf mbr {
                type uint32 {
                  range "0..100000";
                }
                description
                    "rate";
              } //mbr

            } //container up-link

          } //container qos

        } //container ggsn

        container pgw {
          status "obsolete";
          description
              "Configure the communication with a Packet Data Network Gateway";
          container qos {
            status "obsolete";
            description
                "Configure the QoS for a Packet Data Network Gateway";
            container ambr {
              status "obsolete";
              description
                  "Configure the Aggregated Maximum Bit Rate (AMBR) to be used in the GTP 
                   messages as AMBR IE";
              leaf down-link {
                type uint32 {
                  range "0..10000000";
                }
              } //down-link

              leaf up-link {
                type uint32 {
                  range "0..10000000";
                }
                description
                    "kbps";
              } //up-link

            } //container ambr

            container arp {
              status "obsolete";
              description
                  "Configure the Allocation/Retention Priority";
              leaf arp-value {
                type uint32 {
                  range "1..15";
                }
              } //arp-value

            } //container arp

            container down-link {
              status "obsolete";
              description
                  "Configure the down-link bitrate in Kbps to be used in the GTP messages";
              leaf gbr {
                type uint32 {
                  range "0..100000";
                }
              } //gbr

              leaf mbr {
                type uint32 {
                  range "0..100000";
                }
                description
                    "rate";
              } //mbr

            } //container down-link

            container qci {
              status "obsolete";
              description
                  "Configure the QoS Class Identifier (QCI) value to be used in the GTP messages";
              leaf qci-value {
                type uint32 {
                  range "1..9";
                }
              } //qci-value

            } //container qci

            container up-link {
              status "obsolete";
              description
                  "Configure the up-link bitrate in Kbps to be used in the GTP messages";
              leaf gbr {
                type uint32 {
                  range "0..100000";
                }
              } //gbr

              leaf mbr {
                type uint32 {
                  range "0..100000";
                }
                description
                    "rate";
              } //mbr

            } //container up-link

          } //container qos

        } //container pgw

      } //list mgw-profile

      list tunnel-query {
        key "query-id";
        description
            "Configure a query for tunnels on the ISA";
        leaf query-id {
          type uint32 {
            range "1..1024";
          }
        } //query-id

        leaf name {
          type string;
        } //name

        container address-type {
          description
              "Configure the IP address type to match";
          leaf address-type {
            type enumeration {
              enum ipv4;
              enum ipv6;
              enum not-specified;
            }
          } //address-type

        } //container address-type

        container ap-mac-learn-failed {
          description
              "Match tunnels where learning of the Access Point MAC address failed";
          leaf status {
            type enumeration {
              enum true;
              enum false;
              enum not-specified;
            }
          } //status

        } //container ap-mac-learn-failed

        leaf calculate-counts {
          type boolean;
          description
              "Calculate the counters of matching tunnels";
        }

        container l2-inner-vlan {
          description
              "Match the layer-2 inner VLAN tag";
          leaf q-tag {
            type uint32 {
              range "0..4095";
            }
          } //q-tag

        } //container l2-inner-vlan

        container l2-outer-vlan {
          description
              "Match the layer-2 outer VLAN tag";
          leaf q-tag {
            type uint32 {
              range "0..4095";
            }
          } //q-tag

        } //container l2-outer-vlan

        container l2-sap {
          description
              "Match the SAP";
          leaf sap-id {
            type string;
            description
                "Attribute sap-id for l2-sap";
          } //sap-id

        } //container l2-sap

        container local-address {
          description
              "Configure the local IP address to match";
          leaf local-address-string {
            type string;
            description
                "ip-address";
          } //local-address-string

        } //container local-address

        container max-num-ue {
          description
              "Configure the maximum number of UE on a tunnel to match";
          leaf max-num-ue-id {
            type uint32;
          } //max-num-ue-id

        } //container max-num-ue

        container min-num-ue {
          description
              "Set the minimum number of UE on a tunnel to match";
          leaf minimum {
            type uint32 {
              range "1..4294967295";
            }
          } //minimum

        } //container min-num-ue

        container remote-address {
          description
              "Configure the remote IP address to match";
          leaf ip-address {
            type string;
            description
                "Attribute ip-address for remote-address";
          } //ip-address

        } //container remote-address

        container router {
          description
              "Configure the router instance to match";
          leaf router-instance {
            type string {
              length "1..32";
            }
            description
                "Attribute router-instance for router";
          } //router-instance

        } //container router

        container type {
          presence
              "Configure the tunnel encapsulation types to match";
          leaf gre {
            type boolean;
            description
                "Match GRE tunnels";
          }

          leaf l2 {
            type boolean;
            description
                "Match layer 2 tunnels";
          }

          leaf l2tp {
            type boolean;
            description
                "Match L2TPv3 tunnels";
          }

          leaf vxlan {
            type boolean;
            description
                "Match VXLAN tunnels";
          }

        } //container type

        container ue-state {
          presence
              "Match only tunnels with sufficient UE of the specified state";
          leaf dsm {
            type boolean;
            description
                "Match tunnels with sufficient DSM UE";
          }

          leaf esm {
            type boolean;
            description
                "Match tunnels with sufficient ESM UE";
          }

          leaf l2w {
            type boolean;
            description
                "Match tunnels with sufficient layer-2 wholesale UE";
          }

          leaf migrant {
            type boolean;
            description
                "Match tunnels with sufficient migrant UE";
          }

          leaf xcon {
            type boolean;
            description
                "Match tunnels with sufficient cross-connect UE";
          }

        } //container ue-state

      } //list tunnel-query

      list ue-query {
        key "query-id";
        description
            "Configure a User Equipment query on the ISA";
        leaf query-id {
          type uint32 {
            range "1..1024";
          }
        } //query-id

        leaf name {
          type string;
        } //name

        container address-type {
          description
              "Configure the IP address type to match";
          leaf addr-type {
            type enumeration {
              enum ipv4;
              enum ipv6;
              enum ipv4-only;
              enum ipv6-only;
              enum ipv4v6;
              enum not-specified;
            }
          } //addr-type

        } //container address-type

        container bd {
          description
              "Configure the bridge identifier to match";
          leaf identifier {
            type uint32 {
              range "0..4294967294";
            }
          } //identifier

        } //container bd

        container dhcp6-address {
          description
              "Configure the DHCPv6 address to match";
          leaf ipv6-address {
            type inet:ipv6-address;
            description
                "Attribute ipv6-address for dhcp6-address";
          } //ipv6-address

        } //container dhcp6-address

        container ipv4-address {
          description
              "Configure the UE IP address to match";
          leaf ip-address {
            type inet:ip-address;
          } //ip-address

        } //container ipv4-address

        container mac-address {
          description
              "Configure the MAC address to match";
          leaf ieee-address {
            type string;
            description
                "xx:xx:xx:xx:xx:xx or xx-xx-xx-xx-xx-xx";
          } //ieee-address

        } //container mac-address

        container slaac-prefix {
          description
              "Configure the SLAAC prefix to match";
          leaf ipv6-address {
            type inet:ipv6-address;
            description
                "Attribute ipv6-address for slaac-prefix";
          } //ipv6-address

        } //container slaac-prefix

        container tunnel-local-address {
          description
              "Configure the IP address of the local endpoint of the UE tunnel to match";
          leaf ip-address {
            type string;
            description
                "Attribute ip-address for tunnel-local-address";
          } //ip-address

        } //container tunnel-local-address

        container tunnel-remote-address {
          description
              "Configure the IP address of the remote endpoint of the UE tunnel to match";
          leaf ip-address {
            type string;
            description
                "Attribute ip-address for tunnel-remote-address";
          } //ip-address

        } //container tunnel-remote-address

        container tunnel-router {
          description
              "Configure the router instance to match";
          leaf router-instance {
            type string {
              length "1..32";
            }
            description
                "Attribute router-instance for tunnel-router";
          } //router-instance

        } //container tunnel-router

        container tunnel-type {
          description
              "Configure the tunnel encapsulation type to match";
          leaf tunnel-type {
            type enumeration {
              enum gre;
              enum l2tp;
              enum l2;
              enum vxlan;
              enum not-specified;
            }
          } //tunnel-type

        } //container tunnel-type

        container vlan {
          description
              "Configure the VLAN Q-tag to match";
          leaf tag {
            type uint32 {
              range "0..4096";
            }
          } //tag

        } //container vlan

        container wlan-gw-group {
          description
              "Configure the WLAN Gateway ISA group ID to match";
          leaf wlan-gw-group-id {
            type uint32 {
              range "1..4";
            }
          } //wlan-gw-group-id

          leaf member {
            type uint8 {
              range "1..255";
            }
          } //member

        } //container wlan-gw-group

        container state {
          presence
              "Configure the UE state to match";
          leaf already-signed-in {
            type boolean;
            description
                "Match UE in state already-signed-in";
          }

          leaf authorized-only {
            type boolean;
            description
                "Match UE in state authorized-only";
          }

          leaf cross-connect {
            type boolean;
            description
                "Match cross-connect UE";
          }

          leaf data-triggered {
            type boolean;
            description
                "Match data-triggered UE";
          }

          leaf delete-pending {
            type boolean;
            description
                "Match UE in state delete-pending";
          }

          leaf dhcp-triggered {
            type boolean;
            description
                "Match DHCP triggered UE";
          }

          leaf dsm {
            type boolean;
            description
                "Match DSM UE";
          }

          leaf esm {
            type boolean;
            description
                "Match ESM UE";
          }

          leaf gtp-authorized {
            type boolean;
            description
                "Match GTP-authorized UE";
          }

          leaf ip-assigned {
            type boolean;
            description
                "Match UE in state IP-assigned";
          }

          leaf ip-assigned-authorized {
            type boolean;
            description
                "Match UE in state IP-assigned-authorized";
          }

          leaf l2 {
            type boolean;
            description
                "Match L2 UE";
          }

          leaf portal {
            type boolean;
            description
                "Match portal UE";
          }

        } //container state

      } //list ue-query

    } //container wlan-gw

  } //grouping alu-conf-submgmt-wlangw-r13

} //module  alu-conf-submgmt-wlangw-r13
