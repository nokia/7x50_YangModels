module alu-conf-svc-epipe-r13 {
  yang-version "1";

  namespace "urn:alcatel-lucent.com:sros:ns:yang:conf-svc-epipe-r13";

  prefix "conf-svc-epipe-r13";

  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure Ether Pipe services on SR OS based 
       routers. 
       
       Copyright 2014-2015 Alcatel-Lucent, 2016 Nokia. All rights reserved. 
       Reproduction of this document is authorized on the condition that the 
       foregoing copyright notice is included. 
       
       This alu-conf-svc-epipe-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-04-21";

  grouping alu-conf-svc-epipe-r13 {
    list epipe {
      key "service-id";
      description
          "Configure Ether Pipe services";
      leaf service-id {
        type string;
        description
            "Attribute service-id for epipe";
      } //service-id

      leaf customer {
        type uint32 {
          range "1..2147483647";
        }
      } //customer

      leaf vpn {
        type uint32 {
          range "1..2147483647";
        }
      } //vpn

      leaf vc-switching {
        type boolean;
        description
            "keyword - create a vc-switching Epipe";
      } //vc-switching

      leaf test {
        type boolean;
      } //test

      leaf name {
        type string;
        description
            "64-char max";
      } //name

      list description {
        key "description-string";
        description
            "Description for the service";
        leaf description-string {
          type string {
            length "1..80";
          }
        } //description-string

      } //list description

      container oper-group {
        description
            "Configure oper-group";
        leaf name {
          type string;
        } //name

      } //container oper-group

      container service-mtu {
        description
            "Configure service MTU";
        leaf octets {
          type uint32 {
            range "1..9782";
          }
        } //octets

      } //container service-mtu

      container service-name {
        status "obsolete";
        description
            "Configure a service name";
        leaf service-name {
          type string;
          description
              "64-char max";
        } //service-name

      } //container service-name

      leaf shutdown {
        type boolean;
        description
            "Administratively enable/disable the service";
      }

      container vxlan-src-vtep {
        description
            "Configure termination IP in the EPIPE service for VXLAN tunnels";
        leaf ip-address-ipv6-address {
          type string;
          description
              "Attribute ip-address|ipv6-address for vxlan-src-vtep";
        } //ip-address-ipv6-address

      } //container vxlan-src-vtep

      container bgp {
        presence
            "Configure BGP";
        container route-distinguisher {
          description
              "Configure route distinguisher";
          leaf rd {
            type string {
              length "1..21";
            }
            description
                "<ip-addr:comm-val>|<2byte-asnumber:ext-comm-val>|<4byte-asnumber:comm-val> 
                 ip-addr - a.b.c.d 
                 comm-val - [0..65535] 
                 2byte-asnumber - [1..65535] 
                 ext-comm-val - [0..4294967295] 
                 4byte-asnumber - [1..4294967295]";
          } //rd

          leaf auto-rd {
            type boolean;
          } //auto-rd

        } //container route-distinguisher

        container route-target {
          description
              "Configure route target";
          leaf ext-community {
            type string;
            description
                "Attribute ext-community for route-target";
          } //ext-community

          leaf export {
            type string;
          } //export

          leaf import {
            type string;
          } //import

        } //container route-target

        container vsi-export {
          description
              "VSI export route policies";
          leaf-list policy-name {
            type string {
              length "1..32";
            }
            max-elements 5;
          } //policy-name

        } //container vsi-export

        container vsi-import {
          description
              "VSI import route policies";
          leaf-list policy-name {
            type string {
              length "1..32";
            }
            max-elements 5;
          } //policy-name

        } //container vsi-import

        list pw-template-binding {
          key "policy-id";
          description
              "Configure pw-template bind policy";
          leaf policy-id {
            type uint32 {
              range "1..2147483647";
            }
          } //policy-id

          leaf-list import-rt {
            type string;
            max-elements 5;
            description
                "Attribute ext-community for pw-template-binding";
          } //import-rt

          leaf endpoint {
            type string;
          } //endpoint

          leaf bfd-enable {
            type boolean;
            description
                "Enable/disable BFD";
          }

          container bfd-template {
            description
                "Configure BFD template";
            leaf bfd-template-string {
              type string {
              }
            } //bfd-template-string

          } //container bfd-template

        } //list pw-template-binding

      } //container bgp

      container bgp-evpn {
        presence
            "Configure BGP Ethernet VPN";
        container evi {
          description
              "EVPN Identifier";
          leaf value {
            type uint32 {
              range "1..65535";
            }
          } //value

        } //container evi

        container local-ac-name {
          description
              "Configure local attachment-circuit name";
          leaf ac-name {
            type string;
          } //ac-name

          container eth-tag {
            description
                "Configure ethernet tag value";
            leaf tag-value {
              type int32 {
                range "1..16777215";
              }
            } //tag-value

          } //container eth-tag

        } //container local-ac-name

        list local-attachment-circuit {
          key "ac-name";
          description
              "Configure local attachment circuit information";
          leaf ac-name {
            type string;
          } //ac-name

          leaf endpoint {
            type string;
          } //endpoint

          container eth-tag {
            description
                "Configure ethernet tag";
            leaf tag-value {
              type int32 {
                range "1..16777215";
              }
            } //tag-value

          } //container eth-tag

        } //list local-attachment-circuit

        list mpls {
          key "bgp";
          description
              "Configure BGP EVPN mpls";
          leaf bgp {
            type uint32 {
              range "1..2";
            }
          } //bgp

          leaf endpoint {
            type string;
          } //endpoint

          leaf control-word {
            type boolean;
            description
                "Enable/disable setting the CW bit in the label message";
          }

          container default-route-tag {
            description
                "Configure default-route-tag to match against export policies";
            leaf t0x01..0xff {
              type string;
              description
                  "[1..255] - accepts in decimal or hex";
            } //t0x01..0xff

          } //container default-route-tag

          container ecmp {
            description
                "Configure maximum ECMP routes information";
            leaf max-ecmp-routes {
              type string;
              description
                  "Attribute max-ecmp-routes for ecmp";
            } //max-ecmp-routes

          } //container ecmp

          leaf entropy-label {
            type boolean;
            description
                "Enable/disable use of entropy-label";
          }

          container force-qinq-vc-forwarding {
            description
                "Forces qinq-vc-type forwarding in the data-path";
            leaf c-tag-c-tag---s-tag-c-tag {
              type enumeration {
                enum c-tag-c-tag;
                enum s-tag-c-tag;
              }
              description
                  "c-tag-c-tag | s-tag-c-tag";
            } //c-tag-c-tag---s-tag-c-tag

          } //container force-qinq-vc-forwarding

          leaf force-vlan-vc-forwarding {
            type boolean;
            description
                "Forces vlan-vc-type forwarding in the data-path";
          }

          container oper-group {
            description
                "Configure oper-group";
            leaf name {
              type string;
            } //name

          } //container oper-group

          container route-next-hop {
            description
                "Configure route next-hop";
            leaf system-ipv4 {
              type boolean;
            } //system-ipv4

            leaf system-ipv6 {
              type boolean;
            } //system-ipv6

            leaf ip-address {
              type inet:ip-address;
            } //ip-address

          } //container route-next-hop

          container send-evpn-encap {
            description
                "Configure encapsulation for this service";
            leaf mpls {
              type boolean;
            } //mpls

            leaf mplsoudp {
              type boolean;
            } //mplsoudp

          } //container send-evpn-encap

          leaf shutdown {
            type boolean;
            description
                "Administratively Enable/Disable BGP-EVPN mpls";
          }

          container auto-bind-tunnel {
            description
                "Configure BGP EVPN mpls auto-bind-tunnel";
            leaf allow-flex-algo-fallback {
              type boolean;
              description
                  "Allow/Disallow Flex Algo Fallback";
            }

            container ecmp {
              description
                  "Configure maximum ECMP routes information";
              leaf max-ecmp-routes {
                type string;
                description
                    "[1..32]: default 1";
              } //max-ecmp-routes

            } //container ecmp

            leaf enforce-strict-tunnel-tagging {
              type boolean;
              description
                  "Enable/disable enforcement of strict tunnel tagging";
            }

            container resolution {
              description
                  "Configure resolution method for tunnel selection";
              leaf disabled-any-filter {
                type enumeration {
                  enum disabled;
                  enum any;
                  enum filter;
                }
              } //disabled-any-filter

            } //container resolution

            container resolution-filter {
              description
                  "Configure auto-bind-tunnel resolution filter information";
              leaf bgp {
                type boolean;
                description
                    "Enable/disable setting BGP type for auto-bind-tunnel";
              }

              leaf ldp {
                type boolean;
                description
                    "Enable/disable setting LDP type for auto-bind-tunnel";
              }

              leaf mpls-fwd-policy {
                type boolean;
                description
                    "Enable/disable MPLS Forwarding Policy for auto-bind-tunnel";
              }

              leaf rib-api {
                type boolean;
                description
                    "Enable/disable setting RIB-API type for auto-bind-tunnel";
              }

              leaf rsvp {
                type boolean;
                description
                    "Enable/disable setting RSVP-TE type for auto-bind-tunnel";
              }

              leaf sr-isis {
                type boolean;
                description
                    "Enable/disable setting SR-ISIS type for auto-bind-tunnel";
              }

              leaf sr-ospf {
                type boolean;
                description
                    "Enable/disable setting SR-OSPF type for auto-bind-tunnel";
              }

              leaf sr-ospf3 {
                type boolean;
                description
                    "Enable/disable setting SR-OSPFv3 type for auto-bind-tunnel";
              }

              leaf sr-policy {
                type boolean;
                description
                    "Enable/disable setting SR-Policy type for auto-bind-tunnel";
              }

              leaf sr-te {
                type boolean;
                description
                    "Enable/disable setting SR-TE type for auto-bind-tunnel";
              }

              leaf udp {
                type boolean;
                description
                    "Enable/disable setting UDP type for auto-bind-tunnel";
              }

            } //container resolution-filter

          } //container auto-bind-tunnel

        } //list mpls

        container remote-ac-name {
          description
              "Configure remote attachment-circuit name";
          leaf ac-name {
            type string;
          } //ac-name

          container eth-tag {
            description
                "Configure ethernet tag value";
            leaf tag-value {
              type int32 {
                range "1..16777215";
              }
            } //tag-value

          } //container eth-tag

        } //container remote-ac-name

        list remote-attachment-circuit {
          key "ac-name";
          description
              "Configure remote attachment circuit information";
          leaf ac-name {
            type string;
          } //ac-name

          leaf endpoint {
            type string;
          } //endpoint

          container eth-tag {
            description
                "Configure ethernet tag";
            leaf tag-value {
              type int32 {
                range "1..16777215";
              }
            } //tag-value

          } //container eth-tag

        } //list remote-attachment-circuit

        list vxlan {
          key "bgp";
          description
              "Configure BGP EVPN vxlan";
          leaf bgp {
            type uint32 {
              range "1..2";
            }
          } //bgp

          leaf vxlan-instance {
            type uint32 {
              range "1..2";
            }
          } //vxlan-instance

          container default-route-tag {
            description
                "Configure default-route-tag to match against export policies";
            leaf t0x01..0xff {
              type string;
              description
                  "[1..255] - accepts in decimal or hex";
            } //t0x01..0xff

          } //container default-route-tag

          container ecmp {
            description
                "Configure max ECMP routes";
            leaf max-ecmp-routes {
              type uint32 {
                range "1..32";
              }
              description
                  "[1..32]: default 1";
            } //max-ecmp-routes

          } //container ecmp

          leaf send-evpn-encap {
            type boolean;
            description
                "Enable/Disable sending Vxlan Encap";
          }

          leaf shutdown {
            type boolean;
            description
                "Administratively Enable/Disable BGP-EVPN vxlan";
          }

        } //list vxlan

      } //container bgp-evpn

      container bgp-vpws {
        presence
            "Configure BGP-VPWS";
        leaf shutdown {
          type boolean;
          description
              "Administratively Enable/Disable BGP-VPWS";
        }

        list remote-ve-name {
          key "name";
          description
              "Configure remote vpws-edge name for BGP-VPWS";
          leaf name {
            type string;
          } //name

          container ve-id {
            description
                "Configure vpws-edge identifier";
            leaf value {
              type uint32 {
                range "1..65535";
              }
            } //value

          } //container ve-id

        } //list remote-ve-name

        container ve-name {
          description
              "Configure vpws-edge name for BGP-VPWS";
          leaf name {
            type string;
          } //name

          container ve-id {
            description
                "Configure vpws-edge identifier";
            leaf value {
              type uint32 {
                range "1..65535";
              }
            } //value

          } //container ve-id

        } //container ve-name

      } //container bgp-vpws

      list endpoint {
        key "endpoint-name";
        description
            "Configure a service end-point";
        leaf endpoint-name {
          type string {
            length "1..32";
          }
        } //endpoint-name

        container active-hold-delay {
          description
              "Configure the time to hold the active status";
          leaf active-hold-delay {
            type uint32 {
              range "1..60";
            }
            description
                "[1..60] deci-seconds";
          } //active-hold-delay

        } //container active-hold-delay

        container description {
          description
              "Description for the service end-point";
          leaf description-string {
            type string {
              length "1..80";
            }
          } //description-string

        } //container description

        container revert-time {
          description
              "Configure the time to wait before reverting to primary spoke-sdp";
          leaf revert-time {
            type uint32 {
              range "0..600";
            }
            description
                "[0..600] seconds";
          } //revert-time

          leaf infinite {
            type boolean;
            description
                "keyword - makes endpoint non-revertive";
          } //infinite

        } //container revert-time

        leaf standby-signaling-master {
          type boolean;
          description
              "Enable PW standby-signaling master";
        }

        leaf standby-signaling-slave {
          type boolean;
          description
              "Enable PW standby-signaling slave";
        }

      } //list endpoint

      container eth-cfm {
        description
            "Configure CFM parameters";
        container tunnel-fault {
          description
              "Accept/Ignore tunnel fault notification";
          leaf tunnel-fault-id {
            type enumeration {
              enum accept;
              enum ignore;
            }
          } //tunnel-fault-id

        } //container tunnel-fault

      } //container eth-cfm

      container load-balancing {
        description
            "Configure load balancing information";
        leaf per-service-hashing {
          type boolean;
          description
              "Enable/disable per service hashing";
        }

      } //container load-balancing

      list nat-outside {
        key "nat-group-id";
        description
            "Configure the NAT outside service";
        leaf nat-group-id {
          type uint32 {
            range "1..4";
          }
        } //nat-group-id

        leaf shutdown {
          type boolean;
          description
              "Administratively enable/disable the service";
        }

      } //list nat-outside

      container pbb {
        description
            "Configure PBB paramters";
        leaf force-qtag-forwarding {
          type boolean;
          description
              "Enable/Disable 802.1q tag forwarding";
        }

        container tunnel {
          description
              "Configure pbb-tunnel with b-vpls service information";
          leaf service-id {
            type string;
            description
                "Attribute service-id for tunnel";
          } //service-id

          leaf backbone-dest-mac {
            type boolean;
          } //backbone-dest-mac

          leaf mac-name {
            type string {
              length "1..32";
            }
            description
                "32 char max";
          } //mac-name

          leaf ieee-address {
            type string;
            description
                "xx:xx:xx:xx:xx:xx or xx-xx-xx-xx-xx-xx";
          } //ieee-address

          leaf isid {
            type int32 {
              range "0..16777215";
            }
          } //isid

        } //container tunnel

      } //container pbb

      container pw-port {
        description
            "Configure PW cross connect information";
        leaf pw-port-id {
          type uint32 {
            range "1..32767";
          }
        } //pw-port-id

        leaf fpe {
          type uint32 {
            range "1..64";
          }
        } //fpe

        container monitor-oper-group {
          description
              "Configure an Operational-Group to monitor";
          leaf group-name {
            type string;
          } //group-name

        } //container monitor-oper-group

        leaf shutdown {
          type boolean;
          description
              "Enable/Disable pseudo-wire port";
        }

        container egress {
          description
              "Configure pseudo-wire port egress side parameters";
          container shaper {
            presence
                "Configure shaper parameters";
            container int-dest-id {
              description
                  "Configure an intermediate destination identifier applicable to esm pw-saps";
              leaf name {
                type string;
              } //name

            } //container int-dest-id

            container vport {
              description
                  "Configure a virtual port applicable to all pw-saps";
              leaf vport {
                type string;
              } //vport

            } //container vport

          } //container shaper

        } //container egress

      } //container pw-port

      list sap {
        key "sap-id";
        description
            "Provision a SAP";
        leaf sap-id {
          type string;
          description
              "Attribute sap-id for sap";
        } //sap-id

        leaf endpoint {
          type string {
            length "1..32";
          }
        } //endpoint

        leaf no-endpoint {
          type boolean;
          description
              "keyword - used to remove an endpoint association";
        } //no-endpoint

        container aarp {
          description
              "Configure AARP instance id";
          leaf aarpId {
            type uint32 {
              range "1..65535";
            }
          } //aarpId

          leaf type {
            type enumeration {
              enum dual-homed;
              enum dual-homed-secondary;
            }
          } //type

        } //container aarp

        list accounting-policy {
          key "acct-policy-id";
          description
              "Configure accounting-policy to be used";
          leaf acct-policy-id {
            type uint64 {
              range "1..99";
            }
          } //acct-policy-id

        } //list accounting-policy

        container app-profile {
          description
              "Configure the application profile name";
          leaf app-profile-name {
            type string {
              length "1..32";
            }
          } //app-profile-name

        } //container app-profile

        container bandwidth {
          description
              "Configure SAP Bandwidth";
          leaf bandwidth-in-kbps {
            type string;
            description
                "[1..6400000000]";
          } //bandwidth-in-kbps

        } //container bandwidth

        leaf cflowd {
          type boolean;
          description
              "Configure Cflowd collection and analysis on this SAP";
        }

        leaf collect-stats {
          type boolean;
          description
              "Enable/disable statistics collection";
        }

        container cpu-protection {
          description
              "Configure CPU protection";
          leaf policy-id {
            type uint32 {
              range "1..255";
            }
          } //policy-id

          leaf mac-monitoring {
            type boolean;
            description
                "keyword - enable MAC monitoring";
          } //mac-monitoring

          leaf eth-cfm-monitoring {
            type boolean;
            description
                "keyword - enable Ethernet Connectivity Fault Management monitoring";
          } //eth-cfm-monitoring

          leaf aggregate {
            type boolean;
            description
                "keyword - apply the rate limit to the sum of the per peer packet rates";
          } //aggregate

          leaf car {
            type boolean;
            description
                "keyword - Committed Access Rate - ignore Eth-CFM packets when enforcing 
                 overall-rate";
          } //car

        } //container cpu-protection

        list description {
          key "long-description-string";
          description
              "Description for the SAP";
          leaf long-description-string {
            type string {
              length "1..160";
            }
          } //long-description-string

        } //list description

        container dist-cpu-protection {
          description
              "Assign Distributed CPU protection policy for the SAP";
          leaf policy-name {
            type string;
          } //policy-name

        } //container dist-cpu-protection

        leaf ignore-oper-down {
          type boolean;
          description
              "Enable/Disable whether to ignore operationally down status for service oper 
               state calculation";
        }

        container lag-link-map-profile {
          description
              "Configure lag link profile";
          leaf link-map-profile-id {
            type string;
            description
                "Attribute link-map-profile-id for lag-link-map-profile";
          } //link-map-profile-id

        } //container lag-link-map-profile

        container lag-per-link-hash {
          description
              "Configure lag-per-link-hash information";
          leaf class {
            type enumeration {
              enum 1;
              enum 2;
              enum 3;
            }
          } //class

          leaf weight {
            type uint32 {
              range "1..1024";
            }
          } //weight

        } //container lag-per-link-hash

        container monitor-oper-group {
          description
              "Configure an Operational-Group to monitor";
          leaf group-name {
            type string {
              length "1..32";
            }
          } //group-name

        } //container monitor-oper-group

        container multi-service-site {
          description
              "Specify the multi-service-site to which this SAP belongs";
          leaf customer-site-name {
            type string {
              length "1..32";
            }
          } //customer-site-name

        } //container multi-service-site

        container oper-group {
          description
              "Configure operational-group";
          leaf group-name {
            type string {
              length "1..32";
            }
          } //group-name

        } //container oper-group

        container ring-node {
          description
              "Configure a multi-chassis ring-node for this SAP";
          leaf ring-node-name {
            type string {
              length "1..32";
            }
          } //ring-node-name

        } //container ring-node

        leaf shutdown {
          type boolean;
          description
              "Administratively enable/disable the SAP";
        }

        container tod-suite {
          status "obsolete";
          description
              "Configure a time-of-day suite for this SAP";
          leaf tod-suite-name {
            type string {
              length "1..32";
            }
          } //tod-suite-name

        } //container tod-suite

        container transit-policy {
          description
              "Configure transit policy id";
          leaf prefix {
            type uint32 {
              range "1..65535";
            }
          } //prefix

          leaf ip {
            type uint32 {
              range "1..65535";
            }
          } //ip

        } //container transit-policy

        container atm {
          description
              "Configure ATM properties";
          container encapsulation {
            description
                "Configure the ATM encap-type";
            leaf atm-encap-type {
              type enumeration {
                enum aal5snap-bridged;
                enum aal5mux-bridged-eth-nofcs;
              }
              description
                  "keywords - aal5snap-bridged|aal5mux-bridged-eth-nofcs";
            } //atm-encap-type

          } //container encapsulation

          container egress {
            description
                "Configure egress parameters";
            container traffic-desc {
              description
                  "Assign ATM traffic descriptor profile";
              leaf traffic-desc-profile-id {
                type int32 {
                  range "1..1000";
                }
              } //traffic-desc-profile-id

            } //container traffic-desc

          } //container egress

          container ingress {
            description
                "Configure ingress parameters";
            container traffic-desc {
              description
                  "Assign ATM traffic descriptor profile";
              leaf traffic-desc-profile-id {
                type int32 {
                  range "1..1000";
                }
              } //traffic-desc-profile-id

            } //container traffic-desc

          } //container ingress

          container oam {
            description
                "Configure OAM properties";
            leaf alarm-cells {
              type boolean;
              description
                  "Disable/enable handling and generation of AIS/RDI";
            }

          } //container oam

        } //container atm

        container cem {
          description
              "Configure CEM properties";
          container local-ecid {
            description
                "Configure local ECID";
            leaf emulated-circuit-identifier {
              type uint32 {
                range "0..1048575";
              }
            } //emulated-circuit-identifier

          } //container local-ecid

          container packet {
            description
                "Configure jitter buffer and payload size";
            leaf jitter-buffer {
              type uint32 {
                range "0..250";
              }
              description
                  "[1..250]";
            } //jitter-buffer

            leaf payload-size {
              type uint32 {
                range "16..2048";
              }
            } //payload-size

          } //container packet

          container remote-ecid {
            description
                "Configure remote ECID";
            leaf emulated-circuit-identifier {
              type uint32 {
                range "0..1048575";
              }
            } //emulated-circuit-identifier

          } //container remote-ecid

          container remote-mac {
            description
                "Configure remote MAC address";
            leaf ieee-address {
              type alu:ieee-address;
              description
                  "xx:xx:xx:xx:xx:xx or xx-xx-xx-xx-xx-xx";
            } //ieee-address

          } //container remote-mac

          container report-alarm {
            description
                "Enable/disable logging of CEM SAP alarms";
            leaf stray {
              type boolean;
            } //stray

            leaf malformed {
              type boolean;
            } //malformed

            leaf pktloss {
              type boolean;
            } //pktloss

            leaf overrun {
              type boolean;
            } //overrun

            leaf underrun {
              type boolean;
            } //underrun

            leaf rpktloss {
              type boolean;
            } //rpktloss

            leaf rfault {
              type boolean;
            } //rfault

            leaf rrdi {
              type boolean;
            } //rrdi

          } //container report-alarm

          leaf rtp-header {
            type boolean;
            description
                "Enable/Disable RTP header";
          }

        } //container cem

        container egress {
          description
              "Configure egress policies";
          container egress-remark-policy {
            description
                "Specify an egress-remark-policy";
            leaf egress-remark-policy-name {
              type string {
                length "1..64";
              }
            } //egress-remark-policy-name

          } //container egress-remark-policy

          container filter {
            description
                "Apply egress filter";
            leaf ip {
              type string;
              description
                  "[1..65535]|<name:64 char max>";
            } //ip

            leaf mac {
              type string;
              description
                  "[1..65535]|<name:64 char max>";
            } //mac

            leaf ipv6 {
              type string;
              description
                  "[1..65535]|<name:64 char max>";
            } //ipv6

          } //container filter

          container policer-control-policy {
            description
                "Specify policer control policy";
            leaf policy-name {
              type string {
                length "1..32";
              }
            } //policy-name

          } //container policer-control-policy

          leaf qinq-mark-top-only {
            type boolean;
            description
                "Mark p-bits on top q-tag only";
          }

          list qos {
            key "policy-id";
            description
                "Apply egress QoS policy";
            leaf policy-id {
              type string;
              description
                  "[1..65535]|<name:64 char max>";
            } //policy-id

            leaf port-redirect-group {
              type string {
                length "1..32";
              }
            } //port-redirect-group

            leaf instance {
              type uint16 {
                range "1..65535";
              }
            } //instance

          } //list qos

          container scheduler-policy {
            description
                "Specify a scheduler-policy";
            leaf scheduler-policy-name {
              type string {
                length "1..32";
              }
            } //scheduler-policy-name

          } //container scheduler-policy

          container vlan-qos-policy {
            description
                "Specify a vlan-qos-policy";
            leaf vlan-qos-policy-name {
              type string;
            } //vlan-qos-policy-name

          } //container vlan-qos-policy

          container agg-rate {
            presence
                "Configure aggregate rate limit";
            leaf limit-unused-bandwidth {
              type boolean;
              description
                  "Specify whether to enable limit unused bandwidth";
            }

            leaf queue-frame-based-accounting {
              type boolean;
              description
                  "Specify whether to enable queue frame based accounting";
            }

            container rate {
              description
                  "Specify rate limit for agg-rate";
              leaf kilobits-per-second {
                type string;
                description
                    "[1..6400000000|max] Kbps";
              } //kilobits-per-second

              leaf cir {
                type string;
                description
                    "Attribute cir-kilobits-per-second for rate";
              } //cir

            } //container rate

          } //container agg-rate

          container hsmda-queue-override {
            presence
                "Configure HSMDA egress queue overrides";
            container packet-byte-offset {
              description
                  "Specify a packet offset for HSMDA queue accounting";
              leaf add {
                type uint32 {
                  range "0..31";
                }
              } //add

              leaf subtract {
                type string;
                description
                    "Attribute sub-bytes for packet-byte-offset";
              } //subtract

            } //container packet-byte-offset

            container secondary-shaper {
              description
                  "Configure a HSMDA egress secondary shaper";
              leaf secondary-shaper-name {
                type string {
                  length "1..32";
                }
              } //secondary-shaper-name

            } //container secondary-shaper

            container wrr-policy {
              description
                  "Configure a HSMDA egress wrr-policy";
              leaf policy-name {
                type string {
                  length "1..32";
                }
              } //policy-name

            } //container wrr-policy

            list queue {
              key "queue-id";
              description
                  "Configure overrides for a HSMDA egress queue";
              leaf queue-id {
                type uint32 {
                  range "1..8";
                }
              } //queue-id

              container mbs {
                description
                    "Specify MBS rate";
                leaf mbs-string {
                  type string;
                } //mbs-string

                leaf mbs-id-2 {
                  type enumeration {
                    enum bytes;
                    enum kilobytes;
                  }
                } //mbs-id-2

              } //container mbs

              container rate {
                description
                    "Specify rate (PIR)";
                leaf pir-rate {
                  type string;
                  description
                      "[1..100000000|max]";
                } //pir-rate

              } //container rate

              container slope-policy {
                description
                    "Specify slope policy";
                leaf hsmda-slope-policy-name {
                  type string {
                    length "1..32";
                  }
                } //hsmda-slope-policy-name

              } //container slope-policy

              container wrr-weight {
                description
                    "Specify wrr-weight";
                leaf weight {
                  type int32 {
                    range "1..32";
                  }
                  description
                      "[1..32]";
                } //weight

              } //container wrr-weight

            } //list queue

          } //container hsmda-queue-override

          container policer-control-override {
            description
                "Configure policer control overrides";
            container max-rate {
              description
                  "Configure Max Rate override in kilobits-per-second";
              leaf rate {
                type string;
                description
                    "[1..6400000000|max] Kbps";
              } //rate

            } //container max-rate

            container priority-mbs-thresholds {
              description
                  "Configure priority mbs thresholds overrides";
              container min-thresh-separation {
                description
                    "configure min threshold separation override";
                leaf size {
                  type string;
                  description
                      "[0..16777216 default]";
                } //size

                leaf min-thresh-separation-id {
                  type enumeration {
                    enum bytes;
                    enum kilobytes;
                  }
                } //min-thresh-separation-id

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf mbs-contribution-id {
                    type enumeration {
                      enum bytes;
                      enum kilobytes;
                    }
                  } //mbs-contribution-id

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "Specify packet byte offset";
                leaf add {
                  type uint32 {
                    range "0..31";
                  }
                } //add

                leaf subtract {
                  type string;
                  description
                      "Attribute sub-bytes for packet-byte-offset";
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..6400000000|max] Kbps";
                } //pir-rate

                leaf cir {
                  type string;
                  description
                      "[0..6400000000|max] Kbps";
                } //cir

              } //container rate

              container stat-mode {
                description
                    "Specify Stat Mode for the policer";
                leaf stat-mode {
                  type enumeration {
                    enum no-stats;
                    enum minimal;
                    enum offered-profile-no-cir;
                    enum offered-profile-cir;
                    enum offered-total-cir;
                    enum offered-limited-capped-cir;
                    enum offered-profile-capped-cir;
                    enum offered-total-cir-exceed;
                    enum offered-four-profile-no-cir;
                    enum offered-total-cir-four-profile;
                  }
                } //stat-mode

              } //container stat-mode

            } //list policer

          } //container policer-override

          container qtag-manipulation {
            status "obsolete";
            presence
                "Configure VLAN Tag Manipulation";
            leaf preserve {
              type boolean;
              status "obsolete";
              description
                  "Preserve tags";
            }

            leaf push {
              type boolean;
              status "obsolete";
              description
                  "Push tags";
            }

            container translate {
              status "obsolete";
              description
                  "Replace or pop tags";
              leaf t1-to-1-1-to-2-2-to-2 {
                type enumeration {
                  enum 1-to-1;
                  enum 1-to-2;
                  enum 2-to-2;
                }
                description
                    "keywords";
              } //t1-to-1-1-to-2-2-to-2

              leaf qtag1.qtag2 {
                type string;
                description
                    "null[.null]";
              } //qtag1.qtag2

            } //container translate

          } //container qtag-manipulation

          container queue-override {
            presence
                "Apply queue override";
            container hs-secondary-shaper {
              description
                  "Specify HS Secondary Shaper";
              leaf policy-name {
                type string;
              } //policy-name

            } //container hs-secondary-shaper

            list hs-wrr-group {
              key "group-id";
              description
                  "Configure HS WRR Group";
              leaf group-id {
                type uint16 {
                  range "1..2";
                }
                description
                    "[1..2]";
              } //group-id

              container class-weight {
                description
                    "Specify class weight";
                leaf weight {
                  type enumeration {
                    enum 1;
                    enum 2;
                    enum 4;
                    enum 8;
                  }
                } //weight

              } //container class-weight

              container percent-rate {
                description
                    "Specify percent rate";
                leaf percent {
                  type string;
                  description
                      "[0.01..100.00]";
                } //percent

              } //container percent-rate

              container rate {
                description
                    "Specify rates (PIR)";
                leaf rate {
                  type string;
                  description
                      "Attribute rate for rate";
                } //rate

              } //container rate

            } //list hs-wrr-group

            list queue {
              key "queue-id";
              description
                  "Configure a queue override";
              leaf queue-id {
                type int32 {
                  range "1..8";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container avg-frame-overhead {
                description
                    "Specify the average frame overhead";
                leaf percentage {
                  type string;
                  description
                      "[0.00..100.00]";
                } //percentage

              } //container avg-frame-overhead

              container burst-limit {
                description
                    "Specify burst limit";
                leaf size {
                  type string;
                  description
                      "Attribute size for burst-limit";
                } //size

                leaf bytes-kilobytes {
                  type enumeration {
                    enum bytes;
                    enum kilobytes;
                  }
                } //bytes-kilobytes

              } //container burst-limit

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container hs-class-weight {
                description
                    "Specify HS class weight";
                leaf weight {
                  type enumeration {
                    enum 1;
                    enum 2;
                    enum 4;
                    enum 8;
                  }
                } //weight

              } //container hs-class-weight

              container hs-wred-queue {
                description
                    "Configure HS WRED queue";
                leaf policy {
                  type string {
                    length "1..32";
                  }
                } //policy

              } //container hs-wred-queue

              container hs-wrr-weight {
                description
                    "Specify HS WRR weight";
                leaf weight {
                  type uint16 {
                    range "1..127";
                  }
                  description
                      "[1..127]";
                } //weight

              } //container hs-wrr-weight

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container monitor-queue-depth {
                description
                    "Enable/Disable fast polling queue-depth monitoring";
                leaf fast-polling {
                  type boolean;
                } //fast-polling

                leaf violation-threshold {
                  type string;
                  description
                      "[00.01..99.99]";
                } //violation-threshold

              } //container monitor-queue-depth

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..6400000000|max] Kbps";
                } //pir-rate

                leaf cir {
                  type string;
                  description
                      "[0..6400000000|sum|max] Kbps";
                } //cir

              } //container rate

            } //list scheduler

          } //container scheduler-override

          container vlan-manipulation {
            presence
                "Configure VLAN Tag Manipulation";
            leaf preserve {
              type boolean;
              description
                  "Preserve tags";
            }

            leaf push {
              type boolean;
              description
                  "Push tags";
            }

            container translate {
              description
                  "Replace or pop tags";
              leaf t1-to-1-1-to-2-2-to-2 {
                type enumeration {
                  enum 1-to-1;
                  enum 1-to-2;
                  enum 2-to-2;
                }
                description
                    "keywords";
              } //t1-to-1-1-to-2-2-to-2

              leaf qtag1.qtag2 {
                type string;
                description
                    "null[.null]";
              } //qtag1.qtag2

            } //container translate

          } //container vlan-manipulation

        } //container egress

        container eth-cfm {
          description
              "Configure CFM parameters";
          leaf ais-enable {
            type boolean;
            description
                "Configure the generation of AIS messages based on Facility Fault";
          }

          leaf collect-lmm-stats {
            type boolean;
            description
                "Enable/Disable the collection of statistics for OAM-PM Loss Measurement 
                 Message (LMM) tests";
          }

          list mip {
            key "primary-vlan-enable";
            description
                "Enable/Disable Maintenance Intermediate Points";
            leaf mac {
              type yang:mac-address;
            } //mac

            leaf default-mac {
              type boolean;
              description
                  "keyword - Use the default MAC address for the MIP";
            } //default-mac

            leaf primary-vlan-enable {
              type uint32 {
                range "1..4094";
              }
            } //primary-vlan-enable

          } //list mip

          container squelch-ingress-levels {
            description
                "Configure the level(s) of the ETH-CFM PDUs that will be silently discarded";
            leaf t0 {
              type boolean;
              description
                  "[0..7]";
            } //t0

            leaf t1 {
              type boolean;
            } //t1

            leaf t2 {
              type boolean;
            } //t2

            leaf t3 {
              type boolean;
            } //t3

            leaf t4 {
              type boolean;
            } //t4

            leaf t5 {
              type boolean;
            } //t5

            leaf t6 {
              type boolean;
            } //t6

            leaf t7 {
              type boolean;
            } //t7

          } //container squelch-ingress-levels

          container tunnel-fault {
            description
                "Accept/Ignore tunnel fault notification";
            leaf tunnel-fault-id {
              type enumeration {
                enum accept;
                enum ignore;
              }
            } //tunnel-fault-id

          } //container tunnel-fault

          container collect-lmm-fc-stats {
            description
                "Configure the collection of Forwarding Class (FC) aware statistics for OAM-PM 
                 Loss Measurement Message (LMM) tests";
            container fc {
              description
                  "Configure Forwarding Class (FC) counters without regard for profile";
              leaf-list fc-name {
                type enumeration {
                  enum be;
                  enum l2;
                  enum af;
                  enum l1;
                  enum h2;
                  enum ef;
                  enum h1;
                  enum nc;
                }
                max-elements 8;
              } //fc-name

            } //container fc

            container fc-in-profile {
              description
                  "Configure only in profile Forwarding Class (FC) counters";
              leaf-list fc-name {
                type enumeration {
                  enum be;
                  enum l2;
                  enum af;
                  enum l1;
                  enum h2;
                  enum ef;
                  enum h1;
                  enum nc;
                }
                max-elements 8;
              } //fc-name

            } //container fc-in-profile

          } //container collect-lmm-fc-stats

          list mep {
            key "mep-id domain association";
            description
                "Configure a CFM Maintenance Endpoint";
            leaf mep-id {
              type int16 {
                range "1..8191";
              }
              description
                  "Attribute mep-id for mep";
            } //mep-id

            leaf domain {
              type uint32 {
                range "1..4294967295";
              }
            } //domain

            leaf association {
              type uint32 {
                range "1..4294967295";
              }
            } //association

            leaf direction {
              type enumeration {
                enum up;
                enum down;
              }
              description
                  "keywords";
            } //direction

            leaf primary-vlan-enable {
              type boolean;
              description
                  "keyword - Provision MEP using MA primary vlan-id";
            } //primary-vlan-enable

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            container description {
              description
                  "Add/remove a text description for the MEP";
              leaf description-string {
                type string {
                }
                description
                    "[80 chars max]";
              } //description-string

            } //container description

            container fault-propagation-enable {
              description
                  "Configure the Fault Propagation for the MEP";
              leaf use-if-tlv-suspend-ccm {
                type enumeration {
                  enum use-if-tlv;
                  enum suspend-ccm;
                }
                description
                    "keywords - use interface TLV, or suspend Continuity Check Messages";
              } //use-if-tlv-suspend-ccm

            } //container fault-propagation-enable

            leaf install-mep {
              type boolean;
              description
                  "Enable/Disable Installation of the MEP in the forwarding plane";
            }

            leaf lbm-svc-act-responder {
              type boolean;
              description
                  "Enable/Disable processing of service activation streams that may be 
                   encapsulated in the ETH-CFM request Loopback Message (LBM) on the MEP";
            }

            container low-priority-defect {
              description
                  "Configure the Lowest Priority Defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the MAC Address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container ais-enable {
              presence
                  "Configure the generation and reception of Alarm Indication Signal (AIS) 
                   message parameters";
              container client-meg-level {
                description
                    "Configure the client meg level";
                leaf t1 {
                  type boolean;
                  description
                      "[1..7]";
                } //t1

                leaf t2 {
                  type boolean;
                } //t2

                leaf t3 {
                  type boolean;
                } //t3

                leaf t4 {
                  type boolean;
                } //t4

                leaf t5 {
                  type boolean;
                } //t5

                leaf t6 {
                  type boolean;
                } //t6

                leaf t7 {
                  type boolean;
                } //t7

              } //container client-meg-level

              leaf interface-support-enable {
                type boolean;
                description
                    "Enable/disable the generation of AIS PDUs based on the associated endpoint 
                     state";
              }

              container interval {
                description
                    "Configure the transmission interval of AIS messages";
                leaf t1-60 {
                  type enumeration {
                    enum 1;
                    enum 60;
                  }
                  default 1;
                  description
                      "seconds - Default: 1";
                } //t1-60

              } //container interval

              container low-priority-defect {
                description
                    "Configure the Lowest Priority Defect for the MEP AIS generation";
                leaf allDef-macRemErrXcon {
                  type enumeration {
                    enum allDef;
                    enum macRemErrXcon;
                  }
                  description
                      "keywords";
                } //allDef-macRemErrXcon

              } //container low-priority-defect

              container priority {
                description
                    "Configure the priority of AIS messages originated by the node";
                leaf priority-value {
                  type uint32 {
                    range "0..7";
                  }
                  default 7;
                  description
                      "[0..7] - Default: 7";
                } //priority-value

              } //container priority

            } //container ais-enable

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container csf-enable {
              presence
                  "Configure the reception of Client Signal Fail (CSF) message parameters";
              container multiplier {
                description
                    "Configure the multiplier used for timing out CSF";
                leaf multiplier-value {
                  type string;
                  description
                      "[0.0|2.0 .. 30.0] - Default: 3.5";
                } //multiplier-value

              } //container multiplier

            } //container csf-enable

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

        container eth-tunnel {
          description
              "Configure Ethernet Tunnel SAP parameters";
          list path {
            key "path-index";
            description
                "Configure Ethernet Tunnel SAP Path parameters";
            leaf path-index {
              type string;
              description
                  "Attribute path-index for path";
            } //path-index

            leaf tag {
              type string;
              description
                  "[0..4094|*]";
            } //tag

          } //list path

        } //container eth-tunnel

        container ethernet {
          description
              "Configure Ethernet properties";
          leaf llf {
            type boolean;
            description
                "Enable/Disable Ethernet Link Loss Forwarding";
          }

        } //container ethernet

        container frame-relay {
          description
              "Configure frame-relay parameters";
          container scheduling-class {
            description
                "Configure frf.12 scheduling class";
            leaf class-id {
              type uint32 {
                range "0..3";
              }
            } //class-id

          } //container scheduling-class

          container frf-12 {
            presence
                "Enable/Disable FRF12 Headers";
            container ete-fragment-threshold {
              description
                  "Configure frf.12 fragmentation threshold";
              leaf threshold {
                type uint32 {
                  range "128..512";
                }
              } //threshold

            } //container ete-fragment-threshold

            leaf interleave {
              type boolean;
              description
                  "Enable/Disable frf-12 interleave";
            }

          } //container frf-12

        } //container frame-relay

        container ingress {
          description
              "Configure ingress policies";
          container aggregate-policer-rate {
            description
                "Specify aggregate policer rate and burst";
            leaf rate-in-kbps {
              type string;
              description
                  "Attribute rate-in-kbps for aggregate-policer-rate";
            } //rate-in-kbps

            leaf burst {
              type string;
              description
                  "[1..33292 | default]";
            } //burst

            leaf cir {
              type string;
              description
                  "Attribute cir-in-kbps for aggregate-policer-rate";
            } //cir

            leaf cbs {
              type string;
              description
                  "[1..33292 | default]";
            } //cbs

          } //container aggregate-policer-rate

          container filter {
            description
                "Apply ingress filter";
            leaf ip {
              type string;
              description
                  "[1..65535]|<name:64 char max>";
            } //ip

            leaf mac {
              type string;
              description
                  "[1..65535]|<name:64 char max>";
            } //mac

            leaf ipv6 {
              type string;
              description
                  "[1..65535]|<name:64 char max>";
            } //ipv6

          } //container filter

          container match-qinq-dot1p {
            description
                "Define 802.1P bits to match in QinQ SAP's";
            leaf top-bottom {
              type enumeration {
                enum top;
                enum bottom;
              }
            } //top-bottom

          } //container match-qinq-dot1p

          container policer-control-policy {
            description
                "Specify policer control policy";
            leaf policy-name {
              type string {
                length "1..32";
              }
            } //policy-name

          } //container policer-control-policy

          container qinq-vlan-translation {
            description
                "Apply Qinq Ingress Vlan Translation";
            leaf s-tag.c-tag {
              type string;
              description
                  "Attribute s-tag.c-tag for qinq-vlan-translation";
            } //s-tag.c-tag

          } //container qinq-vlan-translation

          list qos {
            key "policy-id";
            description
                "Apply ingress qos policy";
            leaf policy-id {
              type string;
              description
                  "[1..65535]|<name:64 char max>";
            } //policy-id

            leaf shared-queuing {
              type enumeration {
                enum shared-queuing;
              }
              description
                  "enables shared-queuing";
            } //shared-queuing

            leaf fp-redirect-group {
              type string {
                length "1..32";
              }
            } //fp-redirect-group

            leaf instance {
              type uint16 {
                range "1..65535";
              }
            } //instance

          } //list qos

          container scheduler-policy {
            description
                "Specify a scheduler-policy";
            leaf scheduler-policy-name {
              type string {
                length "1..32";
              }
            } //scheduler-policy-name

          } //container scheduler-policy

          container vlan-translation {
            description
                "Apply Ingress Vlan Translation";
            leaf t0..4094 {
              type uint32 {
                range "0..4094";
              }
            } //t0..4094

            leaf copy-outer {
              type boolean;
              description
                  "Keyword - Use outer vlan-id";
            } //copy-outer

          } //container vlan-translation

          container criteria-overrides {
            description
                "Configure sap ingress criteria overrides";
            container ip-criteria {
              presence
                  "Configure sap ingress ip criteria override";
              container activate-entry-tag {
                description
                    "Configure activate entry-tag id";
                leaf activate-entry-tag {
                  type uint32 {
                    range "1..255";
                  }
                } //activate-entry-tag

              } //container activate-entry-tag

            } //container ip-criteria

            container ipv6-criteria {
              presence
                  "Configure sap ingress ipv6 criteria override";
              container activate-entry-tag {
                description
                    "Configure activate entry-tagi-id";
                leaf activate-entry-tag {
                  type uint32 {
                    range "1..255";
                  }
                } //activate-entry-tag

              } //container activate-entry-tag

            } //container ipv6-criteria

          } //container criteria-overrides

          container policer-control-override {
            description
                "Configure policer control overrides";
            container max-rate {
              description
                  "Configure Max Rate override in kilobits-per-second";
              leaf rate {
                type string;
                description
                    "[1..6400000000|max] Kbps";
              } //rate

            } //container max-rate

            container priority-mbs-thresholds {
              description
                  "Configure priority mbs thresholds overrides";
              container min-thresh-separation {
                description
                    "configure min threshold separation override";
                leaf size {
                  type string;
                  description
                      "[0..16777216 default]";
                } //size

                leaf min-thresh-separation-id {
                  type enumeration {
                    enum bytes;
                    enum kilobytes;
                  }
                } //min-thresh-separation-id

              } //container min-thresh-separation

              list priority {
                key "level";
                description
                    "Configure Priority Levels overrides";
                leaf level {
                  type uint32 {
                    range "1..8";
                  }
                } //level

                container mbs-contribution {
                  description
                      "Configure mbs size override";
                  leaf size {
                    type string;
                    description
                        "[0..16777216 default]";
                  } //size

                  leaf mbs-contribution-id {
                    type enumeration {
                      enum bytes;
                      enum kilobytes;
                    }
                  } //mbs-contribution-id

                } //container mbs-contribution

              } //list priority

            } //container priority-mbs-thresholds

          } //container policer-control-override

          container policer-override {
            presence
                "Configure policer overrides";
            list policer {
              key "policer-id";
              description
                  "Configure overrides for the policer";
              leaf policer-id {
                type uint32 {
                  range "1..63";
                }
              } //policer-id

              container cbs {
                description
                    "Specify Cbs override";
                leaf size {
                  type string;
                  description
                      "[0..16777216 default]";
                } //size

                leaf bytes-kilobytes {
                  type enumeration {
                    enum bytes;
                    enum kilobytes;
                  }
                } //bytes-kilobytes

              } //container cbs

              container mbs {
                description
                    "Specify Mbs override";
                leaf size {
                  type string;
                  description
                      "[0..16777216 default]";
                } //size

                leaf bytes-kilobytes {
                  type enumeration {
                    enum bytes;
                    enum kilobytes;
                  }
                } //bytes-kilobytes

              } //container mbs

              container packet-byte-offset {
                description
                    "specify packet byte offset";
                leaf add {
                  type uint32 {
                    range "0..31";
                  }
                } //add

                leaf subtract {
                  type uint32 {
                    range "1..32";
                  }
                } //subtract

              } //container packet-byte-offset

              container percent-rate {
                description
                    "Specify percent rates (CIR and PIR) override";
                leaf pir-percent {
                  type string;
                  description
                      "[0.01..100.00]";
                } //pir-percent

                leaf cir {
                  type string;
                  description
                      "[0.00..100.00]";
                } //cir

              } //container percent-rate

              container rate {
                description
                    "Specify rates (CIR and PIR) override";
                leaf pir-rate {
                  type string;
                  description
                      "[1..6400000000|max] Kbps";
                } //pir-rate

                leaf cir {
                  type string;
                  description
                      "[0..6400000000|max] Kbps";
                } //cir

              } //container rate

              container stat-mode {
                description
                    "Specify Stat Mode for the policer";
                leaf stat-mode {
                  type enumeration {
                    enum no-stats;
                    enum minimal;
                    enum offered-profile-no-cir;
                    enum offered-priority-no-cir;
                    enum offered-profile-cir;
                    enum offered-priority-cir;
                    enum offered-total-cir;
                    enum offered-limited-profile-cir;
                    enum offered-profile-capped-cir;
                    enum offered-limited-capped-cir;
                  }
                } //stat-mode

              } //container stat-mode

            } //list policer

          } //container policer-override

          container qtag-manipulation {
            status "obsolete";
            presence
                "Configure VLAN Tag Manipulation";
            leaf preserve {
              type boolean;
              status "obsolete";
              description
                  "Preserve tags";
            }

            container push {
              status "obsolete";
              description
                  "Push tags";
              leaf qtag1.qtag2 {
                type string;
                description
                    "Attribute qtag1[.qtag2] for push";
              } //qtag1.qtag2

            } //container push

            container translate {
              status "obsolete";
              description
                  "Replace or pop tags";
              leaf t1-to-1-2-to-1-2-to-2 {
                type enumeration {
                  enum 1-to-1;
                  enum 2-to-1;
                  enum 2-to-2;
                }
                description
                    "keywords";
              } //t1-to-1-2-to-1-2-to-2

              leaf qtag1.qtag2 {
                type string;
                description
                    "Attribute qtag1[.qtag2] for translate";
              } //qtag1.qtag2

            } //container translate

          } //container qtag-manipulation

          container queue-override {
            presence
                "Apply queue override";
            list queue {
              key "queue-id";
              description
                  "Configure a queue override";
              leaf queue-id {
                type int32 {
                  range "1..32";
                }
              } //queue-id

              container adaptation-rule {
                description
                    "Specify the CIR and PIR adaptation rules";
                leaf pir {
                  type enumeration {
                    enum max;
                    enum min;
                    enum closest;
                  }
                } //pir

                leaf cir {
                  type enumeration {
                    enum max;
                    enum min;
                    enum closest;
                  }
                } //cir

              } //container adaptation-rule

              container cbs {
                description
                    "Specify CBS";
                leaf size-in-kbytes {
                  type string;
                  description
                      "Attribute size-in-kbytes for cbs";
                } //size-in-kbytes

              } //container cbs

              container high-prio-only {
                status "obsolete";
                description
                    "Specify high priority only burst size";
                leaf percent {
                  type string;
                  description
                      "[0..100 | default]";
                } //percent

              } //container high-prio-only

              container mbs {
                description
                    "Specify MBS";
                leaf size {
                  type string;
                  description
                      "Attribute size for mbs";
                } //size

                leaf bytes-kilobytes {
                  type enumeration {
                    enum bytes;
                    enum kilobytes;
                  }
                } //bytes-kilobytes

              } //container mbs

              leaf monitor-depth {
                type boolean;
                description
                    "Enable/Disable queue-depth monitoring";
              }

              container parent {
                description
                    "Specify the override weights for the queue within its parental scheduling 
                     context";
                leaf weight {
                  type uint32 {
                    range "0..100";
                  }
                } //weight

                leaf cir-weight {
                  type uint32 {
                    range "0..100";
                  }
                } //cir-weight

              } //container parent

              container percent-rate {
                description
                    "Specify percent rates (CIR and PIR)";
                leaf pir-percent {
                  type string;
                  description
                      "[0.01..100.00]";
                } //pir-percent

                leaf cir {
                  type string;
                  description
                      "[0.00..100.00]";
                } //cir

              } //container percent-rate

              container rate {
                description
                    "Specify rates (CIR and PIR)";
                leaf pir-rate {
                  type string;
                  description
                      "Attribute pir-rate for rate";
                } //pir-rate

                leaf cir {
                  type string;
                  description
                      "Attribute cir-rate for rate";
                } //cir

              } //container rate

              container drop-tail {
                description
                    "Specify drop tail";
                container low {
                  description
                      "Specify low drop-tail";
                  container percent-reduction-from-mbs {
                    description
                        "Specify low drop tail percent reduction from MBS";
                    leaf percent {
                      type string;
                      description
                          "[0..100|default]";
                    } //percent

                  } //container percent-reduction-from-mbs

                } //container low

              } //container drop-tail

            } //list queue

          } //container queue-override

          container scheduler-override {
            presence
                "Apply a scheduler override";
            list scheduler {
              key "scheduler-name";
              description
                  "Configure a scheduler override";
              leaf scheduler-name {
                type string {
                  length "1..32";
                }
              } //scheduler-name

              container parent {
                description
                    "Specify the override weights for the scheduler";
                leaf weight {
                  type uint32 {
                    range "0..100";
                  }
                } //weight

                leaf cir-weight {
                  type uint32 {
                    range "0..100";
                  }
                } //cir-weight

              } //container parent

              container rate {
                description
                    "Specify rates (CIR and PIR)";
                leaf pir-rate {
                  type string;
                  description
                      "[1..6400000000|max] Kbps";
                } //pir-rate

                leaf cir {
                  type string;
                  description
                      "[0..6400000000|sum|max] Kbps";
                } //cir

              } //container rate

            } //list scheduler

          } //container scheduler-override

          container vlan-manipulation {
            presence
                "Configure VLAN Tag Manipulation";
            leaf preserve {
              type boolean;
              description
                  "Preserve tags";
            }

            container push {
              description
                  "Push tags";
              leaf qtag1.qtag2 {
                type string;
                description
                    "Attribute qtag1[.qtag2] for push";
              } //qtag1.qtag2

            } //container push

            container translate {
              description
                  "Replace or pop tags";
              leaf t1-to-1-2-to-1-2-to-2 {
                type enumeration {
                  enum 1-to-1;
                  enum 2-to-1;
                  enum 2-to-2;
                }
                description
                    "keywords";
              } //t1-to-1-2-to-1-2-to-2

              leaf qtag1.qtag2 {
                type string;
                description
                    "Attribute qtag1[.qtag2] for translate";
              } //qtag1.qtag2

            } //container translate

          } //container vlan-manipulation

        } //container ingress

        container l2tpv3-session {
          description
              "Configure L2TPv3 session parameters";
          container pw-type {
            description
                "Configure pseudo-wire type";
            leaf ethernet {
              type boolean;
            } //ethernet

            leaf ethernet-vlan {
              type int32 {
                range "0..4095";
              }
            } //ethernet-vlan

          } //container pw-type

          container router {
            description
                "Configure L2TPv3 session router information";
            leaf router-instance {
              type string {
                length "1..32";
              }
              default "Base";
              description
                  "Attribute router-instance for router";
            } //router-instance

            leaf group {
              type string {
                length "1..32";
              }
            } //group

            leaf service-name {
              type string;
            } //service-name

          } //container router

          leaf shutdown {
            type boolean;
            description
                "Configure adminstrative state of the entry";
          }

          container vc-id {
            description
                "Configure VC identifier";
            leaf vc-id {
              type uint32 {
                range "1..4294967295";
              }
            } //vc-id

          } //container vc-id

        } //container l2tpv3-session

      } //list sap

      list site {
        key "name";
        description
            "Configure a Epipe site";
        leaf name {
          type string {
            length "1..32";
          }
        } //name

        container boot-timer {
          description
              "Configure/Override site boot-timer";
          leaf seconds {
            type int32 {
              range "0..600";
            }
          } //seconds

        } //container boot-timer

        container sap {
          description
              "Configure a SAP for the site";
          leaf sap-id {
            type string;
            description
                "Attribute sap-id for sap";
          } //sap-id

        } //container sap

        leaf shutdown {
          type boolean;
          description
              "Administratively enable/disable the site";
        }

        container site-activation-timer {
          description
              "Configure/Override site activation timer";
          leaf seconds {
            type int32 {
              range "0..100";
            }
          } //seconds

        } //container site-activation-timer

        container site-id {
          description
              "Configure site identifier";
          leaf value {
            type uint32 {
              range "1..65535";
            }
          } //value

        } //container site-id

        container site-min-down-timer {
          description
              "Configure minimum down timer for the site";
          leaf seconds {
            type int32 {
              range "0..100";
            }
          } //seconds

        } //container site-min-down-timer

        container site-preference {
          description
              "Configure site preference value";
          leaf preference-value {
            type uint32 {
              range "1..65535";
            }
          } //preference-value

        } //container site-preference

      } //list site

      list spoke-sdp {
        key "sdp-id-vc-id";
        description
            "Provision a spoke SDP binding";
        leaf sdp-id-vc-id {
          type string;
          description
              "sdp-id - [1..32767] 
               vc-id - [1..4294967295]";
        } //sdp-id-vc-id

        leaf vc-type {
          type enumeration {
            enum ether;
            enum vlan;
          }
          description
              "keywords";
        } //vc-type

        leaf endpoint {
          type string {
            length "1..32";
          }
        } //endpoint

        leaf no-endpoint {
          type boolean;
          description
              "keyword - used to remove an endpoint association";
        } //no-endpoint

        leaf icb {
          type boolean;
          description
              "keyword - configure spoke-sdp as inter-chassis backup";
        } //icb

        container aarp {
          description
              "Configure AARP instance id";
          leaf aarpId {
            type uint32 {
              range "1..65535";
            }
          } //aarpId

          leaf type {
            type enumeration {
              enum dual-homed;
              enum dual-homed-secondary;
            }
          } //type

        } //container aarp

        container accounting-policy {
          description
              "Configure accounting-policy to be used";
          leaf acct-policy-id {
            type uint64 {
              range "1..99";
            }
          } //acct-policy-id

        } //container accounting-policy

        container adv-service-mtu {
          description
              "Configure service-mtu";
          leaf adv-service-mtu-id {
            type uint32 {
              range "0..9782";
            }
          } //adv-service-mtu-id

        } //container adv-service-mtu

        container app-profile {
          description
              "Configure the application profile name";
          leaf app-profile-name {
            type string {
              length "1..32";
            }
          } //app-profile-name

        } //container app-profile

        container bandwidth {
          description
              "Configure the spoke-sdp bandwidth";
          leaf bw-value {
            type string;
            description
                "[0..100000000] Kbps";
          } //bw-value

          leaf max {
            type boolean;
          } //max

        } //container bandwidth

        leaf bfd-enable {
          type boolean;
          description
              "Enable/disable BFD";
        }

        container bfd-template {
          description
              "Configure BFD template";
          leaf bfd-template-string {
            type string {
            }
          } //bfd-template-string

        } //container bfd-template

        leaf block-on-peer-fault {
          type boolean;
          description
              "Enable/Disable block traffic on peer fault";
        }

        leaf collect-stats {
          type boolean;
          description
              "Enable/disable statistics collection";
        }

        leaf control-word {
          type boolean;
          description
              "Enable/disable setting the CW bit in the label message";
        }

        container cpu-protection {
          description
              "Configure CPU protection";
          leaf policy-id {
            type uint32 {
              range "1..255";
            }
          } //policy-id

          leaf mac-monitoring {
            type boolean;
            description
                "keyword - enable MAC monitoring";
          } //mac-monitoring

          leaf eth-cfm-monitoring {
            type boolean;
            description
                "keyword - enable Ethernet Connectivity Fault Management monitoring";
          } //eth-cfm-monitoring

          leaf aggregate {
            type boolean;
            description
                "keyword - apply the rate limit to the sum of the per peer packet rates";
          } //aggregate

          leaf car {
            type boolean;
            description
                "keyword - Committed Access Rate - ignore Eth-CFM packets when enforcing 
                 overall-rate";
          } //car

        } //container cpu-protection

        container description {
          description
              "Set description for spoke-sdp";
          leaf description-string {
            type string {
              length "1..80";
            }
            description
                "80 char max";
          } //description-string

        } //container description

        leaf entropy-label {
          type boolean;
          description
              "Enable/disable use of entropy-label";
        }

        container force-qinq-vc-forwarding {
          description
              "Forces qinq-vc-type forwarding in the data-path";
          leaf c-tag-c-tag---s-tag-c-tag {
            type enumeration {
              enum c-tag-c-tag;
              enum s-tag-c-tag;
            }
            description
                "c-tag-c-tag | s-tag-c-tag";
          } //c-tag-c-tag---s-tag-c-tag

        } //container force-qinq-vc-forwarding

        leaf force-vlan-vc-forwarding {
          type boolean;
          description
              "Forces vlan-vc-type forwarding in the data-path";
        }

        container hash-label {
          description
              "Enable/disable use of hash-label";
          leaf signal-capability {
            type boolean;
          } //signal-capability

        } //container hash-label

        container monitor-oper-group {
          description
              "Configure an Operational-Group to monitor";
          leaf group-name {
            type string {
              length "1..32";
            }
          } //group-name

        } //container monitor-oper-group

        container oper-group {
          description
              "Configure operational-group";
          leaf oper-name {
            type string {
              length "1..32";
            }
          } //oper-name

        } //container oper-group

        container precedence {
          description
              "Configure the spoke-sdp precedence";
          leaf precedence-value {
            type uint32 {
              range "1..4";
            }
          } //precedence-value

          leaf primary {
            type boolean;
            description
                "keyword - used to make this the primary spoke-sdp";
          } //primary

        } //container precedence

        leaf pw-status-signaling {
          type boolean;
          description
              "Enable/disable PW Status Signaling for spoke SDP binding";
        }

        leaf shutdown {
          type boolean;
          description
              "Administratively enable/disable the spoke SDP binding";
        }

        leaf standby-signaling-slave {
          type boolean;
          description
              "Enable PW standby-signaling slave";
        }

        container transit-policy {
          description
              "Configure transit policy id";
          leaf prefix {
            type uint32 {
              range "1..65535";
            }
          } //prefix

          leaf ip {
            type uint32 {
              range "1..65535";
            }
          } //ip

        } //container transit-policy

        leaf use-sdp-bmac {
          type boolean;
          description
              "Specify whether to use SDP Backbone MAC";
        }

        list vlan-vc-tag {
          key "vlan-id";
          description
              "Configure VLAN VC tag";
          leaf vlan-id {
            type uint32 {
              range "0..4094";
            }
          } //vlan-id

        } //list vlan-vc-tag

        container control-channel-status {
          description
              "Configure control channel status information";
          leaf acknowledgment {
            type boolean;
            description
                "Enable/disable acknowledgment";
          }

          container refresh-timer {
            description
                "Configure refresh timer";
            leaf seconds {
              type uint32 {
                range "10..65535";
              }
            } //seconds

          } //container refresh-timer

          container request-timer {
            description
                "Configure request-timer for the control channel status";
            leaf request-timer-secs {
              type uint32 {
                range "10..65535";
              }
            } //request-timer-secs

            leaf retry-timer {
              type uint32 {
                range "3..60";
              }
            } //retry-timer

            leaf timeout-multiplier {
              type uint32 {
                range "3..15";
              }
            } //timeout-multiplier

          } //container request-timer

          leaf shutdown {
            type boolean;
            description
                "Administratively enable/disable the control channel status";
          }

        } //container control-channel-status

        container egress {
          description
              "Spoke SDP egress configuration";
          container filter {
            description
                "Apply egress filter";
            leaf ip {
              type string;
              description
                  "[1..65535]|<name:64 char max>";
            } //ip

            leaf mac {
              type string;
              description
                  "[1..65535]|<name:64 char max>";
            } //mac

            leaf ipv6 {
              type string;
              description
                  "[1..65535]|<name:64 char max>";
            } //ipv6

          } //container filter

          list qos {
            key "network-policy-id";
            description
                "Configure egress qos";
            leaf network-policy-id {
              type uint32 {
                range "1..65535";
              }
            } //network-policy-id

            leaf port-redirect-group {
              type string {
                length "1..32";
              }
            } //port-redirect-group

            leaf instance {
              type uint16 {
                range "1..65535";
              }
            } //instance

          } //list qos

          list vc-label {
            key "egress-vc-label";
            description
                "Configure egress VC label";
            leaf egress-vc-label {
              type int32 {
                range "16..1048575";
              }
            } //egress-vc-label

          } //list vc-label

          container l2tpv3 {
            description
                "Configure L2TPv3 parameters";
            container cookie {
              description
                  "Configure cookie value for the tunnel";
              leaf t64-bit-value {
                type string;
                description
                    "xx-xx-xx-xx-xx-xx-xx-xx or xx:xx:xx:xx:xx:xx:xx:xx";
              } //t64-bit-value

            } //container cookie

          } //container l2tpv3

        } //container egress

        container eth-cfm {
          description
              "Configure CFM parameters";
          leaf collect-lmm-stats {
            type boolean;
            description
                "Enable/Disable the collection of statistics for OAM-PM Loss Measurement 
                 Message (LMM) tests";
          }

          list mip {
            key "primary-vlan-enable";
            description
                "Enable/Disable Maintenance Intermediate Points";
            leaf mac {
              type yang:mac-address;
            } //mac

            leaf default-mac {
              type boolean;
              description
                  "keyword - Use the default MAC address for the MIP";
            } //default-mac

            leaf primary-vlan-enable {
              type uint32 {
                range "1..4094";
              }
            } //primary-vlan-enable

          } //list mip

          container squelch-ingress-levels {
            description
                "Configure the level(s) of the ETH-CFM PDUs that will be silently discarded";
            leaf t0 {
              type boolean;
              description
                  "[0..7]";
            } //t0

            leaf t1 {
              type boolean;
            } //t1

            leaf t2 {
              type boolean;
            } //t2

            leaf t3 {
              type boolean;
            } //t3

            leaf t4 {
              type boolean;
            } //t4

            leaf t5 {
              type boolean;
            } //t5

            leaf t6 {
              type boolean;
            } //t6

            leaf t7 {
              type boolean;
            } //t7

          } //container squelch-ingress-levels

          container collect-lmm-fc-stats {
            description
                "Configure the collection of Forwarding Class (FC) aware statistics for OAM-PM 
                 Loss Measurement Message (LMM) tests";
            container fc {
              description
                  "Configure Forwarding Class (FC) counters without regard for profile";
              leaf-list fc-name {
                type enumeration {
                  enum be;
                  enum l2;
                  enum af;
                  enum l1;
                  enum h2;
                  enum ef;
                  enum h1;
                  enum nc;
                }
                max-elements 8;
              } //fc-name

            } //container fc

            container fc-in-profile {
              description
                  "Configure only in profile Forwarding Class (FC) counters";
              leaf-list fc-name {
                type enumeration {
                  enum be;
                  enum l2;
                  enum af;
                  enum l1;
                  enum h2;
                  enum ef;
                  enum h1;
                  enum nc;
                }
                max-elements 8;
              } //fc-name

            } //container fc-in-profile

          } //container collect-lmm-fc-stats

          list mep {
            key "mep-id domain association";
            description
                "Configure a CFM Maintenance Endpoint";
            leaf mep-id {
              type int16 {
                range "1..8191";
              }
              description
                  "Attribute mep-id for mep";
            } //mep-id

            leaf domain {
              type uint32 {
                range "1..4294967295";
              }
            } //domain

            leaf association {
              type uint32 {
                range "1..4294967295";
              }
            } //association

            leaf direction {
              type enumeration {
                enum up;
                enum down;
              }
              description
                  "keywords";
            } //direction

            leaf primary-vlan-enable {
              type boolean;
              description
                  "keyword - Provision MEP using MA primary vlan-id";
            } //primary-vlan-enable

            leaf ccm-enable {
              type boolean;
              description
                  "Enable/Disable Generation of CCM messages";
            }

            container ccm-ltm-priority {
              description
                  "Configure the priority of CCM and LTM messages";
              leaf priority {
                type uint16 {
                  range "0..7";
                }
                description
                    "[0..7] - Default highest priority on bridge-port";
              } //priority

            } //container ccm-ltm-priority

            container ccm-padding-size {
              description
                  "Insert additional padding in the CCM packets";
              leaf ccm-padding {
                type uint32 {
                  range "3..1500";
                }
                description
                    "3..1500 octets";
              } //ccm-padding

            } //container ccm-padding-size

            container description {
              description
                  "Add/remove a text description for the MEP";
              leaf description-string {
                type string {
                }
                description
                    "[80 chars max]";
              } //description-string

            } //container description

            container fault-propagation-enable {
              description
                  "Configure the Fault Propagation for the MEP";
              leaf use-if-tlv-suspend-ccm {
                type enumeration {
                  enum use-if-tlv;
                  enum suspend-ccm;
                }
                description
                    "keywords - use interface TLV, or suspend Continuity Check Messages";
              } //use-if-tlv-suspend-ccm

            } //container fault-propagation-enable

            leaf install-mep {
              type boolean;
              description
                  "Enable/Disable Installation of the MEP in the forwarding plane";
            }

            leaf lbm-svc-act-responder {
              type boolean;
              description
                  "Enable/Disable processing of service activation streams that may be 
                   encapsulated in the ETH-CFM request Loopback Message (LBM) on the MEP";
            }

            container low-priority-defect {
              description
                  "Configure the Lowest Priority Defect for the MEP";
              leaf allDef-macRemErrXcon-remErrXcon-errXcon-xcon-noXcon {
                type enumeration {
                  enum allDef;
                  enum macRemErrXcon;
                  enum remErrXcon;
                  enum errXcon;
                  enum xcon;
                  enum noXcon;
                }
                description
                    "keywords";
              } //allDef-macRemErrXcon-remErrXcon-errXcon-xcon-noXcon

            } //container low-priority-defect

            container mac-address {
              description
                  "Configure the MAC Address for the MEP";
              leaf mac-address {
                type yang:mac-address;
              } //mac-address

            } //container mac-address

            container one-way-delay-threshold {
              description
                  "Configure the one-way-delay test threshold";
              leaf seconds {
                type uint32 {
                  range "0..600";
                }
                default 3;
                description
                    "[0..600] Default: 3";
              } //seconds

            } //container one-way-delay-threshold

            leaf shutdown {
              type boolean;
              description
                  "Administratively enable/disable the MEP";
            }

            container ais-enable {
              presence
                  "Configure the generation and reception of Alarm Indication Signal (AIS) 
                   message parameters";
              container client-meg-level {
                description
                    "Configure the client meg level";
                leaf t1 {
                  type boolean;
                  description
                      "[1..7]";
                } //t1

                leaf t2 {
                  type boolean;
                } //t2

                leaf t3 {
                  type boolean;
                } //t3

                leaf t4 {
                  type boolean;
                } //t4

                leaf t5 {
                  type boolean;
                } //t5

                leaf t6 {
                  type boolean;
                } //t6

                leaf t7 {
                  type boolean;
                } //t7

              } //container client-meg-level

              leaf interface-support-enable {
                type boolean;
                description
                    "Enable/disable the generation of AIS PDUs based on the associated endpoint 
                     state";
              }

              container interval {
                description
                    "Configure the transmission interval of AIS messages";
                leaf t1-60 {
                  type enumeration {
                    enum 1;
                    enum 60;
                  }
                  default 1;
                  description
                      "seconds - Default: 1";
                } //t1-60

              } //container interval

              container low-priority-defect {
                description
                    "Configure the Lowest Priority Defect for the MEP AIS generation";
                leaf allDef-macRemErrXcon {
                  type enumeration {
                    enum allDef;
                    enum macRemErrXcon;
                  }
                  description
                      "keywords";
                } //allDef-macRemErrXcon

              } //container low-priority-defect

              container priority {
                description
                    "Configure the priority of AIS messages originated by the node";
                leaf priority-value {
                  type uint32 {
                    range "0..7";
                  }
                  default 7;
                  description
                      "[0..7] - Default: 7";
                } //priority-value

              } //container priority

            } //container ais-enable

            container alarm-notification {
              description
                  "Configure the MEP alarm notification parameters";
              container fng-alarm-time {
                description
                    "Configure the Fault Notification Generation (FNG) alarm time";
                leaf time {
                  type enumeration {
                    enum 0;
                    enum 250;
                    enum 500;
                    enum 1000;
                  }
                  default 0;
                  description
                      "[0,250,500,1000] centi-seconds - Default: 0";
                } //time

              } //container fng-alarm-time

              container fng-reset-time {
                description
                    "Configure the Fault Notification Generation (FNG) reset time";
                leaf time {
                  type enumeration {
                    enum 0;
                    enum 250;
                    enum 500;
                    enum 1000;
                  }
                  default 0;
                  description
                      "[0,250,500,1000] centi-seconds - Default: 0";
                } //time

              } //container fng-reset-time

            } //container alarm-notification

            container csf-enable {
              presence
                  "Configure the reception of Client Signal Fail (CSF) message parameters";
              container multiplier {
                description
                    "Configure the multiplier used for timing out CSF";
                leaf multiplier-value {
                  type string;
                  description
                      "[0.0|2.0 .. 30.0] - Default: 3.5";
                } //multiplier-value

              } //container multiplier

            } //container csf-enable

            container eth-test-enable {
              presence
                  "Enable/Disable eth-test functionality on MEP";
              container bit-error-threshold {
                description
                    "Configure the bit error trap threshold";
                leaf bit-errors {
                  type uint32 {
                    range "0..11840";
                  }
                  default 1;
                  description
                      "[0..11840] Default: 1";
                } //bit-errors

              } //container bit-error-threshold

              container test-pattern {
                description
                    "Configure the test pattern for eth-test frames";
                leaf all-zeros-all-ones {
                  type enumeration {
                    enum all-zeros;
                    enum all-ones;
                  }
                  default "all-zeros";
                  description
                      "keywords - Test pattern - default: all-zeros";
                } //all-zeros-all-ones

                leaf crc-enable {
                  type boolean;
                  description
                      "keyword - Generate CRC checksum";
                } //crc-enable

              } //container test-pattern

            } //container eth-test-enable

            container grace {
              description
                  "Configure the generation and reception of grace period parameters";
              container eth-ed {
                description
                    "Configure the generation and reception of eth-ed grace period parameters";
                container max-rx-defect-window {
                  description
                      "Configure/Disable an upper maximum defect window length; when disabled the 
                       advertised value from the peer will be used; when enabled the lower of the 
                       configured value or the advertised value from the peer will be used";
                  leaf seconds {
                    type uint32 {
                      range "1..86400";
                    }
                    description
                        "[1..86400] - Default: no max-rx-defect-window";
                  } //seconds

                } //container max-rx-defect-window

                container priority {
                  description
                      "Configure/Disable the transmission priority value for ETH-ED PDUs; when 
                       disabled the priority value of ccm-ltm-priority associated with this MEP will 
                       be used";
                  leaf priority {
                    type int32 {
                      range "0..7";
                    }
                    default 0;
                    description
                        "[0..7] - Default: no priority";
                  } //priority

                } //container priority

                leaf rx-eth-ed {
                  type boolean;
                  description
                      "Enable/Disable the receiving and processing of ETH-ED PDUs";
                }

                leaf tx-eth-ed {
                  type boolean;
                  description
                      "Enable/Disable the transmission of ETH-ED PDUs";
                }

              } //container eth-ed

              container eth-vsm-grace {
                description
                    "Configure the generation and reception of sros vendor specific message (vsm) 
                     grace period parameters";
                leaf rx-eth-vsm-grace {
                  type boolean;
                  description
                      "Enable/Disable the receiving and processing of vendor specific message (vsm) 
                       grace period notifications";
                }

                leaf tx-eth-vsm-grace {
                  type boolean;
                  description
                      "Enable/Disable the transmission of vsm grace period notifications";
                }

              } //container eth-vsm-grace

            } //container grace

          } //list mep

        } //container eth-cfm

        container ingress {
          description
              "Spoke SDP ingress configuration";
          container filter {
            description
                "Apply ingress filter";
            leaf ip {
              type string;
              description
                  "[1..65535]|<name:64 char max>";
            } //ip

            leaf mac {
              type string;
              description
                  "[1..65535]|<name:64 char max>";
            } //mac

            leaf ipv6 {
              type string;
              description
                  "[1..65535]|<name:64 char max>";
            } //ipv6

          } //container filter

          list qos {
            key "network-policy-id";
            description
                "Configure ingress qos";
            leaf network-policy-id {
              type uint32 {
                range "1..65535";
              }
            } //network-policy-id

            leaf fp-redirect-group {
              type string {
                length "1..32";
              }
            } //fp-redirect-group

            leaf instance {
              type uint16 {
                range "1..65535";
              }
            } //instance

          } //list qos

          list vc-label {
            key "ingress-vc-label";
            description
                "Configure ingress VC label";
            leaf ingress-vc-label {
              type string;
              description
                  "Attribute ingress-vc-label for vc-label";
            } //ingress-vc-label

          } //list vc-label

          container l2tpv3 {
            description
                "Configure L2TPv3 parameters";
            container cookie {
              description
                  "Configure cookie value for the tunnel";
              leaf cookie1-value {
                type string;
                description
                    "xx-xx-xx-xx-xx-xx-xx-xx or xx:xx:xx:xx:xx:xx:xx:xx";
              } //cookie1-value

              leaf cookie2-value {
                type string;
                description
                    "xx-xx-xx-xx-xx-xx-xx-xx or xx:xx:xx:xx:xx:xx:xx:xx";
              } //cookie2-value

            } //container cookie

          } //container l2tpv3

        } //container ingress

        container pw-path-id {
          presence
              "Configure PW path identifier information";
          container agi {
            description
                "Configure Attachment Group Identifier";
            leaf attachment-group-identifier {
              type string {
              }
              description
                  "<0..4294967295>:<0..4294967295>";
            } //attachment-group-identifier

          } //container agi

          container saii-type2 {
            description
                "Configure Source Attachment Individual Identifier (SAII)";
            leaf global-id-node-id-ac-id {
              type string {
              }
              description
                  "Attribute global-id:node-id:ac-id for saii-type2";
            } //global-id-node-id-ac-id

          } //container saii-type2

          container taii-type2 {
            description
                "Configure Target Attachment Individual Identifier (TAII)";
            leaf global-id-node-id-ac-id {
              type string {
              }
              description
                  "Attribute global-id:node-id:ac-id for taii-type2";
            } //global-id-node-id-ac-id

          } //container taii-type2

        } //container pw-path-id

      } //list spoke-sdp

      list spoke-sdp-fec {
        key "spoke-sdp-fec-id";
        description
            "Provision a spoke SDP FEC binding";
        leaf spoke-sdp-fec-id {
          type uint32 {
            range "1..4294967295";
          }
        } //spoke-sdp-fec-id

        leaf fec {
          type int32 {
            range "129..130";
          }
        } //fec

        leaf aii-type {
          type int32 {
            range "1..2";
          }
        } //aii-type

        leaf endpoint {
          type string {
            length "1..32";
          }
        } //endpoint

        leaf icb {
          type boolean;
          description
              "keyword - configure spoke-sdp as inter-chassis backup";
        } //icb

        leaf no-endpoint {
          type boolean;
        } //no-endpoint

        leaf auto-config {
          type boolean;
          description
              "Configure auto-configuration";
        }

        container path {
          description
              "Configure path-name";
          leaf name {
            type string {
              length "1..32";
            }
          } //name

        } //container path

        container precedence {
          description
              "Configure precedence";
          leaf prec-value {
            type int32 {
              range "0..4";
            }
          } //prec-value

          leaf primary {
            type boolean;
          } //primary

        } //container precedence

        container pw-template-bind {
          description
              "Configure Pseudo-Wire template-binding policy";
          leaf policy-id {
            type uint32 {
              range "1..2147483647";
            }
          } //policy-id

        } //container pw-template-bind

        container retry-count {
          description
              "Configure retry count";
          leaf retry-count {
            type int32 {
              range "10..10000";
            }
          } //retry-count

        } //container retry-count

        container retry-timer {
          description
              "Configure retry timer";
          leaf retry-timer {
            type int32 {
              range "10..480";
            }
          } //retry-timer

        } //container retry-timer

        container saii-type2 {
          description
              "Configure Source Attachment Individual Identifier (SAII)";
          leaf global-id-prefix-ac-id {
            type string {
            }
            description
                "Attribute global-id:prefix:ac-id for saii-type2";
          } //global-id-prefix-ac-id

        } //container saii-type2

        leaf shutdown {
          type boolean;
          description
              "Administratively enable/disable the spoke SDP FEC binding";
        }

        container signaling {
          description
              "Configure Spoke-SDP FEC signaling";
          leaf signaling {
            type enumeration {
              enum auto;
              enum master;
            }
          } //signaling

        } //container signaling

        leaf standby-signaling-slave {
          type boolean;
          description
              "Enable PW standby-signaling slave";
        }

        container taii-type2 {
          description
              "Configure Target Attachment Individual Identifier (TAII)";
          leaf global-id-prefix-ac-id {
            type string {
            }
            description
                "Attribute global-id:prefix:ac-id for taii-type2";
          } //global-id-prefix-ac-id

        } //container taii-type2

      } //list spoke-sdp-fec

      list vxlan {
        key "vni instance";
        description
            "Configure vxlan information";
        leaf vni {
          type uint32 {
            range "1..16777215";
          }
        } //vni

        leaf instance {
          type uint32 {
          }
        } //instance

        container egr-vtep {
          description
              "Configure vxlan egress vtep information";
          leaf ip-address-ipv6-address {
            type string;
            description
                "Attribute ip-address|ipv6-address for egr-vtep";
          } //ip-address-ipv6-address

          container oper-group {
            description
                "Configure operational group";
            leaf name {
              type string;
            } //name

          } //container oper-group

        } //container egr-vtep

      } //list vxlan

    } //list epipe

  } //grouping alu-conf-svc-epipe-r13

} //module  alu-conf-svc-epipe-r13
