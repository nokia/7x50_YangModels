module alu-conf-svc-upnp-r13 {
  yang-version "1";

  namespace "urn:alcatel-lucent.com:sros:ns:yang:conf-svc-upnp-r13";

  prefix "conf-svc-upnp-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Universal Plug 'n Play on SR OS 
       based routers. 
       
       Copyright 2014-2015 Alcatel-Lucent, 2016 Nokia. All rights reserved. 
       Reproduction of this document is authorized on the condition that the 
       foregoing copyright notice is included. 
       
       This alu-conf-svc-upnp-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-upnp-r13 {
    container upnp {
      description
          "Configure Universal Plug 'n Play";
      list upnp-policy {
        key "policy-name";
        description
            "Configure a UPnP policy";
        leaf policy-name {
          type string;
        } //policy-name

        container description {
          description
              "Configure a description for this policy";
          leaf description-string {
            type string {
              length "1..80";
            }
          } //description-string

        } //container description

        container http-listening-port {
          description
              "Configure the HTTP listening port";
          leaf http-listening-port-id {
            type uint16 {
              range "1..65535";
            }
          } //http-listening-port-id

        } //container http-listening-port

        container mapping-limit {
          description
              "Limit the number of UPnP mappings per subscriber";
          leaf mapping-limit-id {
            type uint16 {
              range "1..256";
            }
          } //mapping-limit-id

        } //container mapping-limit

        leaf strict-mode {
          type boolean;
          description
              "Restrict hosts to change their own mappings only";
        }

      } //list upnp-policy

    } //container upnp

  } //grouping alu-conf-svc-upnp-r13

} //module  alu-conf-svc-upnp-r13
