module alu-conf-port-mbundle-r13 {
  yang-version "1";

  namespace "urn:alcatel-lucent.com:sros:ns:yang:conf-port-mbundle-r13";

  prefix "conf-port-mbundle-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure multilink bundles on SR OS based 
       routers. 
       
       Copyright 2014-2015 Alcatel-Lucent, 2016 Nokia. All rights reserved. 
       Reproduction of this document is authorized on the condition that the 
       foregoing copyright notice is included. 
       
       This alu-conf-port-mbundle-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-port-mbundle-r13 {
    container multilink-bundle {
      description
          "Configure multilink bundles";
      container fragment-threshold {
        description
            "Configure the maximum bytes of a fragment transmitted across the multilink 
             bundle";
        leaf fragment-threshold {
          type uint32 {
            range "128..512";
          }
          description
              "128 to 512 bytes inclusive for MLPPP and MLFR bundles 
               128 bytes for IMA bundles";
        } //fragment-threshold

        leaf unlimited {
          type boolean;
          description
              "keyword - Disable fragmentation. Only applicable to MLPPP and MLFR bundles";
        } //unlimited

      } //container fragment-threshold

      leaf interleave-fragments {
        type boolean;
        description
            "enables or disables the LFI function on the given multilink bundle";
      }

      list member {
        key "port-id";
        description
            "Add a member port to the bundle";
        leaf port-id {
          type string {
            length "1..64";
          }
          description
              "slot/mda/port.channel";
        } //port-id

      } //list member

      container minimum-links {
        description
            "Configure the minimum links that must be active for the bundle to be active";
        leaf minimum-links {
          type int32 {
            range "1..8";
          }
        } //minimum-links

      } //container minimum-links

      container mrru {
        description
            "Configure the Maximum Received Reconstructed Unit";
        leaf mrru {
          type int32 {
            range "1500..9206";
          }
        } //mrru

      } //container mrru

      list protect-bundle {
        key "bundle-id";
        description
            "Configure the protection bundle that is part of this BPG";
        leaf bundle-id {
          type string {
          }
          description
              "Attribute bundle-id for protect-bundle";
        } //bundle-id

      } //list protect-bundle

      container red-differential-delay {
        description
            "Configure the maximum acceptable differential delay (in milliseconds) for 
             members";
        leaf red-diff-delay {
          type int32 {
            range "0..50";
          }
          description
              "[0..50] milliseconds for IMA bundles 
               [0..25] milliseconds for all other bundles";
        } //red-diff-delay

        leaf down {
          type boolean;
        } //down

      } //container red-differential-delay

      leaf short-sequence {
        type boolean;
        description
            "Enable/disable the use of short sequence by MLPPP bundles";
      }

      list working-bundle {
        key "bundle-id";
        description
            "Configure the working bundle that is part of this BPG";
        leaf bundle-id {
          type string {
          }
          description
              "Attribute bundle-id for working-bundle";
        } //bundle-id

      } //list working-bundle

      container yellow-differential-delay {
        description
            "Configure the yellow warning threshold (in milliseconds) of differential delay 
             for members";
        leaf yellow-diff-delay {
          type int32 {
            range "0..25";
          }
          description
              "[0..25] milliseconds";
        } //yellow-diff-delay

      } //container yellow-differential-delay

      container ima {
        description
            "Configure parameters for an IMA group";
        list link-delay {
          key "activate-deactivate";
          description
              "Time to delay after link activation/deactivation";
          leaf activate-deactivate {
            type enumeration {
              enum activate;
              enum deactivate;
            }
            description
                "keywords";
          } //activate-deactivate

          leaf milli-seconds {
            type uint32 {
              range "1..30000";
            }
            description
                "[1..30000] milli-seconds";
          } //milli-seconds

        } //list link-delay

        container max-bandwidth {
          description
              "Configure max bandwidth on this IMA group";
          leaf number-links {
            type uint32 {
              range "1..8";
            }
          } //number-links

        } //container max-bandwidth

        container version {
          description
              "Configure IMA version";
          leaf IMA-version {
            type enumeration {
              enum 1-0;
              enum 1-1;
            }
            description
                "1-0 - IMA version 1-0 
                 1-1 - IMA version 1-1";
          } //IMA-version

        } //container version

        container atm {
          description
              "configure ATM parameters for IMA bundle";
          container cell-format {
            description
                "Configure the ATM cell-format";
            leaf cell-format {
              type enumeration {
                enum uni;
                enum nni;
              }
              description
                  "keywords - uni|nni";
            } //cell-format

          } //container cell-format

          container min-vp-vpi {
            description
                "Configure the ATM minimum vpi";
            leaf value {
              type uint32 {
                range "0..4095";
              }
              description
                  "[0..4095] (NNI) 
                   [0..255] (UNI)";
            } //value

          } //container min-vp-vpi

        } //container atm

        container test-pattern-procedure {
          description
              "Configure test pattern procedure";
          leaf shutdown {
            type boolean;
            description
                "Enable/disable test pattern procedure";
          }

          container test-link {
            description
                "Configure IMA members to be used to verify link connectivity within an IMA 
                 group";
            leaf port-id {
              type string {
                length "1..64";
              }
              description
                  "Attribute port-id for test-link";
            } //port-id

          } //container test-link

          container test-pattern {
            description
                "Configure the test-pattern value to be used in ima group loopback location";
            leaf pattern {
              type uint32 {
                range "0..255";
              }
            } //pattern

          } //container test-pattern

        } //container test-pattern-procedure

      } //container ima

      container mlfr {
        description
            "Configure the Multi-link Frame Relay Bundle attributes";
        container ack-timeout {
          description
              "Configure time to wait to receive a hello message";
          leaf timer {
            type uint32 {
              range "1..10";
            }
            default 4;
            description
                "[1..10] seconds - Default: 4";
          } //timer

        } //container ack-timeout

        container hello-interval {
          description
              "Configure time interval between hello messages";
          leaf timer {
            type uint32 {
              range "1..180";
            }
            default 10;
            description
                "[1..180] seconds - Default: 10 seconds";
          } //timer

        } //container hello-interval

        container identifier {
          description
              "Configure frf.16 bundle identifier";
          leaf frf16-identifier {
            type string {
              length "1..49";
            }
          } //frf16-identifier

        } //container identifier

        container retry-limit {
          description
              "Configure number of ack-timeouts before taking action";
          leaf count {
            type uint32 {
              range "1..5";
            }
            default 2;
            description
                "[1..5] - Default: 2";
          } //count

        } //container retry-limit

        container egress {
          description
              "Configure egress mlfr parameters";
          container qos-profile {
            description
                "Configure egress mlfr qos-profile";
            leaf profile-id {
              type int32;
              description
                  "Attribute profile-id for qos-profile";
            } //profile-id

          } //container qos-profile

        } //container egress

        container frame-relay {
          description
              "Configure the Frame Relay parameters";
          container lmi-type {
            description
                "Configure the LMI type";
            leaf ansi-itu-none-rev1 {
              type enumeration {
                enum ansi;
                enum itu;
                enum none;
                enum rev1;
              }
              description
                  "keywords";
            } //ansi-itu-none-rev1

          } //container lmi-type

          container mode {
            description
                "Configure the DCE/DTE mode of the Frame Relay interface";
            leaf dce-dte-bidir {
              type enumeration {
                enum dce;
                enum dte;
                enum bidir;
              }
              description
                  "keywords";
            } //dce-dte-bidir

          } //container mode

          container n391dte {
            description
                "Configure the number of DTE full status polling intervals for the LMI";
            leaf intervals {
              type int32 {
                range "1..255";
              }
            } //intervals

          } //container n391dte

          container n392dce {
            description
                "Configure the DCE error threshold for the LMI";
            leaf threshold {
              type int32 {
                range "1..10";
              }
            } //threshold

          } //container n392dce

          container n392dte {
            description
                "Configure the DTE error threshold for the LMI";
            leaf threshold {
              type int32 {
                range "1..10";
              }
            } //threshold

          } //container n392dte

          container n393dce {
            description
                "Configure the DCE monitored event count for the LMI";
            leaf count {
              type int32 {
                range "1..10";
              }
            } //count

          } //container n393dce

          container n393dte {
            description
                "Configure the DTE monitored event count for the LMI";
            leaf count {
              type int32 {
                range "1..10";
              }
            } //count

          } //container n393dte

          container t391dte {
            description
                "Configure the DTE keepalive timer value for the LMI";
            leaf keepalive {
              type int32 {
                range "5..30";
              }
              description
                  "[5..30 seconds]";
            } //keepalive

          } //container t391dte

          container t392dce {
            description
                "Configure the DCE keepalive timer value for the LMI";
            leaf keepalive {
              type int32 {
                range "5..30";
              }
              description
                  "[5..30 seconds]";
            } //keepalive

          } //container t392dce

        } //container frame-relay

        container ingress {
          description
              "Configure ingress mlfr parameters";
          container qos-profile {
            description
                "Configure ingress mlfr qos-profile";
            leaf profile-id {
              type int32;
              description
                  "Attribute profile-id for qos-profile";
            } //profile-id

          } //container qos-profile

        } //container ingress

      } //container mlfr

      container mlppp {
        description
            "Configure the Multi-link PPP Bundle attributes";
        container endpoint-discriminator {
          description
              "Configure the mlppp endpoint discriminator";
          leaf class {
            type enumeration {
              enum ip-address;
              enum global-mac-address;
              enum null;
            }
            description
                "keywords";
          } //class

          leaf discriminator-id {
            type string {
              length "1..20";
            }
            description
                "string - [0..20 characters]";
          } //discriminator-id

        } //container endpoint-discriminator

        leaf magic-number {
          type boolean;
          description
              "Enable/Disable magic-number loopback detection";
        }

        container multiclass {
          description
              "Configure MLPPP Multiclass attributes";
          leaf count {
            type uint32 {
              range "2..4";
            }
          } //count

        } //container multiclass

        leaf stateless-aps-switchover {
          type boolean;
          description
              "Enable/Disable stateless APS switchover";
        }

        container egress {
          description
              "Configure egress mlppp parameters";
          container qos-profile {
            description
                "Configure egress mlppp qos-profile";
            leaf profile-id {
              type int32;
              description
                  "Attribute profile-id for qos-profile";
            } //profile-id

          } //container qos-profile

        } //container egress

        container ingress {
          description
              "Configure ingress mlppp parameters";
          container qos-profile {
            description
                "Configure ingress mlppp qos-profile";
            leaf profile-id {
              type int32;
              description
                  "Attribute profile-id for qos-profile";
            } //profile-id

          } //container qos-profile

        } //container ingress

      } //container mlppp

    } //container multilink-bundle

  } //grouping alu-conf-port-mbundle-r13

} //module  alu-conf-port-mbundle-r13
