module alu-conf-python-r13 {
  yang-version "1";

  namespace "urn:alcatel-lucent.com:sros:ns:yang:conf-python-r13";

  prefix "conf-python-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Python scripts on SR OS based 
       routers. 
       
       Copyright 2014-2015 Alcatel-Lucent, 2016 Nokia. All rights reserved. 
       Reproduction of this document is authorized on the condition that the 
       foregoing copyright notice is included. 
       
       This alu-conf-python-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-python-r13 {
    container python {
      description
          "Configure Python scripts";
      list python-policy {
        key "name";
        description
            "Configure Python policy to select which Python scripts must modify which 
             messages of different protocols";
        leaf name {
          type string {
            length "1..32";
          }
        } //name

        leaf wlan-gw-group {
          type uint32 {
            range "1..4";
          }
        } //wlan-gw-group

        leaf nat-group {
          type uint32 {
            range "1..4";
          }
        } //nat-group

        container description {
          description
              "Configure the description of this policy";
          leaf description-string {
            type string {
              length "1..80";
            }
          } //description-string

        } //container description

        list dhcp {
          key "type direction";
          description
              "Configure scripts to handle dhcp messages";
          leaf type {
            type enumeration {
              enum discover;
              enum offer;
              enum request;
              enum decline;
              enum ack;
              enum nak;
              enum release;
              enum inform;
              enum force-renew;
              enum lease-query;
              enum lease-unassigned;
              enum lease-unknown;
              enum lease-active;
            }
          } //type

          leaf direction {
            type enumeration {
              enum ingress;
              enum egress;
            }
          } //direction

          leaf script {
            type string {
              length "1..32";
            }
          } //script

        } //list dhcp

        list dhcp6 {
          key "type direction";
          description
              "Configure scripts to handle dhcp6 messages";
          leaf type {
            type enumeration {
              enum solicit;
              enum advertise;
              enum request;
              enum confirm;
              enum renew;
              enum rebind;
              enum reply;
              enum release;
              enum decline;
              enum reconfigure;
              enum info-request;
              enum relay-forward;
              enum relay-reply;
            }
          } //type

          leaf direction {
            type enumeration {
              enum ingress;
              enum egress;
            }
          } //direction

          leaf script {
            type string {
              length "1..32";
            }
          } //script

        } //list dhcp6

        list diameter {
          key "type direction";
          description
              "Configure scripts to handle diameter messages";
          leaf type {
            type enumeration {
              enum aaa;
              enum aar;
              enum asa;
              enum asr;
              enum cca;
              enum ccr;
              enum cea;
              enum cer;
              enum dpa;
              enum dpr;
              enum dwa;
              enum dwr;
              enum raa;
              enum rar;
            }
          } //type

          leaf direction {
            type enumeration {
              enum ingress;
              enum egress;
            }
          } //direction

          leaf script {
            type string {
              length "1..32";
            }
          } //script

        } //list diameter

        list gtpv1-c {
          key "type direction";
          description
              "Configure scripts to handle GTPv1-C messages";
          leaf type {
            type enumeration {
              enum echo-request;
              enum echo-response;
              enum version-not-supported;
              enum create-pdp-context-request;
              enum create-pdp-context-response;
              enum delete-pdp-context-request;
              enum delete-pdp-context-response;
              enum error-indication;
              enum end-marker;
            }
          } //type

          leaf direction {
            type enumeration {
              enum ingress;
              enum egress;
            }
          } //direction

          leaf script {
            type string {
              length "1..32";
            }
          } //script

        } //list gtpv1-c

        list gtpv2-c {
          key "type direction";
          description
              "Configure scripts to handle GTPv2-C messages";
          leaf type {
            type enumeration {
              enum echo-request;
              enum echo-response;
              enum version-not-supported;
              enum create-session-request;
              enum create-session-response;
              enum delete-session-request;
              enum delete-session-response;
              enum delete-bearer-request;
              enum delete-bearer-response;
              enum modify-bearer-request;
              enum modify-bearer-response;
              enum release-access-bearers-request;
              enum release-access-bearers-response;
              enum downlink-data-notification;
              enum downlink-data-notification-ack;
              enum change-notification-request;
              enum change-notification-response;
              enum stop-paging-indication;
            }
          } //type

          leaf direction {
            type enumeration {
              enum ingress;
              enum egress;
            }
          } //direction

          leaf script {
            type string {
              length "1..32";
            }
          } //script

        } //list gtpv2-c

        list pppoe {
          key "type direction";
          description
              "Configure scripts to handle PPPoE messages";
          leaf type {
            type enumeration {
              enum session-lcp;
              enum session-pap;
              enum session-chap;
              enum session-ipcp;
              enum session-ip6cp;
              enum pado;
              enum padi;
              enum padr;
              enum pads;
              enum padt;
            }
          } //type

          leaf direction {
            type enumeration {
              enum ingress;
              enum egress;
            }
          } //direction

          leaf script {
            type string;
          } //script

        } //list pppoe

        list radius {
          key "type direction";
          description
              "Configure scripts to handle RADIUS messages";
          leaf type {
            type enumeration {
              enum access-request;
              enum access-accept;
              enum access-reject;
              enum accounting-request;
              enum accounting-response;
              enum access-challenge;
              enum disconnect-request;
              enum change-of-authorization-request;
            }
          } //type

          leaf direction {
            type enumeration {
              enum ingress;
              enum egress;
            }
          } //direction

          leaf script {
            type string {
              length "1..32";
            }
          } //script

        } //list radius

        container syslog {
          description
              "Configure a script to handle outgoing syslog messages";
          leaf script {
            type string;
          } //script

        } //container syslog

        container vsd {
          description
              "Configure scripts to handle VSD messages";
          leaf script {
            type string {
              length "1..32";
            }
          } //script

        } //container vsd

        container cache {
          description
              "Configure the limits of the caching API inside the Python scripts";
          container entry-size {
            description
                "Configure the maximum accepted size of a single cache entry";
            leaf size {
              type uint32 {
                range "32..2048";
              }
            } //size

          } //container entry-size

          container max-entries {
            description
                "Configure the maximum number of cache entries allowed";
            leaf count {
              type uint32 {
                range "1..1000000";
              }
            } //count

          } //container max-entries

          container max-entry-lifetime {
            description
                "Configure the maximum lifetime that can be set on a cache entry";
            leaf days {
              type uint8 {
                range "0..7";
              }
            } //days

            leaf hrs {
              type uint8 {
                range "0..23";
              }
            } //hrs

            leaf min {
              type uint8 {
                range "0..59";
              }
            } //min

            leaf sec {
              type uint8 {
                range "0..59";
              }
            } //sec

          } //container max-entry-lifetime

          container mcs-peer {
            description
                "Configure the Multi-chassis redundancy synchronization peer and optional tag";
            leaf ip-address {
              type string;
              description
                  "Attribute ip-address for mcs-peer";
            } //ip-address

            leaf sync-tag {
              type string {
                length "1..32";
              }
            } //sync-tag

          } //container mcs-peer

          leaf persistence {
            type boolean;
            description
                "Enable/disable cache persistence";
          }

          leaf shutdown {
            type boolean;
            description
                "Enable/disable the Python cache";
          }

          container minimum-lifetimes {
            presence
                "Configure minimum lifetimes for cache entries to be protected by 
                 synchronization or persistence";
            container high-availability {
              description
                  "Configure the minimum lifetime for a cache entry to be synchronized with the 
                   stand-by CPM";
              leaf seconds {
                type uint32 {
                  range "1..600";
                }
              } //seconds

            } //container high-availability

            container multi-chassis-redundancy {
              description
                  "Configure the minimum lifetime for a cache entry to be synchronized with the 
                   MCS peer";
              leaf seconds {
                type uint32 {
                  range "1..600";
                }
              } //seconds

            } //container multi-chassis-redundancy

            container persistence {
              description
                  "Configure the minimum lifetime for a cache entry to be made persistent";
              leaf seconds {
                type uint32 {
                  range "1..1800";
                }
              } //seconds

            } //container persistence

          } //container minimum-lifetimes

        } //container cache

      } //list python-policy

      list python-script {
        key "name";
        description
            "Configure Python scripts to modify messages of different protocols";
        leaf name {
          type string {
            length "1..32";
          }
        } //name

        container action-on-fail {
          description
              "Action taken on script failure";
          leaf action-on-fail-id {
            type enumeration {
              enum drop;
              enum passthrough;
            }
          } //action-on-fail-id

        } //container action-on-fail

        container description {
          description
              "Configure the description of this script";
          leaf description-string {
            type string {
              length "1..80";
            }
          } //description-string

        } //container description

        container primary-url {
          description
              "Configure the primary URL of the Python script";
          leaf url {
            type string {
              length "1..180";
            }
          } //url

        } //container primary-url

        container protection {
          description
              "Configure how the content of the Python script is protected";
          leaf none {
            type boolean;
          } //none

          leaf hmac-sha256 {
            type boolean;
          } //hmac-sha256

          leaf key {
            type string {
              length "1..500";
            }
            description
                "secret-key - [128 chars max] 
                 hash-key 
                 hash2-key 
                 custom-key";
          } //key

          leaf hash-hash2-custom {
            type enumeration {
              enum hash;
              enum hash2;
              enum custom;
            }
            description
                "keywords - specify hashing scheme";
          } //hash-hash2-custom

        } //container protection

        container secondary-url {
          description
              "Configure the secondary URL of the Python script";
          leaf url {
            type string {
            }
          } //url

        } //container secondary-url

        leaf shutdown {
          type boolean;
          description
              "Enable/disable script execution";
        }

        container tertiary-url {
          description
              "Configure the tertiary URL of the Python script";
          leaf url {
            type string {
            }
          } //url

        } //container tertiary-url

      } //list python-script

    } //container python

  } //grouping alu-conf-python-r13

} //module  alu-conf-python-r13
