module alu-conf-svc-vpls-igmp-r13 {
  yang-version "1";

  namespace "urn:alcatel-lucent.com:sros:ns:yang:conf-svc-vpls-igmp-r13";

  prefix "conf-svc-vpls-igmp-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure IGMP snooping parameters on SR OS 
       based routers. 
       
       Copyright 2014-2015 Alcatel-Lucent, 2016 Nokia. All rights reserved. 
       Reproduction of this document is authorized on the condition that the 
       foregoing copyright notice is included. 
       
       This alu-conf-svc-vpls-igmp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-06-09";

  grouping alu-conf-svc-vpls-igmp-r13 {
    container igmp-snooping {
      description
          "Configure IGMP snooping parameters";
      container query-interval {
        description
            "Configure the IGMP Query Interval for v1/v2 Queriers";
        leaf seconds {
          type uint32 {
            range "1..65535";
          }
        } //seconds

      } //container query-interval

      container query-src-ip {
        description
            "Configure the IP source address used in IGMP queries";
        leaf ip-address {
          type inet:ip-address;
        } //ip-address

      } //container query-src-ip

      container report-src-ip {
        description
            "Configure the IP source address used in IGMP reports";
        leaf ip-address {
          type inet:ip-address;
        } //ip-address

      } //container report-src-ip

      container robust-count {
        description
            "Configure the IGMP Robustness Variable for v1/v2 Queriers";
        leaf robust-count {
          type uint32 {
            range "1..255";
          }
        } //robust-count

      } //container robust-count

      leaf shutdown {
        type boolean;
        description
            "Administratively enable or disable IGMP snooping";
      }

      container mvr {
        description
            "Configure Multicast VPLS Registration parameters";
        container description {
          description
              "Description for this MVR";
          leaf description-string {
            type string {
              length "1..80";
            }
          } //description-string

        } //container description

        container group-policy {
          description
              "Policy to select groups for this MVR";
          leaf policy-name {
            type string {
              length "1..32";
            }
          } //policy-name

        } //container group-policy

        leaf shutdown {
          type boolean;
          description
              "Administratively enable or disable MVR";
        }

      } //container mvr

    } //container igmp-snooping

  } //grouping alu-conf-svc-vpls-igmp-r13

} //module  alu-conf-svc-vpls-igmp-r13
