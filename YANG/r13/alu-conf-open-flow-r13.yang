module alu-conf-open-flow-r13 {
  yang-version "1";

  namespace "urn:alcatel-lucent.com:sros:ns:yang:conf-open-flow-r13";

  prefix "conf-open-flow-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure OpenFlow on SR OS based routers. 
       
       Copyright 2014-2015 Alcatel-Lucent, 2016 Nokia. All rights reserved. 
       Reproduction of this document is authorized on the condition that the 
       foregoing copyright notice is included. 
       
       This alu-conf-open-flow-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-10-16";

  grouping alu-conf-open-flow-r13 {
    container open-flow {
      description
          "Configure OpenFlow";
      container of-controller {
        presence
            "Configure Open-Flow Controller";
        container address {
          description
              "Configure Open-Flow Controller IP address";
          leaf ip-address {
            type inet:ip-address;
          } //ip-address

          leaf port {
            type int32 {
              range "1..65535";
            }
          } //port

        } //container address

        container description {
          description
              "Description for this Open-Flow Controller";
          leaf description-string {
            type string {
              length "1..80";
            }
          } //description-string

        } //container description

        container echo-interval {
          description
              "Configure Echo Request Interval for Open-Flow Controller";
          leaf seconds {
            type uint16 {
              range "10..3600";
            }
            default 10;
            description
                "[10..3600]";
          } //seconds

        } //container echo-interval

        container echo-multiple {
          description
              "Configure Echo-Multiple for Open-Flow Controller";
          leaf value {
            type uint16 {
              range "3..100";
            }
            default 3;
            description
                "[3..100]";
          } //value

        } //container echo-multiple

        container ipv6-address {
          description
              "Configure Open-Flow Controller IPv6 address";
          leaf ipv6-address {
            type inet:ipv6-address;
            description
                "Attribute ipv6-address for ipv6-address";
          } //ipv6-address

        } //container ipv6-address

        container role {
          description
              "Configure Role for Open-Flow Controller";
          leaf equal {
            type enumeration {
              enum equal;
            }
          } //equal

        } //container role

        leaf shutdown {
          type boolean;
          description
              "Shutdown Open-Flow Controller instance";
        }

        container tls-server-profile {
          description
              "Configure Open-Flow Controller TLS Server Profile Name";
          leaf profile-name {
            type string;
          } //profile-name

        } //container tls-server-profile

        container version {
          description
              "Configure Version for Open-Flow Controller";
          leaf version-number {
            type uint32 {
            }
            description
                "[4]";
          } //version-number

        } //container version

      } //container of-controller

      list of-switch {
        key "ofs-name";
        description
            "Configure open-flow switch";
        leaf ofs-name {
          type string;
        } //ofs-name

        leaf ofs-id {
          type uint32 {
            range "1..8";
          }
        } //ofs-id

        leaf aux-channel-enable {
          type boolean;
          description
              "Enable/Disable auxiliary channel";
        }

        list controller {
          key "ip-address-port";
          status "obsolete";
          description
              "Configure controller IP address and port";
          leaf ip-address-port {
            type string;
            description
                "ip-address - a.b.c.d 
                 port - [1..65535]";
          } //ip-address-port

        } //list controller

        container description {
          description
              "Description for this open-flow switch";
          leaf description-string {
            type string {
              length "1..255";
            }
          } //description-string

        } //container description

        container echo-interval {
          description
              "Configure Echo Request Interval";
          leaf seconds {
            type uint16 {
              range "1..3600";
            }
            description
                "[1..3600]";
          } //seconds

        } //container echo-interval

        container echo-multiple {
          description
              "Configure echo-multiple";
          leaf value {
            type uint16 {
              range "3..100";
            }
            description
                "[3..100]";
          } //value

        } //container echo-multiple

        list logical-port-status {
          key "rsvp-te-mpls-tp-sr-te";
          description
              "Configure reporting of Logical Ports";
          leaf rsvp-te-mpls-tp-sr-te {
            type enumeration {
              enum rsvp-te;
              enum mpls-tp;
              enum sr-te;
            }
          } //rsvp-te-mpls-tp-sr-te

        } //list logical-port-status

        leaf shutdown {
          type boolean;
          description
              "Shutdown open-flow switch instance";
        }

        list flowtable {
          key "of-table-id";
          description
              "Configure open-flow Flow-Table";
          leaf of-table-id {
            type uint16 {
            }
          } //of-table-id

          container max-size {
            description
                "Configure flow-table max-size";
            leaf size {
              type string;
              description
                  "Attribute size for max-size";
            } //size

          } //container max-size

          container no-match-action {
            description
                "Configure no-match action";
            leaf action {
              type enumeration {
                enum drop;
                enum fall-through;
                enum packet-in;
              }
            } //action

          } //container no-match-action

          leaf switch-defined-cookie {
            type boolean;
            description
                "Enable/Disable switch defined cookie";
          }

        } //list flowtable

        list of-controller {
          key "ip-address-port";
          description
              "Configure switch controller IP address and port";
          leaf ip-address-port {
            type string;
            description
                "Attribute ip-address:port for of-controller";
          } //ip-address-port

          container tls-client-profile {
            description
                "Configure Open-Flow Switch Controller TLS Client Profile Name.";
            leaf profile-name {
              type string;
            } //profile-name

          } //container tls-client-profile

          container vprn {
            description
                "Configure vprn service id for OpenFlow Switch Controller.";
            leaf service-id {
              type uint32 {
                range "1..2147483647";
              }
            } //service-id

            leaf ofc-loopback {
              type inet:ip-address;
              description
                  "Attribute ip-address for vprn";
            } //ofc-loopback

            leaf name {
              type string {
                length "1..64";
              }
              description
                  "64-char max";
            } //name

          } //container vprn

        } //list of-controller

      } //list of-switch

    } //container open-flow

  } //grouping alu-conf-open-flow-r13

} //module  alu-conf-open-flow-r13
