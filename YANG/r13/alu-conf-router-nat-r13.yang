module alu-conf-router-nat-r13 {
  yang-version "1";

  namespace "urn:alcatel-lucent.com:sros:ns:yang:conf-router-nat-r13";

  prefix "conf-router-nat-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure NAT on SR OS based routers. 
       
       Copyright 2014-2015 Alcatel-Lucent, 2016 Nokia. All rights reserved. 
       Reproduction of this document is authorized on the condition that the 
       foregoing copyright notice is included. 
       
       This alu-conf-router-nat-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-09-15";

  grouping alu-conf-router-nat-r13 {
    container nat {
      presence
          "Configure NAT";
      container inside {
        description
            "Configure the inside NAT";
        container classic-lsn-max-subscriber-limit {
          description
              "Configure the maximum value allowed as subscriber-limit in each 
               (deterministic) pool used for Classic LSN";
          leaf max {
            type uint32 {
              range "1..32768";
            }
            description
                "1,2,4,8,...32768";
          } //max

        } //container classic-lsn-max-subscriber-limit

        list destination-prefix {
          key "ip-prefix-length";
          description
              "Configure a destination prefix";
          leaf ip-prefix-length {
            type inet:ip-prefix;
            description
                "ip-prefix a.b.c.d (host bits must be 0) 
                 length [0..32]";
          } //ip-prefix-length

          leaf nat-policy {
            type string {
              length "1..32";
            }
          } //nat-policy

        } //list destination-prefix

        container dslite-max-subscriber-limit {
          description
              "Configure the maximum value allowed as subscriber-limit in each 
               (deterministic) pool used for Dual Stack Lite LSN";
          leaf max {
            type uint32 {
              range "1..32768";
            }
            description
                "1,2,4,8,...32768";
          } //max

        } //container dslite-max-subscriber-limit

        container nat-policy {
          description
              "Configure the NAT policy";
          leaf nat-policy-name {
            type string {
              length "1..32";
            }
          } //nat-policy-name

        } //container nat-policy

        container deterministic {
          description
              "Configure Deterministic NAT";
          container classic-lsn-max-subscriber-limit {
            status "obsolete";
            description
                "Configure the maximum value allowed as subscriber-limit in each 
                 (deterministic) pool used for Classic LSN";
            leaf max {
              type uint32 {
                range "1..32768";
              }
              description
                  "1,2,4,8,...32768";
            } //max

          } //container classic-lsn-max-subscriber-limit

          container dslite-max-subscriber-limit {
            status "obsolete";
            description
                "Configure the maximum value allowed as subscriber-limit in each 
                 (deterministic) pool used for Dual Stack Lite LSN";
            leaf max {
              type uint32 {
                range "1..32768";
              }
              description
                  "1,2,4,8,...32768";
            } //max

          } //container dslite-max-subscriber-limit

          list prefix {
            key "ip-prefix-ip-prefix-length subscriber-type";
            description
                "Configure a subscriber source IP address prefix and its NAT policy";
            leaf ip-prefix-ip-prefix-length {
              type string {
                length "1..64";
              }
              description
                  "Attribute ip-prefix/ip-prefix-length for prefix";
            } //ip-prefix-ip-prefix-length

            leaf subscriber-type {
              type enumeration {
                enum classic-lsn-sub;
                enum dslite-lsn-sub;
              }
            } //subscriber-type

            leaf nat-policy {
              type string;
            } //nat-policy

            list map {
              key "start end";
              description
                  "Map a NAT subscriber range to an outside address range";
              leaf start {
                type string {
                  length "1..64";
                }
                description
                    "Attribute lsn-sub-address for map";
              } //start

              leaf end {
                type string {
                  length "1..64";
                }
                description
                    "lsn-sub-address";
              } //end

              leaf to {
                type inet:ip-address;
                description
                    "a.b.c.d";
              } //to

            } //list map

            leaf shutdown {
              type boolean;
              description
                  "Enable/disable this prefix";
            }

          } //list prefix

        } //container deterministic

        container dnat-only {
          description
              "Configure Destination NAT while Source Network Address and Port Translation is 
               not being done";
          container source-prefix-list {
            description
                "Configure the NAT prefix list that defines the upstream traffic flows subject 
                 to Destination NAT only";
            leaf prefix-list-name {
              type string;
            } //prefix-list-name

          } //container source-prefix-list

        } //container dnat-only

        container dual-stack-lite {
          description
              "Configure Dual-Stack-Lite NAT";
          leaf shutdown {
            type boolean;
            description
                "Administratively enable or disable the operation of dual-stack-lite";
          }

          container subscriber-prefix-length {
            description
                "Configure the IPv6 prefix length of the dual-stack-lite subscribers";
            leaf prefix-length {
              type uint8 {
                range "32..128";
              }
              description
                  "[32..64] | 128";
            } //prefix-length

          } //container subscriber-prefix-length

          list address {
            key "ipv6-address";
            description
                "Configure a dual-stack-lite address";
            leaf ipv6-address {
              type inet:ipv6-address;
              description
                  "Attribute ipv6-address for address";
            } //ipv6-address

            container ip-fragmentation {
              description
                  "Configure fragmentation of payload IP datagrams";
              leaf ip-fragmentation-id {
                type enumeration {
                  enum disabled;
                  enum fragment-ipv6;
                  enum fragment-ipv6-unless-ipv4-df-set;
                }
              } //ip-fragmentation-id

            } //container ip-fragmentation

            leaf reassembly {
              type boolean;
              description
                  "Enable or disable reassembly";
            }

            container tunnel-mtu {
              description
                  "Configure the dual-stack-lite tunnel MTU";
              leaf mtu-bytes {
                type uint32 {
                  range "512..9212";
                }
              } //mtu-bytes

            } //container tunnel-mtu

          } //list address

        } //container dual-stack-lite

        container l2-aware {
          description
              "Configure layer-2-aware NAT";
          list address {
            key "ip-address-mask";
            description
                "Configure a layer-2-aware NAT address";
            leaf ip-address-mask {
              type string;
              description
                  "ip-address a.b.c.d 
                   mask [16..32]";
            } //ip-address-mask

          } //list address

        } //container l2-aware

        container nat64 {
          presence
              "Configure NAT64";
          leaf drop-zero-ipv4-checksum {
            type boolean;
            description
                "Drop UDP datagrams with zero IPv4 checksum";
          }

          leaf ignore-tos {
            type boolean;
            description
                "Ignore the IPv4 Type Of Service (TOS) is ignored and set the IPv6 Traffic 
                 Class bits to zero";
          }

          leaf insert-ipv6-fragment-header {
            type boolean;
            description
                "Always insert an IPv6 fragment header, to indicate that the sender allows 
                 fragmentation";
          }

          container ip-fragmentation {
            description
                "Configure fragmentation of IP datagrams";
            leaf ip-fragmentation-id {
              type enumeration {
                enum disabled;
                enum fragment-ipv6;
                enum fragment-ipv6-unless-ipv4-df-set;
              }
            } //ip-fragmentation-id

          } //container ip-fragmentation

          container ipv6-mtu {
            description
                "Configure the IPv6 MTU";
            leaf ipv6-mtu-id {
              type uint32 {
                range "1280..9212";
              }
            } //ipv6-mtu-id

          } //container ipv6-mtu

          container prefix {
            description
                "Configure the NAT64 destination prefix";
            leaf ipv6-prefix-prefix-length {
              type string;
              description
                  "Attribute ipv6-prefix/prefix-length for prefix";
            } //ipv6-prefix-prefix-length

          } //container prefix

          container set-tos {
            description
                "Ignore the IPv6 Traffic Class is ignored and set the IPv4 TOS to a fixed value";
            leaf set-tos-id {
              type uint8;
            } //set-tos-id

          } //container set-tos

          leaf shutdown {
            type boolean;
            description
                "Enable/disable NAT64";
          }

          container subscriber-prefix-length {
            description
                "Configure the IPv6 prefix length for the NAT64 subscribers";
            leaf prefix-length {
              type uint8 {
                range "32..128";
              }
              description
                  "[32..64] | 128";
            } //prefix-length

          } //container subscriber-prefix-length

        } //container nat64

        container redundancy {
          description
              "Configure redundancy";
          container peer {
            description
                "Configure the peer";
            leaf ip-address {
              type inet:ip-address;
              description
                  "a.b.c.d";
            } //ip-address

          } //container peer

          container peer6 {
            description
                "Configure the peer for IPv6";
            leaf ipv6-address {
              type inet:ipv6-address;
              description
                  "Attribute ipv6-address for peer6";
            } //ipv6-address

          } //container peer6

          container steering-route {
            description
                "Configure the steering route";
            leaf ip-prefix-length {
              type inet:ip-prefix;
              description
                  "Attribute ip-prefix/length for steering-route";
            } //ip-prefix-length

          } //container steering-route

        } //container redundancy

        container subscriber-identification {
          description
              "Configure subscriber identification for Large Scale NAT";
          container attribute {
            description
                "Configure the RADIUS attribute to be used as subscriber identifier";
            leaf vendor {
              type string {
                length "1..32";
              }
              default "nokia";
              description
                  "Attribute vendor-id for attribute";
            } //vendor

            leaf attribute-type {
              type string {
                length "1..32";
              }
            } //attribute-type

          } //container attribute

          container description {
            description
                "Describe this configuration";
            leaf description-string {
              type string {
                length "1..80";
              }
            } //description-string

          } //container description

          leaf drop-unidentified-traffic {
            type boolean;
            description
                "Enable/disable dropping traffic from unidentified flows";
          }

          container radius-proxy-server {
            description
                "Configure the RADIUS Proxy server to use";
            leaf router {
              type string {
                length "1..32";
              }
              default "Base";
              description
                  "Attribute router-instance for radius-proxy-server";
            } //router

            leaf name {
              type string {
                length "1..32";
              }
            } //name

          } //container radius-proxy-server

          leaf shutdown {
            type boolean;
            description
                "Enable/disable subscriber identification";
          }

        } //container subscriber-identification

      } //container inside

      container map {
        description
            "Configure Mapping of Address and Port with Translation (MAP-T)";
        list map-domain {
          key "domain-name";
          description
              "Configure the MAP domain";
          leaf domain-name {
            type string;
          } //domain-name

        } //list map-domain

      } //container map

      container outside {
        description
            "Configure the outside NAT";
        container downstream-ip-filter {
          description
              "Configure the ip-filter for downstream traffic";
          leaf ip-filter-id {
            type string;
            description
                "Attribute ip-filter-id for downstream-ip-filter";
          } //ip-filter-id

        } //container downstream-ip-filter

        container downstream-ipv6-filter {
          description
              "Configure the ipv6-filter for downstream traffic";
          leaf ipv6-filter-id {
            type string;
            description
                "Attribute ipv6-filter-id for downstream-ipv6-filter";
          } //ipv6-filter-id

        } //container downstream-ipv6-filter

        container mtu {
          description
              "Configure the MTU for downstream traffic";
          leaf mtu-id {
            type uint32 {
              range "512..9000";
            }
          } //mtu-id

        } //container mtu

        container upstream-ip-filter {
          description
              "Configure the ip-filter for upstream traffic";
          leaf ip-filter-id {
            type string;
            description
                "Attribute ip-filter-id for upstream-ip-filter";
          } //ip-filter-id

        } //container upstream-ip-filter

        container upstream-ipv6-filter {
          description
              "Configure the ipv6-filter for upstream traffic";
          leaf ipv6-filter-id {
            type string;
            description
                "Attribute ipv6-filter-id for upstream-ipv6-filter";
          } //ipv6-filter-id

        } //container upstream-ipv6-filter

        container dnat-only {
          description
              "Configure Destination NAT while Source Network Address and Port Translation is 
               not being done";
          container route-limit {
            description
                "Limit the number of internal routes for downstream traffic";
            leaf route-limit-id {
              type uint32 {
                range "1..131072";
              }
            } //route-limit-id

          } //container route-limit

        } //container dnat-only

        list pool {
          key "nat-pool-name";
          description
              "Configure a NAT pool";
          leaf nat-pool-name {
            type string {
              length "1..32";
            }
          } //nat-pool-name

          leaf nat-group {
            type uint32 {
              range "1..4";
            }
          } //nat-group

          leaf type {
            type enumeration {
              enum large-scale;
              enum l2-aware;
              enum wlan-gw-anchor;
            }
          } //type

          leaf applications {
            type enumeration {
              enum agnostic;
            }
          } //applications

          container description {
            description
                "Configure the description of this NAT pool";
            leaf description-string {
              type string {
                length "1..80";
              }
            } //description-string

          } //container description

          leaf external-assignment {
            type boolean;
            description
                "Enable or disable external IP address assignment from this pool";
          }

          container mode {
            description
                "Configure the mode of operation of this NAT pool";
            leaf mode-id {
              type enumeration {
                enum auto;
                enum napt;
                enum one-to-one;
              }
            } //mode-id

          } //container mode

          leaf port-forwarding-dyn-block-reservation {
            type boolean;
            description
                "Configure for each subscriber with a port forwarding entry, a port block 
                 reserved for dynamic NAT traffic flows";
          }

          container port-forwarding-range {
            description
                "Configure the port forwarding range";
            leaf range-end {
              type uint16;
              description
                  "[0 | 1023..65535]";
            } //range-end

          } //container port-forwarding-range

          container port-reservation {
            description
                "Configure the port reservation";
            leaf blocks {
              type uint16 {
                range "1..64512";
              }
            } //blocks

            leaf ports {
              type uint16 {
                range "1..32256";
              }
            } //ports

          } //container port-reservation

          leaf shutdown {
            type boolean;
            description
                "Administratively enable or disable the NAT pool";
          }

          container subscriber-limit {
            description
                "Configure the maximum number of subscribers per IP address";
            leaf subscriber-limit-id {
              type uint32 {
                range "1..65535";
              }
            } //subscriber-limit-id

          } //container subscriber-limit

          container watermarks {
            description
                "Configure the watermarks of this NAT pool";
            leaf high {
              type uint32 {
                range "1..100";
              }
            } //high

            leaf low {
              type uint32 {
                range "0..99";
              }
            } //low

          } //container watermarks

          list address-range {
            key "start-ip-address end-ip-address";
            description
                "Configure a NAT address range";
            leaf start-ip-address {
              type inet:ip-address;
              description
                  "a.b.c.d";
            } //start-ip-address

            leaf end-ip-address {
              type inet:ip-address;
              description
                  "a.b.c.d";
            } //end-ip-address

            container description {
              description
                  "Configure the description of this NAT address range";
              leaf description-string {
                type string {
                  length "1..80";
                }
              } //description-string

            } //container description

            leaf drain {
              type boolean;
              description
                  "Start/stop draining this NAT address range";
            }

          } //list address-range

          container deterministic {
            description
                "Configure deterministic NAT for this pool";
            container port-reservation {
              description
                  "Configure the port reservation";
              leaf num-ports {
                type uint32 {
                  range "1..65536";
                }
              } //num-ports

            } //container port-reservation

          } //container deterministic

          container redundancy {
            description
                "Configure NAT pool redundancy";
            container export {
              description
                  "Configure the route to export to the peer";
              leaf ip-prefix-length {
                type inet:ip-prefix;
                description
                    "Attribute ip-prefix/length for export";
              } //ip-prefix-length

            } //container export

            container follow {
              description
                  "Configure this pool to follow the redundancy state of another pool";
              leaf router {
                type string {
                  length "1..32";
                }
                description
                    "Attribute router-instance for follow";
              } //router

              leaf pool {
                type string;
              } //pool

            } //container follow

            container monitor {
              description
                  "Configure the peer route to monitor";
              leaf ip-prefix-length {
                type inet:ip-prefix;
                description
                    "Attribute ip-prefix/length for monitor";
              } //ip-prefix-length

            } //container monitor

            leaf shutdown {
              type boolean;
              description
                  "Administratively enable or disable the operation of dual-homing";
            }

          } //container redundancy

        } //list pool

      } //container outside

    } //container nat

  } //grouping alu-conf-router-nat-r13

} //module  alu-conf-router-nat-r13
