module alu-conf-port-aps-r13 {
  yang-version "1";

  namespace "urn:alcatel-lucent.com:sros:ns:yang:conf-port-aps-r13";

  prefix "conf-port-aps-r13";

  import alu-types {
    prefix "alu";
  }

  alu:alu-major-release "rel19";

  organization "Alcatel-Lucent";

  contact
      "Alcatel-Lucent SR OS Support 
       Web: <http://www.alcatel-lucent.com>";

  description
      "Alcatel-Lucent YANG Data model to configure Automatic Protection Switching on 
       SR OS based routers. 
       
       Copyright 2014-2015 Alcatel-Lucent, 2016 Nokia. All rights reserved. 
       Reproduction of this document is authorized on the condition that the 
       foregoing copyright notice is included. 
       
       This alu-conf-port-aps-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-port-aps-r13 {
    container aps {
      description
          "Configure Automatic Protection Switching";
      container advertise-interval {
        description
            "Configure interval between subsequent advertisement messages";
        leaf advertise-interval {
          type uint32 {
            range "10..650";
          }
          description
              "[10..650] in tenths of a second";
        } //advertise-interval

      } //container advertise-interval

      container hold-time {
        description
            "Configure how long to wait for an APS advertisement packet before the peer in 
             a Multi-Chassis APS group is considered operationally down";
        leaf hold-time {
          type uint32 {
            range "10..650";
          }
          description
              "[10..650] in 100s of milliseconds";
        } //hold-time

      } //container hold-time

      container hold-time-aps {
        description
            "Configure timers to bring down APS due to SF/SD";
        leaf lsignal-fail {
          type uint32 {
            range "1..100";
          }
          description
              "[1..100] in 100s of milliseconds";
        } //lsignal-fail

        leaf lsignal-degrade {
          type uint32 {
            range "1..100";
          }
          description
              "[1..100] in 100s of milliseconds";
        } //lsignal-degrade

      } //container hold-time-aps

      leaf mode-annexb {
        type boolean;
        description
            "Configure Annex B mode";
      }

      container neighbor {
        description
            "Configure neighbor's IP address for Multi-Chassis APS";
        leaf ip-address {
          type string;
          description
              "Attribute ip-address for neighbor";
        } //ip-address

      } //container neighbor

      container protect-circuit {
        description
            "Configure a physical port that will act as the protection circuit for this APS 
             group";
        leaf port-id {
          type string {
            length "1..64";
          }
          description
              "Attribute port-id for protect-circuit";
        } //port-id

      } //container protect-circuit

      container rdi-alarms {
        description
            "Configure the RDI alarm generation method for the APS working/protecting 
             circuits";
        leaf rdi-alarms-id {
          type enumeration {
            enum suppress;
            enum circuit;
          }
        } //rdi-alarms-id

      } //container rdi-alarms

      container revert-time {
        description
            "Configure how long to wait before switching back to the working circuit after 
             it has been restored to service";
        leaf minutes {
          type uint32 {
            range "0..60";
          }
        } //minutes

      } //container revert-time

      container switching-mode {
        description
            "Configure the switching mode for the APS port";
        leaf switching-mode-id {
          type enumeration {
            enum bi-directional;
            enum uni-directional;
            enum uni-1plus1;
          }
        } //switching-mode-id

      } //container switching-mode

      list working-circuit {
        key "number";
        description
            "Configure a physical port that will act as the working circuit for this APS 
             group";
        leaf port-id {
          type string {
            length "1..64";
          }
          description
              "Attribute port-id for working-circuit";
        } //port-id

        leaf number {
          type uint32 {
            range "1..2";
          }
          description
              "[1-2]";
        } //number

      } //list working-circuit

      container wtr-annexb {
        description
            "Configure Annex B Wait To Restore (WTR) time";
        leaf minutes {
          type uint32 {
            range "0..60";
          }
          default 5;
          description
              "[0..60] - Default: 5";
        } //minutes

      } //container wtr-annexb

    } //container aps

  } //grouping alu-conf-port-aps-r13

} //module  alu-conf-port-aps-r13
