module alu-conf-svc-dynsrv-r13 {
  yang-version "1";

  namespace "urn:alcatel-lucent.com:sros:ns:yang:conf-svc-dynsrv-r13";

  prefix "conf-svc-dynsrv-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Dynamic Services on SR OS based 
       routers. 
       
       Copyright 2014-2015 Alcatel-Lucent, 2016 Nokia. All rights reserved. 
       Reproduction of this document is authorized on the condition that the 
       foregoing copyright notice is included. 
       
       This alu-conf-svc-dynsrv-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-dynsrv-r13 {
    container dynamic-services {
      description
          "Configure Dynamic Services";
      container service-range {
        description
            "Configure the range of service identifiers reserved for dynamic services";
        leaf-list service-id {
          type uint32 {
            range "1..2147483647";
          }
          max-elements 2;
        } //service-id

      } //container service-range

      list dynamic-services-policy {
        key "dynsvc-policy-name";
        description
            "Configure a Dynamic Services policy";
        leaf dynsvc-policy-name {
          type string;
        } //dynsvc-policy-name

        container cli-user {
          description
              "Configure the CLI user";
          leaf name {
            type string;
          } //name

        } //container cli-user

        container description {
          description
              "Configure the description";
          leaf description-string {
            type string {
              length "1..80";
            }
          } //description-string

        } //container description

        container sap-limit {
          description
              "Configure the maximum number of dynamic-services SAP's";
          leaf sap-limit-id {
            type uint32 {
              range "0..131072";
            }
          } //sap-limit-id

        } //container sap-limit

        container script-policy {
          description
              "Configure the script policy";
          leaf name {
            type string;
          } //name

        } //container script-policy

        container accounting-1 {
          description
              "Configure the first accounting instance";
          container server-policy {
            description
                "Configure the server policy";
            leaf policy-name {
              type string;
            } //policy-name

          } //container server-policy

          container stats-type {
            description
                "Configure the type of accounting";
            leaf stats-type-id {
              type enumeration {
                enum time;
                enum volume-time;
              }
            } //stats-type-id

          } //container stats-type

          container update-interval {
            description
                "Configure the update interval";
            leaf hrs {
              type uint32 {
                range "1..23";
              }
            } //hrs

            leaf min {
              type uint32 {
                range "1..59";
              }
            } //min

            leaf days {
              type uint8 {
                range "1..180";
              }
            } //days

          } //container update-interval

          container update-interval-jitter {
            description
                "Configure the update interval jitter";
            leaf absolute {
              type uint32 {
                range "0..3600";
              }
              description
                  "[0..3600]";
            } //absolute

          } //container update-interval-jitter

        } //container accounting-1

        container accounting-2 {
          description
              "Configure the second accounting instance";
          container server-policy {
            description
                "Configure the server policy";
            leaf name {
              type string;
            } //name

          } //container server-policy

          container stats-type {
            description
                "Configure the type of accounting";
            leaf stats-type-id {
              type enumeration {
                enum time;
                enum volume-time;
              }
            } //stats-type-id

          } //container stats-type

          container update-interval {
            description
                "Configure the update interval";
            leaf hrs {
              type uint32 {
                range "1..23";
              }
            } //hrs

            leaf min {
              type uint32 {
                range "1..59";
              }
            } //min

            leaf days {
              type uint32 {
                range "1..180";
              }
            } //days

          } //container update-interval

          container update-interval-jitter {
            description
                "Configure the update interval jitter";
            leaf absolute {
              type uint32 {
                range "0..3600";
              }
              description
                  "[0..3600]";
            } //absolute

          } //container update-interval-jitter

        } //container accounting-2

        container authentication {
          description
              "Configure the authentication parameters";
          container local-auth-db {
            description
                "Configure the local authentication database to be used";
            leaf name {
              type string;
            } //name

          } //container local-auth-db

          container password {
            description
                "Configure the RADIUS server password";
            leaf password {
              type string {
                length "1..500";
              }
              description
                  "secret-key - [64 chars max] 
                   hash-key 
                   hash2-key 
                   custom-key";
            } //password

            leaf hash-hash2-custom {
              type enumeration {
                enum hash;
                enum hash2;
                enum custom;
              }
              description
                  "keywords - specify hashing scheme";
            } //hash-hash2-custom

          } //container password

          container server-policy {
            description
                "Configure the RADIUS server policy to be used for authentication";
            leaf policy-name {
              type string;
            } //policy-name

          } //container server-policy

        } //container authentication

      } //list dynamic-services-policy

      list local-auth-db {
        key "name";
        description
            "Configure a local authentication database";
        leaf name {
          type string;
        } //name

        container description {
          description
              "Configure the description of this local authentication database";
          leaf description-string {
            type string {
              length "1..80";
            }
          } //description-string

        } //container description

        leaf shutdown {
          type boolean;
          description
              "Configure the dynamic services admin state of this local authentication 
               database";
        }

        list user-name {
          key "name";
          description
              "Configure a user-name for this local authentication database";
          leaf name {
            type string {
              length "1..64";
            }
          } //name

          container description {
            description
                "Configure the description of this user in the local authentication database";
            leaf description-string {
              type string {
                length "1..80";
              }
            } //description-string

          } //container description

          leaf shutdown {
            type boolean;
            description
                "Configure the local authentication database admin state of this user";
          }

          list index {
            key "index";
            description
                "Configure a per-user SAP entry";
            leaf index {
              type int32 {
                range "1..32";
              }
            } //index

            container dynamic-services-policy {
              description
                  "Configure the dynamic services policy for this SAP entry";
              leaf name {
                type string;
              } //name

            } //container dynamic-services-policy

            container sap-id {
              description
                  "Configure the SAP identifier of this SAP entry";
              leaf sap-string {
                type string {
                  length "1..64";
                }
              } //sap-string

            } //container sap-id

            container script-parameters-1 {
              description
                  "Configure the Python script parameters of this SAP entry";
              leaf param-string1 {
                type string {
                  length "1..250";
                }
              } //param-string1

            } //container script-parameters-1

            container script-parameters-2 {
              description
                  "Configure the Python script parameters of this SAP entry";
              leaf param-string2 {
                type string {
                  length "1..250";
                }
              } //param-string2

            } //container script-parameters-2

            container script-parameters-3 {
              description
                  "Configure the Python script parameters of this SAP entry";
              leaf param-string3 {
                type string {
                  length "1..250";
                }
              } //param-string3

            } //container script-parameters-3

            container script-parameters-4 {
              description
                  "Configure the Python script parameters of this SAP entry";
              leaf param-string4 {
                type string {
                  length "1..250";
                }
              } //param-string4

            } //container script-parameters-4

            list accounting {
              key "accounting-id";
              description
                  "Configure the accounting configuration of per-user SAP entries in the local 
                   authentication database";
              leaf accounting-id {
                type enumeration {
                  enum 1;
                  enum 2;
                }
              } //accounting-id

              container stats-type {
                description
                    "Configure the type of statistics";
                leaf stats-type-id {
                  type enumeration {
                    enum volume-time;
                    enum time;
                  }
                } //stats-type-id

              } //container stats-type

              container update-interval {
                description
                    "Configure the time interval between consecutive accounting updates";
                leaf hrs {
                  type uint32 {
                    range "1..23";
                  }
                } //hrs

                leaf min {
                  type uint32 {
                    range "1..59";
                  }
                } //min

                leaf days {
                  type uint32 {
                    range "1..180";
                  }
                } //days

              } //container update-interval

            } //list accounting

          } //list index

        } //list user-name

      } //list local-auth-db

      container timers {
        description
            "Configure a Dynamic Services timer";
        container setup-timeout {
          description
              "Configure the dynamic services setup timeout";
          leaf access-accept {
            type uint64 {
              range "2..3600";
            }
            default 30;
            description
                "[2..3600] in seconds";
          } //access-accept

        } //container setup-timeout

      } //container timers

    } //container dynamic-services

  } //grouping alu-conf-svc-dynsrv-r13

} //module  alu-conf-svc-dynsrv-r13
