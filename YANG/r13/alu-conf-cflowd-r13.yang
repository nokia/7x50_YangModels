module alu-conf-cflowd-r13 {
  yang-version "1";

  namespace "urn:alcatel-lucent.com:sros:ns:yang:conf-cflowd-r13";

  prefix "conf-cflowd-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Cflowd on SR OS based routers. 
       
       Copyright 2014-2015 Alcatel-Lucent, 2016 Nokia. All rights reserved. 
       Reproduction of this document is authorized on the condition that the 
       foregoing copyright notice is included. 
       
       This alu-conf-cflowd-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-01-06";

  grouping alu-conf-cflowd-r13 {
    container cflowd {
      presence
          "Configure Cflowd";
      container active-flow-timeout {
        description
            "Configure Cflowd active flow timeout";
        leaf seconds {
          type uint32 {
            range "60..36000";
          }
          default 3600;
        } //seconds

      } //container active-flow-timeout

      container active-timeout {
        status "obsolete";
        description
            "Configure Cflowd active timeout";
        leaf minutes {
          type uint32 {
            range "1..600";
          }
        } //minutes

      } //container active-timeout

      leaf analyze-gre-payload {
        type boolean;
        description
            "Enable/disable Cflowd analysis on the inner IP packet in a GRE packet";
      }

      leaf analyze-l2tp-traffic {
        type boolean;
        description
            "Enable/disable Cflowd analysis on the inner header in an L2TP packet";
      }

      leaf analyze-v4overv6-traffic {
        type boolean;
        description
            "Enable/disable Cflowd analysis on the inner IPv4 packet within an IPv6 packet";
      }

      container cache-size {
        description
            "Configure maximum number of flows in the Cflowd cache table";
        leaf num-entries {
          type string;
          description
              "Attribute num-entries for cache-size";
        } //num-entries

      } //container cache-size

      leaf enhanced-distribution {
        type boolean;
        description
            "Enable/disable the inclusion of the ingress port ID in the hashing of sampled 
             packets";
      }

      container export-mode {
        description
            "Configure Cflowd Export Mode";
        leaf automatic-manual {
          type enumeration {
            enum automatic;
            enum manual;
          }
          description
              "automatic - export generated messages automatically 
               manual - export generated messages by CLI or SNMP 
               request 
               ";
        } //automatic-manual

      } //container export-mode

      container inactive-flow-timeout {
        description
            "Configure Cflowd inactive flow timeout";
        leaf seconds {
          type uint32 {
            range "10..600";
          }
          default 15;
        } //seconds

      } //container inactive-flow-timeout

      container inactive-timeout {
        status "obsolete";
        description
            "Configure Cflowd inactive timeout";
        leaf seconds {
          type uint32 {
            range "10..600";
          }
        } //seconds

      } //container inactive-timeout

      leaf inband-collector-export-only {
        type boolean;
        description
            "Enable/disable the export of traffic to all collectors to only be via in-band 
             interfaces";
      }

      container overflow {
        description
            "Configure percentage of entries to be removed from Cflowd cache when the 
             maximum number of entries has been exceeded";
        leaf percent {
          type uint32 {
            range "1..50";
          }
        } //percent

      } //container overflow

      container rate {
        status "obsolete";
        description
            "Configure the rate at which traffic is sampled and sent for Cflowd analysis";
        leaf sample-rate {
          type uint32 {
            range "1..10000";
          }
        } //sample-rate

      } //container rate

      leaf shutdown {
        type boolean;
        description
            "Administratively enable/disable Cflowd sampling";
      }

      container template-retransmit {
        description
            "Configure the time interval to resend template information";
        leaf seconds {
          type uint32 {
            range "10..600";
          }
        } //seconds

      } //container template-retransmit

      leaf use-vrtr-if-index {
        type boolean;
        description
            "Configure whether the virtual router interface index is used for Cflowd flow 
             records";
      }

      list collector {
        key "ip-address-port";
        description
            "Configure a Cflowd data collector";
        leaf ip-address-port {
          type string;
          description
              "ip-address - a.b.c.d[:port] (IPv4) 
               x:x:x:x:x:x:x:x (IPv6) 
               [x:x:x:x:x:x:x:x]:port (IPv6) 
               x - [0..FFFF]H 
               port - [1..65535]";
        } //ip-address-port

        leaf version {
          type uint32;
          description
              "Attribute version for collector";
        } //version

        container autonomous-system-type {
          description
              "Configures AS information based on origination or external peer AS routes";
          leaf autonomous-system-type-id {
            type enumeration {
              enum origin;
              enum peer;
            }
          } //autonomous-system-type-id

        } //container autonomous-system-type

        container description {
          description
              "Configure description for this Cflowd collector";
          leaf description-string {
            type string {
              length "1..80";
            }
            description
                "[80 characters max]";
          } //description-string

        } //container description

        container router {
          description
              "Configure the router context for the flow data for this Cflowd collector";
          leaf router-instance {
            type string {
              length "1..32";
            }
            default "management";
            description
                "<router-name>|<vprn-svc-id> 
                 router-name - Base|management Default - management 
                 vprn-svc-id - [1..2147483647]";
          } //router-instance

        } //container router

        leaf shutdown {
          type boolean;
          description
              "Administratively enable/disable this Cflowd collector";
        }

        container template-set {
          description
              "Configure the template set for this Cflowd collector";
          leaf template-set-id {
            type enumeration {
              enum basic;
              enum mpls-ip;
              enum l2-ip;
              enum mpls-transport;
            }
          } //template-set-id

        } //container template-set

        container aggregation {
          presence
              "Configure the type of aggregation scheme to be exported";
          leaf as-matrix {
            type boolean;
            description
                "Configure Cflowd aggregation based on AS information";
          }

          leaf destination-prefix {
            type boolean;
            description
                "Configure Cflowd aggregation based on destination prefix";
          }

          leaf protocol-port {
            type boolean;
            description
                "Configure Cflowd aggregation based on protocol and port information";
          }

          leaf raw {
            type boolean;
            description
                "Configure raw flow data to be sent in version 5";
          }

          leaf source-destination-prefix {
            type boolean;
            description
                "Configure Cflowd aggregation based on source and destination prefixes";
          }

          leaf source-prefix {
            type boolean;
            description
                "Configure Cflowd aggregation based on source prefix information";
          }

        } //container aggregation

        container export-filter {
          description
              "Configure which flow data is exported to this Cflowd collector";
          list router {
            key "router-instance";
            description
                "Configure which routers' flow data is included in being sent to this collector";
            leaf router-instance {
              type string {
                length "1..32";
              }
              description
                  "<router-name>|<vprn-svc-id> 
                   router-name - Base 
                   vprn-svc-id - [1..2147483647]";
            } //router-instance

          } //list router

          container family {
            presence
                "Configure which address families' flow data is excluded from being sent to 
                 this collector";
            leaf ipv4 {
              type boolean;
              description
                  "Configure the IPv4 address family attribute for this collector";
            }

            leaf ipv6 {
              type boolean;
              description
                  "Configure IPv6 address family attribute for this collector";
            }

            leaf l2-ip {
              type boolean;
              description
                  "Configure Layer 2 IP address family attribute for this collector";
            }

            leaf mcast-ipv4 {
              type boolean;
              description
                  "Configure Multicast IPv4 address family attribute for this collector";
            }

            leaf mcast-ipv6 {
              type boolean;
              description
                  "Configure Multicast IPv6 address family attribute for this collector";
            }

            leaf mpls {
              type boolean;
              description
                  "Configure MPLS address family attribute for this collector";
            }

          } //container family

          container interface-list {
            description
                "Configure which sampling interfaces' flow data is included in being sent to 
                 this collector";
            list router {
              key "router-instance interface";
              description
                  "Configure which router interfaces' flow data is being sent to this collector";
              leaf router-instance {
                type string {
                  length "1..32";
                }
                description
                    "<router-name>|<vprn-svc-id> 
                     router-name - Base|management Default - Base 
                     vprn-svc-id - [1..2147483647]";
              } //router-instance

              leaf interface {
                type string {
                  length "1..32";
                }
                description
                    "[32 chars max] (must start with a letter)";
              } //interface

            } //list router

            container service {
              description
                  "Configure which service interfaces' flow data is being sent to this collector";
              list ies {
                key "service-id";
                description
                    "Configure which ies service interfaces' flow data is being sent to this 
                     collector";
                leaf service-id {
                  type string;
                  description
                      "Attribute service-id for ies";
                } //service-id

                leaf interface {
                  type string {
                    length "1..32";
                  }
                  description
                      "[32 chars max] (must start with a letter)";
                } //interface

                leaf subscriber-interface {
                  type string {
                    length "1..32";
                  }
                  description
                      "[32 chars max] (must start with a letter)";
                } //subscriber-interface

                leaf group-interface {
                  type string {
                    length "1..32";
                  }
                  description
                      "[32 chars max] (must start with a letter)";
                } //group-interface

              } //list ies

              list vprn {
                key "service-id";
                description
                    "Configure which vprn service interfaces' flow data is being sent to this 
                     collector";
                leaf service-id {
                  type string;
                  description
                      "Attribute service-id for vprn";
                } //service-id

                leaf interface {
                  type string {
                    length "1..32";
                  }
                  description
                      "[32 chars max] (must start with a letter)";
                } //interface

                leaf network-interface {
                  type string {
                    length "1..32";
                  }
                  description
                      "[32 chars max] (must start with a letter)";
                } //network-interface

                leaf subscriber-interface {
                  type string {
                    length "1..32";
                  }
                  description
                      "[32 chars max] (must start with a letter)";
                } //subscriber-interface

                leaf group-interface {
                  type string {
                    length "1..32";
                  }
                } //group-interface

              } //list vprn

            } //container service

          } //container interface-list

        } //container export-filter

      } //list collector

      list sample-profile {
        key "profile-id";
        description
            "Configure Cflowd sample profiles";
        leaf profile-id {
          type uint32 {
            range "1..5";
          }
        } //profile-id

        container sample-rate {
          description
              "Configure the sample rate for this sample profile";
          leaf sample-rate-id {
            type uint32 {
              range "1..10000";
            }
          } //sample-rate-id

        } //container sample-rate

      } //list sample-profile

    } //container cflowd

  } //grouping alu-conf-cflowd-r13

} //module  alu-conf-cflowd-r13
