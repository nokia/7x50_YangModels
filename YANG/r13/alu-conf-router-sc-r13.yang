module alu-conf-router-sc-r13 {
  yang-version "1";

  namespace "urn:alcatel-lucent.com:sros:ns:yang:conf-router-sc-r13";

  prefix "conf-router-sc-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure ISA Service Chaining for a virtual 
       router on SR OS based routers. 
       
       Copyright 2014-2015 Alcatel-Lucent, 2016 Nokia. All rights reserved. 
       Reproduction of this document is authorized on the condition that the 
       foregoing copyright notice is included. 
       
       This alu-conf-router-sc-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-router-sc-r13 {
    container isa-service-chaining {
      presence
          "Configure ISA Service Chaining for a virtual router";
      list nat-group {
        key "nat-group-id";
        description
            "Specifies NAT groups";
        leaf nat-group-id {
          type uint32 {
            range "1..4";
          }
        } //nat-group-id

      } //list nat-group

      container vxlan-vtep-range {
        description
            "Specifies VXLAN Tunnel Endpoint (VTEP) Information";
        leaf start {
          type string;
        } //start

        leaf end {
          type string;
        } //end

      } //container vxlan-vtep-range

    } //container isa-service-chaining

  } //grouping alu-conf-router-sc-r13

} //module  alu-conf-router-sc-r13
