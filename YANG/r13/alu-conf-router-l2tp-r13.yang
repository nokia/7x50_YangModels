module alu-conf-router-l2tp-r13 {
  yang-version "1";

  namespace "urn:alcatel-lucent.com:sros:ns:yang:conf-router-l2tp-r13";

  prefix "conf-router-l2tp-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure L2TP on SR OS based routers. 
       
       Copyright 2014-2015 Alcatel-Lucent, 2016 Nokia. All rights reserved. 
       Reproduction of this document is authorized on the condition that the 
       foregoing copyright notice is included. 
       
       This alu-conf-router-l2tp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-router-l2tp-r13 {
    container l2tp {
      description
          "Configure L2TP";
      container avp-hiding {
        description
            "Configure the AVP hiding";
        leaf avp-hiding-id {
          type enumeration {
            enum sensitive;
            enum always;
          }
        } //avp-hiding-id

      } //container avp-hiding

      container calling-number-format {
        description
            "Specify the L2TP Calling Number AVP";
        leaf ascii-spec {
          type string {
            length "1..255";
          }
          description
              "Attribute ascii-spec for calling-number-format";
        } //ascii-spec

      } //container calling-number-format

      container challenge {
        description
            "Configure the use of challenge-response authentication";
        leaf challenge-id {
          type enumeration {
            enum always;
          }
        } //challenge-id

      } //container challenge

      container cisco-nas-port {
        description
            "Specify the L2TP Cisco NAS-Port AVP";
        leaf ethernet {
          type string {
          }
          description
              "Attribute binary-spec-eth for cisco-nas-port";
        } //ethernet

        leaf atm {
          type string {
          }
          description
              "Attribute binary-spec-atm for cisco-nas-port";
        } //atm

      } //container cisco-nas-port

      container destruct-timeout {
        description
            "Configure the destruction timeout";
        leaf destruct-timeout {
          type uint32 {
            range "60..86400";
          }
          description
              "[60..86400] s";
        } //destruct-timeout

      } //container destruct-timeout

      container df-bit-lac {
        description
            "Enable/disable setting the DF (don't fragment) bit in data traffic transmitted 
             as LAC";
        leaf df-bit-lac-id {
          type enumeration {
            enum always;
            enum never;
          }
        } //df-bit-lac-id

      } //container df-bit-lac

      container exclude-avps {
        description
            "Configure the AVP's to exclude in transmitted L2TP messages";
        leaf calling-number {
          type boolean;
        } //calling-number

        leaf initial-rx-lcp-conf-req {
          type boolean;
        } //initial-rx-lcp-conf-req

      } //container exclude-avps

      container group-session-limit {
        description
            "Configure the L2TP session limit for each group of this router";
        leaf session-limit {
          type string;
          description
              "Attribute session-limit for group-session-limit";
        } //session-limit

        leaf unlimited {
          type boolean;
          description
              "Use the maximum available";
        } //unlimited

      } //container group-session-limit

      container hello-interval {
        description
            "Configure the hello interval";
        leaf hello-interval {
          type uint32 {
            range "10..3600";
          }
          description
              "Attribute hello-interval for hello-interval";
        } //hello-interval

        leaf infinite {
          type boolean;
        } //infinite

      } //container hello-interval

      container idle-timeout {
        description
            "Configure the idle timeout";
        leaf idle-timeout {
          type uint32 {
            range "0..3600";
          }
          description
              "[0..3600] s";
        } //idle-timeout

      } //container idle-timeout

      container ignore-avps {
        description
            "Configure the AVP's to ignore in received L2TP messages";
        leaf sequencing-required {
          type boolean;
        } //sequencing-required

      } //container ignore-avps

      container local-address {
        description
            "Configure the local address";
        leaf ip-address {
          type inet:ip-address;
          description
              "[a.b.c.d]";
        } //ip-address

      } //container local-address

      container local-name {
        description
            "Configure the local host name";
        leaf host-name {
          type string {
            length "1..64";
          }
        } //host-name

      } //container local-name

      container max-retries-estab {
        description
            "Configure the maximum number of retries for established tunnels";
        leaf max-retries {
          type uint32 {
            range "2..7";
          }
        } //max-retries

      } //container max-retries-estab

      container max-retries-not-estab {
        description
            "Configure the maximum number of retries for unestablished tunnels";
        leaf max-retries {
          type uint32 {
            range "2..7";
          }
        } //max-retries

      } //container max-retries-not-estab

      container next-attempt {
        description
            "Specify which tunnel to select when previous session setup failed";
        leaf next-attempt-id {
          type enumeration {
            enum same-preference-level;
            enum next-preference-level;
          }
        } //next-attempt-id

      } //container next-attempt

      container password {
        description
            "Configure the password";
        leaf password {
          type string {
            length "1..500";
          }
          description
              "password - [64 chars max] 
               hash-key 
               hash2-key 
               custom-key";
        } //password

        leaf hash-hash2-custom {
          type enumeration {
            enum hash;
            enum hash2;
            enum custom;
          }
        } //hash-hash2-custom

      } //container password

      container peer-address-change-policy {
        description
            "Configure the reaction to a change of tunnel peer address in this router";
        leaf peer-address-change-policy-id {
          type enumeration {
            enum accept;
            enum ignore;
            enum reject;
          }
        } //peer-address-change-policy-id

      } //container peer-address-change-policy

      container radius-accounting-policy {
        description
            "Configure the RADIUS accounting policy";
        leaf policy-name {
          type string {
            length "1..32";
          }
        } //policy-name

      } //container radius-accounting-policy

      container receive-window-size {
        description
            "Configure the L2TP Receive Window Size";
        leaf receive-window-size-id {
          type uint16 {
            range "4..1024";
          }
        } //receive-window-size-id

      } //container receive-window-size

      container replace-result-code {
        description
            "Configure the L2TP Result codes that need to be replaced";
        leaf-list code {
          type enumeration {
            enum cdn-inv-dest;
            enum cdn-perm-no-facilities;
            enum cdn-tmp-no-facilities;
          }
          max-elements 3;
        } //code

      } //container replace-result-code

      container rtm-debounce-time {
        description
            "Configure the debounce timer for the L2TP action upon Route Table Management 
             events";
        leaf milliseconds {
          type uint32 {
            range "0..5000";
          }
        } //milliseconds

      } //container rtm-debounce-time

      container session-assign-method {
        description
            "Configure the session assignment method";
        leaf session-assign-method-id {
          type enumeration {
            enum weighted;
            enum weighted-random;
          }
        } //session-assign-method-id

      } //container session-assign-method

      container session-limit {
        description
            "Configure the L2TP session limit of this router";
        leaf session-limit {
          type string;
          description
              "Attribute session-limit for session-limit";
        } //session-limit

        leaf unlimited {
          type boolean;
          description
              "Use the maximum available";
        } //unlimited

      } //container session-limit

      leaf shutdown {
        type boolean;
        description
            "Administratively enable or disable the operation of L2TP";
      }

      container tunnel-session-limit {
        description
            "Configure the L2TP session limit for each tunnel of this router";
        leaf session-limit {
          type string;
        } //session-limit

        leaf unlimited {
          type boolean;
          description
              "Use the maximum available";
        } //unlimited

      } //container tunnel-session-limit

      container eth-tunnel {
        description
            "Configure ethernet tunnel client settings";
        container reconnect-timeout {
          description
              "Configure the timeout for session setup retry";
          leaf reconnect-timeout {
            type uint32 {
              range "10..3600";
            }
            description
                "[10..3600] s";
          } //reconnect-timeout

        } //container reconnect-timeout

      } //container eth-tunnel

      container failover {
        description
            "Configure LAC Multi-Chassis Redundancy";
        container recovery-max-session-lifetime {
          description
              "Select the sub-set of sessions to recover";
          leaf minutes {
            type uint32 {
              range "2..4294967295";
            }
          } //minutes

        } //container recovery-max-session-lifetime

        container recovery-method {
          description
              "Configure the method to recover the sequence numbers in case of failover";
          leaf method {
            type enumeration {
              enum mcs;
              enum recovery-tunnel;
            }
          } //method

        } //container recovery-method

        container recovery-time {
          description
              "Configure the time requested from the L2TP peer to wait before assuming 
               failover failed";
          leaf seconds {
            type uint32 {
              range "0..900";
            }
          } //seconds

        } //container recovery-time

        list track-srrp {
          key "srrp-instance";
          description
              "Configure the SRRP instance, peer and sync-tag";
          leaf srrp-instance {
            type uint32 {
              range "1..4294967295";
            }
          } //srrp-instance

          leaf peer {
            type inet:ip-address;
            description
                "a.b.c.d";
          } //peer

          leaf sync-tag {
            type string;
          } //sync-tag

        } //list track-srrp

      } //container failover

      list group {
        key "tunnel-group-name";
        description
            "Configure an L2TP tunnel group";
        leaf tunnel-group-name {
          type string {
            length "1..63";
          }
        } //tunnel-group-name

        leaf protocol {
          type enumeration {
            enum v2;
            enum v3;
            enum v3draft;
          }
          description
              "{v2|v3|v3draft} - 
               optional while creating a group, default v2";
        } //protocol

        container avp-hiding {
          description
              "Configure the AVP hiding";
          leaf avp-hiding-id {
            type enumeration {
              enum sensitive;
              enum always;
              enum never;
            }
          } //avp-hiding-id

        } //container avp-hiding

        container challenge {
          description
              "Configure the use of challenge-response authentication";
          leaf challenge-id {
            type enumeration {
              enum always;
              enum never;
            }
          } //challenge-id

        } //container challenge

        container description {
          description
              "Configure the description";
          leaf description-string {
            type string {
              length "1..80";
            }
          } //description-string

        } //container description

        container destruct-timeout {
          description
              "Configure the destruction timeout";
          leaf destruct-timeout {
            type uint32 {
              range "60..86400";
            }
            description
                "[60..86400] s";
          } //destruct-timeout

        } //container destruct-timeout

        container df-bit-lac {
          description
              "Enable/disable setting the DF (don't fragment) bit in data traffic transmitted 
               as LAC";
          leaf df-bit-lac-id {
            type enumeration {
              enum always;
              enum never;
              enum default;
            }
          } //df-bit-lac-id

        } //container df-bit-lac

        container hello-interval {
          description
              "Configure the hello interval";
          leaf hello-interval {
            type uint32 {
              range "10..3600";
            }
            description
                "Attribute hello-interval for hello-interval";
          } //hello-interval

          leaf infinite {
            type boolean;
          } //infinite

        } //container hello-interval

        container idle-timeout {
          description
              "Configure the idle timeout";
          leaf idle-timeout {
            type uint32 {
              range "0..3600";
            }
            description
                "[0..3600] s";
          } //idle-timeout

          leaf infinite {
            type boolean;
          } //infinite

        } //container idle-timeout

        container lns-group {
          description
              "Configure the ISA LNS group";
          leaf lns-group-id {
            type uint32 {
              range "1..4";
            }
          } //lns-group-id

        } //container lns-group

        container load-balance-method {
          description
              "Configure the load balance method";
          leaf load-balance-method-id {
            type enumeration {
              enum per-session;
              enum per-tunnel;
            }
          } //load-balance-method-id

        } //container load-balance-method

        container local-address {
          description
              "Configure the local address";
          leaf ip-address {
            type inet:ip-address;
            description
                "[a.b.c.d]";
          } //ip-address

        } //container local-address

        container local-name {
          description
              "Configure the local host name";
          leaf host-name {
            type string {
              length "1..64";
            }
          } //host-name

        } //container local-name

        container max-retries-estab {
          description
              "Configure the maximum number of retries for established tunnels";
          leaf max-retries {
            type uint32 {
              range "2..7";
            }
          } //max-retries

        } //container max-retries-estab

        container max-retries-not-estab {
          description
              "Configure the maximum number of retries for unestablished tunnels";
          leaf max-retries {
            type uint32 {
              range "2..7";
            }
          } //max-retries

        } //container max-retries-not-estab

        container password {
          description
              "Configure the password";
          leaf password {
            type string {
              length "1..500";
            }
            description
                "password - [64 chars max] 
                 hash-key 
                 hash2-key 
                 custom-key";
          } //password

          leaf hash-hash2-custom {
            type enumeration {
              enum hash;
              enum hash2;
              enum custom;
            }
          } //hash-hash2-custom

        } //container password

        container radius-accounting-policy {
          description
              "Configure the RADIUS accounting policy";
          leaf policy-name {
            type string {
              length "1..32";
            }
          } //policy-name

        } //container radius-accounting-policy

        container receive-window-size {
          description
              "Configure the Receive Window Size";
          leaf receive-window-size-id {
            type uint16 {
              range "4..1024";
            }
          } //receive-window-size-id

        } //container receive-window-size

        container session-assign-method {
          description
              "Configure the session assignment method";
          leaf session-assign-method-id {
            type enumeration {
              enum existing-first;
              enum weighted;
              enum weighted-random;
            }
          } //session-assign-method-id

        } //container session-assign-method

        container session-limit {
          description
              "Configure the session limit";
          leaf session-limit {
            type string;
            description
                "Attribute session-limit for session-limit";
          } //session-limit

          leaf unlimited {
            type boolean;
            description
                "Use the maximum available";
          } //unlimited

        } //container session-limit

        leaf shutdown {
          type boolean;
          description
              "Administratively enable or disable this L2TP tunnel group";
        }

        container eth-tunnel {
          description
              "Configure ethernet tunnel client settings at group level";
          container reconnect-timeout {
            description
                "Configure the timeout for session setup retry at group level";
            leaf reconnect-timeout {
              type uint32 {
                range "10..3600";
              }
              description
                  "[10..3600] s";
            } //reconnect-timeout

            leaf infinite {
              type boolean;
            } //infinite

          } //container reconnect-timeout

        } //container eth-tunnel

        container failover {
          description
              "Configure LAC Multi-Chassis Redundancy";
          container recovery-method {
            description
                "Configure the method to recover the sequence numbers in case of failover";
            leaf method {
              type enumeration {
                enum default;
                enum mcs;
                enum recovery-tunnel;
              }
            } //method

          } //container recovery-method

          container recovery-time {
            description
                "Configure the time requested from the L2TP peer to wait before assuming 
                 failover failed";
            leaf seconds {
              type uint32 {
                range "0..900";
              }
            } //seconds

          } //container recovery-time

        } //container failover

        container l2tpv3 {
          description
              "Configure L2TP V3";
          container cookie-length {
            description
                "Configure the cookie length";
            leaf cookie-length {
              type enumeration {
                enum 4;
                enum 8;
              }
              description
                  "[4|8]";
            } //cookie-length

            leaf default {
              type boolean;
            } //default

          } //container cookie-length

          container digest-type {
            description
                "Configure the digest type";
            leaf digest-type-id {
              type enumeration {
                enum default;
                enum none;
                enum md5;
                enum sha1;
              }
            } //digest-type-id

          } //container digest-type

          container nonce-length {
            description
                "Configure the nonce length";
            leaf nonce-length-id {
              type uint32 {
                range "16..64";
              }
            } //nonce-length-id

            leaf default {
              type boolean;
            } //default

          } //container nonce-length

          container password {
            description
                "Configure the password";
            leaf password {
              type string {
                length "1..500";
              }
              description
                  "password - [64 chars max] 
                   hash-key 
                   hash2-key 
                   custom-key";
            } //password

            leaf hash-hash2-custom {
              type enumeration {
                enum hash;
                enum hash2;
                enum custom;
              }
            } //hash-hash2-custom

          } //container password

          container private-tcp-mss-adjust {
            description
                "Configure the TCP maximum segment size (MSS) on private network";
            leaf octets {
              type uint32 {
                range "512..9000";
              }
            } //octets

            leaf default {
              type boolean;
            } //default

          } //container private-tcp-mss-adjust

          container public-tcp-mss-adjust {
            description
                "Configure the TCP maximum segment size (MSS) on public network";
            leaf octets {
              type uint32 {
                range "512..9000";
              }
            } //octets

            leaf default {
              type boolean;
            } //default

          } //container public-tcp-mss-adjust

          container pw-cap-list {
            description
                "Configure the Pseudo Wire capture list";
            leaf-list pw-cap-list-id {
              type enumeration {
                enum ethernet;
                enum ethernet-vlan;
              }
              max-elements 2;
            } //pw-cap-list-id

          } //container pw-cap-list

          container rem-router-id {
            description
                "Configure the filter on remote router ID";
            leaf ip-address {
              type inet:ip-address;
              description
                  "a.b.c.d";
            } //ip-address

          } //container rem-router-id

          leaf track-password-change {
            type boolean;
            description
                "Configure the tracking of a password change";
          }

        } //container l2tpv3

        container mlppp {
          description
              "Configure MLPPP for the L2TP tunnel group";
          container endpoint {
            description
                "Configure the endpoint ID";
            leaf ip {
              type inet:ip-address;
              description
                  "a.b.c.d";
            } //ip

            leaf mac {
              type alu:ieee-address;
              description
                  "xx:xx:xx:xx:xx:xx or xx-xx-xx-xx-xx-xx (cannot be all zeros)";
            } //mac

            leaf system-ip {
              type boolean;
            } //system-ip

            leaf system-mac {
              type boolean;
            } //system-mac

          } //container endpoint

          leaf interleave {
            type boolean;
            description
                "Configure the use of link fragmentation and interleaving";
          }

          container max-fragment-delay {
            description
                "Configure the maximum fragment delay";
            leaf delay {
              type uint16 {
                range "5..1000";
              }
              description
                  "[5..1000] milliseconds";
            } //delay

          } //container max-fragment-delay

          container max-links {
            description
                "Configure the maximum number of MLPPP links";
            leaf max-links-id {
              type uint16 {
                range "1..8";
              }
            } //max-links-id

          } //container max-links

          container reassembly-timeout {
            description
                "Configure the reassembly timeout";
            leaf reassembly-timeout-id {
              type enumeration {
                enum 100;
                enum 1000;
              }
              description
                  "{100 | 1000} milliseconds";
            } //reassembly-timeout-id

          } //container reassembly-timeout

          leaf short-sequence-numbers {
            type boolean;
            description
                "Request the peer to send us short sequence numbers";
          }

          leaf shutdown {
            type boolean;
            description
                "Enable or disable MLPPP for this L2TP tunnel group";
          }

        } //container mlppp

        container ppp {
          description
              "Configure PPP for the L2TP tunnel group";
          container authentication {
            description
                "Configure the PPP authentication protocol to negotiate";
            leaf authentication-id {
              type enumeration {
                enum chap;
                enum pap;
                enum pref-chap;
                enum pref-pap;
              }
            } //authentication-id

          } //container authentication

          container authentication-policy {
            description
                "Configure the authentication policy";
            leaf auth-policy-name {
              type string {
                length "1..32";
              }
            } //auth-policy-name

          } //container authentication-policy

          container chap-challenge-length {
            description
                "Configure the maximum and minimum PPP CHAP challenge length";
            leaf min {
              type uint32 {
                range "8..64";
              }
            } //min

            leaf max {
              type uint32 {
                range "8..64";
              }
              description
                  "length";
            } //max

          } //container chap-challenge-length

          container default-group-interface {
            description
                "Configure the default group interface";
            leaf ip-int-name {
              type string {
                length "1..32";
              }
            } //ip-int-name

            leaf service-id {
              type string;
              description
                  "Attribute service-id for default-group-interface";
            } //service-id

            leaf service-name {
              type string {
                length "1..64";
              }
            } //service-name

          } //container default-group-interface

          leaf ipcp-subnet-negotiation {
            type boolean;
            description
                "Configure the IPCP subnet negotiation";
          }

          container keepalive {
            description
                "Configure the PPP keepalive interval and multiplier";
            leaf seconds {
              type uint32 {
                range "10..300";
              }
            } //seconds

            leaf hold-up-multiplier {
              type uint32 {
                range "1..5";
              }
            } //hold-up-multiplier

          } //container keepalive

          leaf lcp-force-ack-accm {
            type boolean;
            description
                "Force acknowledgement of the LCP Asynchronous Control Character Map (ACCM) 
                 configuration option during LCP negotiation, but don't do ACC mapping";
          }

          leaf lcp-ignore-magic-numbers {
            type boolean;
            description
                "Configure checking the Magic-Number field in LCP Echo-Request and LCP 
                 Echo-Reply messages";
          }

          container mtu {
            description
                "Configure the maximum PPP MTU size";
            leaf mtu-bytes {
              type uint32 {
                range "512..9212";
              }
            } //mtu-bytes

          } //container mtu

          leaf proxy-authentication {
            type boolean;
            description
                "Configure the use of the Authentication AVPs received from the LAC";
          }

          leaf proxy-lcp {
            type boolean;
            description
                "Configure the use of the Proxy LCP AVPs received from the LAC";
          }

          leaf reject-disabled-ncp {
            type boolean;
            description
                "Force rejection of disabled Network Control Protocols (NCP)";
          }

          container user-db {
            description
                "Configure the local user database to use for PPP PAP/CHAP authentication";
            leaf local-user-db-name {
              type string {
                length "1..32";
              }
            } //local-user-db-name

          } //container user-db

        } //container ppp

        list tunnel {
          key "tunnel-name";
          description
              "Configure an L2TP tunnel";
          leaf tunnel-name {
            type string {
              length "1..32";
            }
          } //tunnel-name

          leaf auto-establish {
            type boolean;
            description
                "Configure if this tunnel must be automatically set up";
          }

          container avp-hiding {
            description
                "Configure the AVP hiding";
            leaf avp-hiding-id {
              type enumeration {
                enum never;
                enum sensitive;
                enum always;
              }
            } //avp-hiding-id

          } //container avp-hiding

          container challenge {
            description
                "Configure the use of challenge-response authentication";
            leaf challenge-id {
              type enumeration {
                enum always;
                enum never;
              }
            } //challenge-id

          } //container challenge

          container description {
            description
                "Configure the description";
            leaf description-string {
              type string {
                length "1..80";
              }
              description
                  "[80 characters max]";
            } //description-string

          } //container description

          container destruct-timeout {
            description
                "Configure the destruct timeout";
            leaf destruct-timeout {
              type uint32 {
                range "60..86400";
              }
              description
                  "[60..86400] s";
            } //destruct-timeout

          } //container destruct-timeout

          container df-bit-lac {
            description
                "Enable/disable setting the DF (don't fragment) bit in data traffic transmitted 
                 as LAC";
            leaf df-bit-lac-id {
              type enumeration {
                enum always;
                enum never;
                enum default;
              }
            } //df-bit-lac-id

          } //container df-bit-lac

          container hello-interval {
            description
                "Configure the hello interval";
            leaf hello-interval {
              type uint32 {
                range "10..3600";
              }
              description
                  "Attribute hello-interval for hello-interval";
            } //hello-interval

            leaf infinite {
              type boolean;
            } //infinite

          } //container hello-interval

          container idle-timeout {
            description
                "Configure the idle timeout";
            leaf idle-timeout {
              type uint32 {
                range "0..3600";
              }
              description
                  "[0..3600] s";
            } //idle-timeout

            leaf infinite {
              type boolean;
            } //infinite

          } //container idle-timeout

          container lns-group {
            description
                "Configure the ISA LNS group";
            leaf lns-group-id {
              type uint32 {
                range "1..4";
              }
            } //lns-group-id

          } //container lns-group

          container load-balance-method {
            description
                "Configure the load balance method";
            leaf load-balance-method-id {
              type enumeration {
                enum per-session;
                enum per-tunnel;
              }
            } //load-balance-method-id

          } //container load-balance-method

          container local-address {
            description
                "Configure the local address";
            leaf ip-address {
              type inet:ip-address;
              description
                  "[a.b.c.d]";
            } //ip-address

          } //container local-address

          container local-name {
            description
                "Configure the local host name";
            leaf host-name {
              type string {
                length "1..64";
              }
            } //host-name

          } //container local-name

          container max-retries-estab {
            description
                "Configure the maximum number of retries while this tunnel is established";
            leaf max-retries {
              type uint32 {
                range "2..7";
              }
            } //max-retries

          } //container max-retries-estab

          container max-retries-not-estab {
            description
                "Configure the maximum number of retries while this tunnel is not established";
            leaf max-retries {
              type uint32 {
                range "2..7";
              }
            } //max-retries

          } //container max-retries-not-estab

          container password {
            description
                "Configure the password";
            leaf password {
              type string {
                length "1..500";
              }
              description
                  "password - [64 chars max] 
                   hash-key 
                   hash2-key 
                   custom-key";
            } //password

            leaf hash-hash2-custom {
              type enumeration {
                enum hash;
                enum hash2;
                enum custom;
              }
            } //hash-hash2-custom

          } //container password

          container peer {
            description
                "Configure the peer address";
            leaf ip-address {
              type inet:ip-address;
            } //ip-address

          } //container peer

          container preference {
            description
                "Configure the preference";
            leaf preference {
              type uint32 {
                range "0..16777215";
              }
            } //preference

          } //container preference

          container radius-accounting-policy {
            description
                "Configure the RADIUS accounting policy";
            leaf policy-name {
              type string {
                length "1..32";
              }
            } //policy-name

          } //container radius-accounting-policy

          container receive-window-size {
            description
                "Configure the Receive Window Size";
            leaf receive-window-size-id {
              type uint16 {
                range "4..1024";
              }
            } //receive-window-size-id

          } //container receive-window-size

          container remote-name {
            description
                "Configure the remote host name";
            leaf host-name {
              type string {
                length "1..64";
              }
            } //host-name

          } //container remote-name

          container session-limit {
            description
                "Configure the session limit of this L2TP tunnel";
            leaf session-limit {
              type string;
            } //session-limit

            leaf unlimited {
              type boolean;
              description
                  "Use the maximum available";
            } //unlimited

          } //container session-limit

          leaf shutdown {
            type boolean;
            description
                "Administratively enable or disable this L2TP tunnel";
          }

          container failover {
            description
                "Configure LAC Multi-Chassis Redundancy";
            container recovery-method {
              description
                  "Configure the method to recover the sequence numbers in case of failover";
              leaf method {
                type enumeration {
                  enum default;
                  enum mcs;
                  enum recovery-tunnel;
                }
              } //method

            } //container recovery-method

            container recovery-time {
              description
                  "Configure the time requested from the L2TP peer to wait before assuming 
                   failover failed";
              leaf seconds {
                type uint32 {
                  range "0..900";
                }
              } //seconds

            } //container recovery-time

          } //container failover

          container l2tpv3 {
            description
                "Configure L2TP V3";
            container private-tcp-mss-adjust {
              description
                  "Configure the TCP maximum segment size (MSS) on private network";
              leaf octets {
                type uint32 {
                  range "512..9000";
                }
              } //octets

              leaf default {
                type boolean;
              } //default

            } //container private-tcp-mss-adjust

            container public-tcp-mss-adjust {
              description
                  "Configure the TCP maximum segment size (MSS) on public network";
              leaf octets {
                type uint32 {
                  range "512..9000";
                }
              } //octets

              leaf default {
                type boolean;
              } //default

            } //container public-tcp-mss-adjust

          } //container l2tpv3

          container mlppp {
            description
                "Configure MLPPP for the L2TP tunnel";
            container admin-state {
              description
                  "Enable or disable MLPPP for this L2TP tunnel group";
              leaf admin-state-id {
                type enumeration {
                  enum down;
                  enum up;
                }
              } //admin-state-id

            } //container admin-state

            container endpoint {
              description
                  "Configure the endpoint ID";
              leaf ip {
                type inet:ip-address;
                description
                    "a.b.c.d";
              } //ip

              leaf mac {
                type alu:ieee-address;
                description
                    "xx:xx:xx:xx:xx:xx or xx-xx-xx-xx-xx-xx (cannot be all zeros)";
              } //mac

              leaf system-ip {
                type boolean;
              } //system-ip

              leaf system-mac {
                type boolean;
              } //system-mac

            } //container endpoint

            container interleave {
              description
                  "Configure the use of link fragmentation and interleaving";
              leaf interleave-id {
                type enumeration {
                  enum always;
                  enum never;
                }
              } //interleave-id

            } //container interleave

            container max-fragment-delay {
              description
                  "Configure the maximum fragment delay";
              leaf delay {
                type uint16 {
                  range "5..1000";
                }
                description
                    "[5..1000] milliseconds";
              } //delay

            } //container max-fragment-delay

            container max-links {
              description
                  "Configure the maximum number of MLPPP links";
              leaf max-links-id {
                type uint16 {
                  range "1..8";
                }
              } //max-links-id

            } //container max-links

            container reassembly-timeout {
              description
                  "Configure the reassembly timeout";
              leaf reassembly-timeout-id {
                type enumeration {
                  enum 100;
                  enum 1000;
                }
                description
                    "{100 | 1000} milliseconds";
              } //reassembly-timeout-id

            } //container reassembly-timeout

            container short-sequence-numbers {
              description
                  "Request the peer to send us short sequence numbers";
              leaf short-sequence-numbers-id {
                type enumeration {
                  enum always;
                  enum never;
                }
              } //short-sequence-numbers-id

            } //container short-sequence-numbers

          } //container mlppp

          container ppp {
            description
                "Configure PPP for the L2TP tunnel";
            container authentication {
              description
                  "Configure the PPP authentication protocol to negotiate";
              leaf authentication-id {
                type enumeration {
                  enum chap;
                  enum pap;
                  enum pref-chap;
                  enum pref-pap;
                }
              } //authentication-id

            } //container authentication

            container authentication-policy {
              description
                  "Configure the authentication policy";
              leaf auth-policy-name {
                type string {
                  length "1..32";
                }
              } //auth-policy-name

            } //container authentication-policy

            container chap-challenge-length {
              description
                  "Configure the maximum and minimum PPP CHAP challenge length";
              leaf min {
                type uint32 {
                  range "8..64";
                }
              } //min

              leaf max {
                type uint32 {
                  range "8..64";
                }
                description
                    "length";
              } //max

            } //container chap-challenge-length

            container default-group-interface {
              description
                  "Configure the default group interface";
              leaf ip-int-name {
                type string {
                  length "1..32";
                }
              } //ip-int-name

              leaf service-id {
                type string;
                description
                    "Attribute service-id for default-group-interface";
              } //service-id

              leaf service-name {
                type string {
                  length "1..64";
                }
              } //service-name

            } //container default-group-interface

            container ipcp-subnet-negotiation {
              description
                  "Configure the IPCP subnet negotiation";
              leaf ipcp-subnet-negotiation-id {
                type enumeration {
                  enum always;
                  enum never;
                }
              } //ipcp-subnet-negotiation-id

            } //container ipcp-subnet-negotiation

            container keepalive {
              description
                  "Configure the PPP keepalive interval and multiplier";
              leaf seconds {
                type uint32 {
                  range "10..300";
                }
              } //seconds

              leaf hold-up-multiplier {
                type uint32 {
                  range "1..5";
                }
              } //hold-up-multiplier

            } //container keepalive

            container lcp-force-ack-accm {
              description
                  "Force acknowledgement of the LCP Asynchronous Control Character Map (ACCM) 
                   configuration option during LCP negotiation, but don't do ACC mapping";
              leaf lcp-force-ack-accm-id {
                type enumeration {
                  enum always;
                  enum never;
                }
              } //lcp-force-ack-accm-id

            } //container lcp-force-ack-accm

            container lcp-ignore-magic-numbers {
              description
                  "Configure checking the Magic-Number field in LCP Echo-Request and LCP 
                   Echo-Reply messages";
              leaf lcp-ignore-magic-numbers-id {
                type enumeration {
                  enum always;
                  enum never;
                }
              } //lcp-ignore-magic-numbers-id

            } //container lcp-ignore-magic-numbers

            container mtu {
              description
                  "Configure the maximum PPP MTU size";
              leaf mtu-bytes {
                type uint32 {
                  range "512..9212";
                }
              } //mtu-bytes

            } //container mtu

            container proxy-authentication {
              description
                  "Configure the use of the Authentication AVPs received from the LAC";
              leaf proxy-authentication-id {
                type enumeration {
                  enum always;
                  enum never;
                }
              } //proxy-authentication-id

            } //container proxy-authentication

            container proxy-lcp {
              description
                  "Configure the use of the Proxy LCP AVPs received from the LAC";
              leaf proxy-lcp-id {
                type enumeration {
                  enum always;
                  enum never;
                }
              } //proxy-lcp-id

            } //container proxy-lcp

            container reject-disabled-ncp {
              description
                  "Force rejection of disabled Network Control Protocols (NCP)";
              leaf reject-disabled-ncp-id {
                type enumeration {
                  enum always;
                  enum never;
                }
              } //reject-disabled-ncp-id

            } //container reject-disabled-ncp

            container user-db {
              description
                  "Configure the local user database to use for PPP PAP/CHAP authentication";
              leaf local-user-db-name {
                type string {
                  length "1..32";
                }
              } //local-user-db-name

            } //container user-db

          } //container ppp

        } //list tunnel

      } //list group

      container l2tpv3 {
        description
            "Configure L2TP V3";
        container cookie-length {
          description
              "Configure the cookie length";
          leaf cookie-length-id {
            type enumeration {
              enum 4;
              enum 8;
            }
          } //cookie-length-id

        } //container cookie-length

        container digest-type {
          description
              "Configure the digest type";
          leaf digest-type-id {
            type enumeration {
              enum none;
              enum md5;
              enum sha1;
            }
          } //digest-type-id

        } //container digest-type

        container nonce-length {
          description
              "Configure the nonce length";
          leaf nonce-length-id {
            type uint32 {
              range "16..64";
            }
          } //nonce-length-id

        } //container nonce-length

        container password {
          description
              "Configure the password";
          leaf password {
            type string {
              length "1..512";
            }
            description
                "password - [64 chars max] 
                 hash-key 
                 hash2-key 
                 custom-key";
          } //password

          leaf hash-hash2-custom {
            type enumeration {
              enum hash;
              enum hash2;
              enum custom;
            }
          } //hash-hash2-custom

        } //container password

        container private-tcp-mss-adjust {
          description
              "Configure the TCP maximum segment size (MSS) on private network";
          leaf octets {
            type uint32 {
              range "512..9000";
            }
          } //octets

        } //container private-tcp-mss-adjust

        container public-tcp-mss-adjust {
          description
              "Configure the TCP maximum segment size (MSS) on public network";
          leaf octets {
            type uint32 {
              range "512..9000";
            }
          } //octets

        } //container public-tcp-mss-adjust

        container transport-type {
          description
              "Configure the transport type";
          leaf-list transport-type-id {
            type enumeration {
              enum ip;
            }
            max-elements 1;
          } //transport-type-id

        } //container transport-type

      } //container l2tpv3

      container tunnel-selection-blacklist {
        description
            "Configure the L2TP Tunnel Selection Blacklist";
        container add-tunnel {
          description
              "Configure the return codes or events that determine which tunnels are added to 
               the blacklist";
          leaf never {
            type boolean;
            description
                "Disable the tunnel-selection-blacklist";
          } //never

          leaf-list on {
            type enumeration {
              enum addr-change-timeout;
              enum cdn-err-code;
              enum cdn-inv-dest;
              enum cdn-tmp-no-facilities;
              enum cdn-perm-no-facilities;
              enum stop-ccn-err-code;
              enum stop-ccn-other;
              enum tx-cdn-not-established-in-time;
            }
            max-elements 8;
          } //on

        } //container add-tunnel

        container max-list-length {
          description
              "Configure the amount of tunnels or peers that can be in the blacklist at the 
               same time";
          leaf unlimited {
            type boolean;
          } //unlimited

          leaf count {
            type uint32 {
              range "1..65535";
            }
          } //count

        } //container max-list-length

        container max-time {
          description
              "Configure the maximum time a tunnel or peer may remain in the blacklist";
          leaf minutes {
            type uint32 {
              range "1..60";
            }
          } //minutes

        } //container max-time

        container timeout-action {
          description
              "Action to be taken when a tunnel or peer has been in the blacklist for the 
               maximum time specified";
          leaf action {
            type enumeration {
              enum remove-from-blacklist;
              enum try-one-session;
            }
          } //action

        } //container timeout-action

      } //container tunnel-selection-blacklist

    } //container l2tp

  } //grouping alu-conf-router-l2tp-r13

} //module  alu-conf-router-l2tp-r13
