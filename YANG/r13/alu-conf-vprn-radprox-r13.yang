module alu-conf-vprn-radprox-r13 {
  yang-version "1";

  namespace "urn:alcatel-lucent.com:sros:ns:yang:conf-vprn-radprox-r13";

  prefix "conf-vprn-radprox-r13";

  import alu-types {
    prefix "alu";
  }
  import ietf-inet-types {
    prefix "inet";
  }

  alu:alu-major-release "rel19";

  organization "Alcatel-Lucent";

  contact
      "Alcatel-Lucent SR OS Support 
       Web: <http://www.alcatel-lucent.com>";

  description
      "Alcatel-Lucent YANG Data model to configure RADIUS Proxy for VPRN services on 
       SR OS based routers. 
       
       Copyright 2014-2015 Alcatel-Lucent, 2016 Nokia. All rights reserved. 
       Reproduction of this document is authorized on the condition that the 
       foregoing copyright notice is included. 
       
       This alu-conf-vprn-radprox-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-vprn-radprox-r13 {
    container radius-proxy {
      description
          "Configure RADIUS Proxy for VPRN services";
      list server {
        key "server-name";
        description
            "Configure a RADIUS Proxy server";
        leaf server-name {
          type string {
            length "1..32";
          }
        } //server-name

        leaf-list purpose {
          type enumeration {
            enum accounting;
            enum authentication;
          }
          max-elements 2;
        } //purpose

        leaf wlan-gw-group {
          type uint32 {
            range "1..4";
          }
        } //wlan-gw-group

        container default-accounting-server-policy {
          description
              "Configure the default accounting RADIUS server policy";
          leaf policy-name {
            type string {
              length "1..32";
            }
          } //policy-name

        } //container default-accounting-server-policy

        container default-authentication-server-policy {
          description
              "Configure the default authentication RADIUS server policy";
          leaf policy-name {
            type string {
              length "1..32";
            }
          } //policy-name

        } //container default-authentication-server-policy

        container description {
          description
              "Configure the description";
          leaf description-string {
            type string {
              length "1..80";
            }
          } //description-string

        } //container description

        list interface {
          key "interface-name";
          description
              "Associate an interface";
          leaf interface-name {
            type string {
              length "1..32";
            }
            description
                "[32 chars max] (must start with a letter)";
          } //interface-name

        } //list interface

        container load-balance-key {
          description
              "Configure how to construct the key for load-balancing RADIUS messages between 
               RADIUS servers";
          leaf source-ip-udp {
            type boolean;
          } //source-ip-udp

          leaf-list vendor {
            type uint32 {
              range "0..16777215";
            }
            max-elements 5;
          } //vendor

          leaf-list attribute-type {
            type uint32 {
              range "1..255";
            }
            max-elements 5;
          } //attribute-type

        } //container load-balance-key

        container python-policy {
          description
              "Configure the Python policy";
          leaf name {
            type string {
              length "1..32";
            }
          } //name

        } //container python-policy

        container secret {
          description
              "Configure the secret";
          leaf secret {
            type string {
              length "1..500";
            }
            description
                "password - [64 chars max] 
                 hash-key 
                 hash2-key 
                 custom-key";
          } //secret

          leaf hash-hash2-custom {
            type enumeration {
              enum hash;
              enum hash2;
              enum custom;
            }
          } //hash-hash2-custom

        } //container secret

        leaf send-accounting-response {
          type boolean;
          description
              "Enable/disable responding to accounting-request messages";
        }

        leaf shutdown {
          type boolean;
          description
              "Administratively enable or disable the RADIUS Proxy server";
        }

        list username {
          key "username-id";
          status "obsolete";
          description
              "Configure username-to-RADIUS-Server-Policy associations";
          leaf username-id {
            type uint8 {
              range "1..32";
            }
          } //username-id

          leaf prefix-string {
            type string {
              length "1..128";
            }
            description
                "[128 characters max; the prefix and suffix together must not exceed 126 
                 characters]";
          } //prefix-string

          leaf accounting-server-policy {
            type string {
              length "1..32";
            }
          } //accounting-server-policy

          leaf authentication-server-policy {
            type string {
              length "1..32";
            }
            description
                "policy-name";
          } //authentication-server-policy

          leaf suffix-string {
            type string {
              length "1..126";
            }
            description
                "[126 characters max; the prefix and suffix together must not exceed 126 
                 characters]";
          } //suffix-string

        } //list username

        container attribute-matching {
          description
              "Configure RADIUS Server Policy associations";
          list entry {
            key "entry-id";
            description
                "Configure entry-to-RADIUS-Server-Policy associations";
            leaf entry-id {
              type uint8 {
                range "1..32";
              }
            } //entry-id

            leaf prefix-string {
              type string {
                length "1..128";
              }
              description
                  "[128 characters max; the prefix and suffix together must not exceed 126 
                   characters]";
            } //prefix-string

            leaf accounting-server-policy {
              type string {
                length "1..32";
              }
            } //accounting-server-policy

            leaf authentication-server-policy {
              type string {
                length "1..32";
              }
              description
                  "policy-name";
            } //authentication-server-policy

            leaf suffix-string {
              type string {
                length "1..126";
              }
              description
                  "[126 characters max; the prefix and suffix together must not exceed 126 
                   characters]";
            } //suffix-string

          } //list entry

          container type {
            description
                "Configure RADIUS Server Policy matching attribute-type and vendor-id";
            leaf type-id {
              type uint8 {
                range "1..255";
              }
            } //type-id

            leaf vendor-id {
              type string;
              description
                  "[1..16777215] | nokia";
            } //vendor-id

          } //container type

        } //container attribute-matching

        container cache {
          description
              "Configure caching";
          container key {
            description
                "Configure the cache key";
            leaf packet-type {
              type enumeration {
                enum accept;
                enum request;
              }
            } //packet-type

            leaf attribute-type {
              type uint8 {
                range "1..255";
              }
            } //attribute-type

            leaf vendor {
              type string;
              description
                  "[1..16777215] | nokia";
            } //vendor

          } //container key

          leaf shutdown {
            type boolean;
            description
                "Enable/disable caching";
          }

          container timeout {
            description
                "Configure the timeout";
            leaf hrs {
              type uint8 {
              }
            } //hrs

            leaf min {
              type uint8 {
                range "1..59";
              }
            } //min

            leaf sec {
              type uint8 {
                range "1..59";
              }
            } //sec

          } //container timeout

          container track-accounting {
            description
                "Configure what RADIUS accounting packets have impact on the cache";
            leaf start {
              type boolean;
            } //start

            leaf stop {
              type boolean;
            } //stop

            leaf interim-update {
              type boolean;
            } //interim-update

            leaf accounting-on {
              type boolean;
            } //accounting-on

            leaf accounting-off {
              type boolean;
            } //accounting-off

          } //container track-accounting

          container track-authentication {
            description
                "Configure what RADIUS authentication packets have impact on the cache";
            leaf accept {
              type boolean;
            } //accept

          } //container track-authentication

          container track-delete-hold-time {
            description
                "Configure the delete hold time";
            leaf seconds {
              type uint32 {
                range "0..600";
              }
            } //seconds

          } //container track-delete-hold-time

        } //container cache

        container wlan-gw {
          description
              "WLAN Gateway specific configuration";
          container address {
            description
                "Configure the IP address of this RADIUS Proxy server";
            leaf ip-address {
              type inet:ip-address;
            } //ip-address

          } //container address

          container ipv6-address {
            description
                "Configure the IPv6 address of this RADIUS Proxy server";
            leaf ipv6-address {
              type inet:ipv6-address;
              description
                  "Attribute ipv6-address for ipv6-address";
            } //ipv6-address

          } //container ipv6-address

        } //container wlan-gw

      } //list server

    } //container radius-proxy

  } //grouping alu-conf-vprn-radprox-r13

} //module  alu-conf-vprn-radprox-r13
