module alu-conf-ipv6-except-r13 {
  yang-version "1";

  namespace "urn:alcatel-lucent.com:sros:ns:yang:conf-ipv6-except-r13";

  prefix "conf-ipv6-except-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure an IPv6 exception filter on SR OS 
       based routers. 
       
       Copyright 2014-2015 Alcatel-Lucent, 2016 Nokia. All rights reserved. 
       Reproduction of this document is authorized on the condition that the 
       foregoing copyright notice is included. 
       
       This alu-conf-ipv6-except-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2022-09-21";

  grouping alu-conf-ipv6-except-r13 {
    list ipv6-exception {
      key "exception-id";
      description
          "Configure an IPv6 exception filter";
      leaf exception-id {
        type string;
        description
            "Attribute exception-id for ipv6-exception";
      } //exception-id

      leaf name {
        type string;
        description
            "[64 chars max]";
      } //name

      container description {
        description
            "Description for this IPv6 exception";
        leaf description-string {
          type string {
            length "1..80";
          }
        } //description-string

      } //container description

      container renum {
        description
            "Renumber an IPv6 exception entry";
        leaf old-entry-id {
          type uint32 {
            range "1..2097151";
          }
        } //old-entry-id

        leaf new-entry-id {
          type uint32 {
            range "1..2097151";
          }
        } //new-entry-id

      } //container renum

      list entry {
        key "entry-id";
        description
            "Configure an IPv6 exception entry";
        leaf entry-id {
          type uint32 {
            range "1..2097151";
          }
          description
              "Attribute entry-id for entry";
        } //entry-id

        container description {
          description
              "Description for this IPv6 exception entry";
          leaf description-string {
            type string {
              length "1..80";
            }
          } //description-string

        } //container description

        container match {
          description
              "Configure match criteria for this IPv6 exception entry";
          leaf next-header {
            type string;
            description
                "Attribute next-header for match";
          } //next-header

          container dst-ip {
            description
                "Configure destination IPv6 address match condition";
            leaf ipv6-address-prefix-length {
              type string;
              description
                  "<ipv6-address>/<prefix-length>";
            } //ipv6-address-prefix-length

            leaf ipv6-address {
              type inet:ipv6-address;
              description
                  "Attribute ipv6-address for dst-ip";
            } //ipv6-address

            leaf ipv6-address-mask {
              type inet:ipv6-address;
              description
                  "Attribute ipv6-address-mask for dst-ip";
            } //ipv6-address-mask

            leaf ipv6-prefix-list {
              type string {
                length "1..32";
              }
            } //ipv6-prefix-list

          } //container dst-ip

          container dst-port {
            description
                "Configure destination port match condition";
            leaf dst-port-id {
              type enumeration {
                enum lt;
                enum gt;
                enum eq;
              }
              description
                  "Attribute for dst-port";
            } //dst-port-id

            leaf dst-port-number {
              type string;
              description
                  "Attribute dst-port-number for dst-port";
            } //dst-port-number

            leaf-list range {
              type string;
              max-elements 2;
              description
                  "dst-port-number";
            } //range

            leaf port-list {
              type string {
                length "1..32";
              }
            } //port-list

          } //container dst-port

          container icmp-code {
            description
                "Configure ICMP code match condition";
            leaf icmp-code {
              type string;
              description
                  "Attribute icmp-code for icmp-code";
            } //icmp-code

          } //container icmp-code

          container icmp-type {
            description
                "Configure ICMP type match condition";
            leaf icmp-type {
              type string;
              description
                  "Attribute icmp-type for icmp-type";
            } //icmp-type

          } //container icmp-type

          container port {
            description
                "Configure port match condition";
            leaf port-id {
              type enumeration {
                enum lt;
                enum gt;
                enum eq;
              }
              description
                  "Attribute for port";
            } //port-id

            leaf port-number {
              type string;
              description
                  "Attribute port-number for port";
            } //port-number

            leaf-list range {
              type string;
              max-elements 2;
              description
                  "port-number";
            } //range

            leaf port-list {
              type string {
                length "1..32";
              }
            } //port-list

          } //container port

          container src-ip {
            description
                "Configure source IPv6 address match condition";
            leaf ipv6-address-prefix-length {
              type string;
              description
                  "<ipv6-address>/<prefix-length>";
            } //ipv6-address-prefix-length

            leaf ipv6-address {
              type inet:ipv6-address;
              description
                  "Attribute ipv6-address for src-ip";
            } //ipv6-address

            leaf ipv6-address-mask {
              type inet:ipv6-address;
              description
                  "Attribute ipv6-address-mask for src-ip";
            } //ipv6-address-mask

            leaf ipv6-prefix-list {
              type string {
                length "1..32";
              }
            } //ipv6-prefix-list

          } //container src-ip

          container src-port {
            description
                "Configure source port match condition";
            leaf src-port-id {
              type enumeration {
                enum lt;
                enum gt;
                enum eq;
              }
              description
                  "Attribute for src-port";
            } //src-port-id

            leaf src-port-number {
              type string;
              description
                  "Attribute src-port-number for src-port";
            } //src-port-number

            leaf-list range {
              type string;
              max-elements 2;
              description
                  "src-port-number";
            } //range

            leaf port-list {
              type string {
                length "1..32";
              }
            } //port-list

          } //container src-port

        } //container match

      } //list entry

    } //list ipv6-exception

  } //grouping alu-conf-ipv6-except-r13

} //module  alu-conf-ipv6-except-r13
