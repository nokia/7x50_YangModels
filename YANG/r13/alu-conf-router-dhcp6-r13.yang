module alu-conf-router-dhcp6-r13 {
  yang-version "1";

  namespace "urn:alcatel-lucent.com:sros:ns:yang:conf-router-dhcp6-r13";

  prefix "conf-router-dhcp6-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure local DHCPv6 servers on SR OS 
       based routers. 
       
       Copyright 2014-2015 Alcatel-Lucent, 2016 Nokia. All rights reserved. 
       Reproduction of this document is authorized on the condition that the 
       foregoing copyright notice is included. 
       
       This alu-conf-router-dhcp6-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-01-13";

  grouping alu-conf-router-dhcp6-r13 {
    container dhcp6 {
      description
          "Configure local DHCPv6 servers";
      list local-dhcp-server {
        key "server-name";
        description
            "Configure the local DHCPv6 server";
        leaf server-name {
          type string {
            length "1..32";
          }
        } //server-name

        leaf auto-provisioned {
          type boolean;
          description
              "keyword - no manual IP address configuration";
        } //auto-provisioned

        leaf allow-lease-query {
          type boolean;
          description
              "Enable/disable handling of Lease Query messages";
        }

        container description {
          description
              "Description for this local DHCPv6 server";
          leaf description-string {
            type string {
              length "1..80";
            }
          } //description-string

        } //container description

        leaf ignore-rapid-commit {
          type boolean;
          description
              "Enable/disable ignoring of Rapid Commit Option";
        }

        leaf interface-id-mapping {
          type boolean;
          description
              "Enable/disable interface-id mapping";
        }

        container lease-hold-time {
          description
              "Configure the lease hold time";
          leaf days {
            type uint32 {
              range "0..7305";
            }
          } //days

          leaf hrs {
            type uint32 {
              range "0..23";
            }
          } //hrs

          leaf min {
            type uint32 {
              range "0..59";
            }
          } //min

          leaf sec {
            type uint32 {
              range "0..59";
            }
          } //sec

        } //container lease-hold-time

        container server-id {
          description
              "Configure the DUID";
          leaf duid-ll {
            type boolean;
            description
                "keyword";
          } //duid-ll

          leaf duid-en {
            type boolean;
            description
                "keyword";
          } //duid-en

          leaf string {
            type string {
              length "1..58";
            }
          } //string

          leaf hex {
            type string {
              length "1..118";
            }
            description
                "[0x0..0xFFFFFFFF...(max 116 hex nibbles)]";
          } //hex

        } //container server-id

        leaf shutdown {
          type boolean;
          description
              "Administratively enable/disable the local DHCPv6 server";
        }

        container use-link-address {
          description
              "Configure the scope of the IP address selection";
          leaf scope {
            type enumeration {
              enum subnet;
              enum pool;
            }
          } //scope

        } //container use-link-address

        leaf use-pool-from-client {
          type boolean;
          description
              "Enable/disable use of pool indicated by DHCP client";
        }

        container user-ident {
          description
              "Configure the user identification method";
          leaf user-ident {
            type enumeration {
              enum duid;
              enum interface-id;
              enum interface-id-link-local;
            }
            description
                "duid|interface-id|interface-id-link-local";
          } //user-ident

        } //container user-ident

        container defaults {
          description
              "Configure server default values";
          container preferred-lifetime {
            description
                "Configure the default time for a prefix to remain preferred";
            leaf days {
              type uint32 {
                range "0..3650";
              }
            } //days

            leaf hrs {
              type uint32 {
                range "0..23";
              }
            } //hrs

            leaf min {
              type uint32 {
                range "0..59";
              }
            } //min

            leaf sec {
              type uint32 {
                range "0..59";
              }
            } //sec

          } //container preferred-lifetime

          container rebind-timer {
            description
                "Configure the default rebind timer";
            leaf days {
              type uint32 {
                range "0..14";
              }
            } //days

            leaf hrs {
              type uint32 {
                range "0..23";
              }
            } //hrs

            leaf min {
              type uint32 {
                range "0..59";
              }
            } //min

            leaf sec {
              type uint32 {
                range "0..59";
              }
            } //sec

          } //container rebind-timer

          container renew-timer {
            description
                "Configure the default renew timer";
            leaf days {
              type uint32 {
                range "0..7";
              }
            } //days

            leaf hrs {
              type uint32 {
                range "0..23";
              }
            } //hrs

            leaf min {
              type uint32 {
                range "0..59";
              }
            } //min

            leaf sec {
              type uint32 {
                range "0..59";
              }
            } //sec

          } //container renew-timer

          container valid-lifetime {
            description
                "Configure time for a prefix to remain valid";
            leaf days {
              type uint32 {
                range "0..3650";
              }
            } //days

            leaf hrs {
              type uint32 {
                range "0..23";
              }
            } //hrs

            leaf min {
              type uint32 {
                range "0..59";
              }
            } //min

            leaf sec {
              type uint32 {
                range "0..59";
              }
            } //sec

          } //container valid-lifetime

          container options {
            description
                "Configure default DHCP options";
            list custom-option {
              key "option-number";
              description
                  "Configure a DHCP option";
              leaf option-number {
                type uint32 {
                  range "1..65535";
                }
              } //option-number

              leaf-list address {
                type inet:ipv6-address;
                max-elements 4;
                description
                    "Attribute ipv6-address for custom-option";
              } //address

              leaf string {
                type string {
                  length "1..127";
                }
              } //string

              leaf hex {
                type string {
                }
                description
                    "[0x0..0xFFFFFFFF...(max 254 hex nibbles)]";
              } //hex

              leaf domain {
                type string {
                  length "1..127";
                }
              } //domain

            } //list custom-option

            container dns-server {
              description
                  "Configure the DNS server";
              leaf-list ipv6-address {
                type inet:ipv6-address;
                max-elements 4;
                description
                    "Attribute ipv6-address for dns-server";
              } //ipv6-address

            } //container dns-server

            container domain-name {
              description
                  "Configure the domain name";
              leaf domain-name {
                type string {
                  length "1..127";
                }
              } //domain-name

            } //container domain-name

          } //container options

        } //container defaults

        container failover {
          description
              "Configure failover";
          leaf ignore-mclt-on-takeover {
            type boolean;
            description
                "Ignore the Maximum Client Lead Time delay while taking over the peer address 
                 space";
          }

          container maximum-client-lead-time {
            description
                "Configure the maximum client lead time";
            leaf hrs {
              type int32 {
                range "1..23";
              }
            } //hrs

            leaf min {
              type int32 {
                range "1..59";
              }
            } //min

            leaf sec {
              type int32 {
                range "1..59";
              }
            } //sec

          } //container maximum-client-lead-time

          container partner-down-delay {
            description
                "Configure the partner-down delay";
            leaf hrs {
              type int32 {
                range "1..23";
              }
            } //hrs

            leaf min {
              type int32 {
                range "1..59";
              }
            } //min

            leaf sec {
              type int32 {
                range "0..59";
              }
            } //sec

          } //container partner-down-delay

          container peer {
            description
                "Create a sync tag";
            leaf ip-address {
              type string;
              description
                  "Attribute ip-address for peer";
            } //ip-address

            leaf tag {
              type string {
                length "1..32";
              }
            } //tag

          } //container peer

          leaf shutdown {
            type boolean;
            description
                "Administratively enable/disable the failover facility";
          }

          container startup-wait-time {
            description
                "Configure the startup wait time";
            leaf min {
              type int32 {
                range "1..59";
              }
            } //min

            leaf sec {
              type int32 {
                range "1..59";
              }
            } //sec

            leaf hrs {
              type uint32 {
              }
            } //hrs

          } //container startup-wait-time

        } //container failover

        container lease-hold-time-for {
          presence
              "Configure additional cases to apply the lease-hold-time to (other than 
               unsolicited releases)";
          leaf internal-lease-ipsec {
            type boolean;
            description
                "Apply the lease hold timer also to internal ipsec leases";
          }

          leaf solicited-release {
            type boolean;
            description
                "Apply the lease hold timer also for solicited releases";
          }

        } //container lease-hold-time-for

        list pool {
          key "pool-name";
          description
              "Configure an IP address pool";
          leaf pool-name {
            type string {
              length "1..32";
            }
          } //pool-name

          container delegated-prefix-length {
            description
                "Configure IPv6 delegated prefix length";
            leaf prefix-length {
              type uint32 {
                range "48..127";
              }
            } //prefix-length

            leaf minimum {
              type uint32 {
                range "48..127";
              }
              description
                  "prefix-length";
            } //minimum

            leaf maximum {
              type uint32 {
                range "48..127";
              }
              description
                  "prefix-length";
            } //maximum

          } //container delegated-prefix-length

          container description {
            description
                "Description for this IP address pool";
            leaf description-string {
              type string {
                length "1..80";
              }
            } //description-string

          } //container description

          list exclude-prefix {
            key "ipv6-prefix-prefix-length";
            description
                "Configure a prefix to be excluded from the pool";
            leaf ipv6-prefix-prefix-length {
              type string;
              description
                  "Attribute ipv6-prefix/prefix-length for exclude-prefix";
            } //ipv6-prefix-prefix-length

          } //list exclude-prefix

          container failover {
            description
                "Configure failover";
            leaf ignore-mclt-on-takeover {
              type boolean;
              description
                  "Ignore the Maximum Client Lead Time delay while taking over the pool address 
                   space from the partner";
            }

            container maximum-client-lead-time {
              description
                  "Configure the maximum client lead time";
              leaf hrs {
                type int32 {
                  range "1..23";
                }
              } //hrs

              leaf min {
                type int32 {
                  range "1..59";
                }
              } //min

              leaf sec {
                type int32 {
                  range "1..59";
                }
              } //sec

            } //container maximum-client-lead-time

            container partner-down-delay {
              description
                  "Configure the partner-down delay";
              leaf hrs {
                type int32 {
                  range "1..23";
                }
              } //hrs

              leaf min {
                type int32 {
                  range "1..59";
                }
              } //min

              leaf sec {
                type int32 {
                  range "0..59";
                }
              } //sec

            } //container partner-down-delay

            container peer {
              description
                  "Create a sync tag";
              leaf ip-address {
                type string;
                description
                    "Attribute ip-address for peer";
              } //ip-address

              leaf tag {
                type string {
                  length "1..32";
                }
              } //tag

            } //container peer

            leaf shutdown {
              type boolean;
              description
                  "Administratively enable/disable the failover facility";
            }

            container startup-wait-time {
              description
                  "Configure the startup wait time";
              leaf min {
                type int32 {
                  range "1..59";
                }
              } //min

              leaf sec {
                type int32 {
                  range "1..59";
                }
              } //sec

              leaf hrs {
                type uint32 {
                }
              } //hrs

            } //container startup-wait-time

          } //container failover

          container options {
            description
                "Configure pool-specific DHCP options";
            list custom-option {
              key "option-number";
              description
                  "Configure a DHCP option";
              leaf option-number {
                type uint32 {
                  range "1..65535";
                }
              } //option-number

              leaf-list address {
                type inet:ipv6-address;
                max-elements 4;
                description
                    "Attribute ipv6-address for custom-option";
              } //address

              leaf string {
                type string {
                  length "1..127";
                }
              } //string

              leaf hex {
                type string {
                }
                description
                    "[0x0..0xFFFFFFFF...(max 254 hex nibbles)]";
              } //hex

              leaf domain {
                type string {
                  length "1..127";
                }
              } //domain

            } //list custom-option

            container dns-server {
              description
                  "Configure the DNS server";
              leaf-list ipv6-address {
                type inet:ipv6-address;
                max-elements 4;
                description
                    "Attribute ipv6-address for dns-server";
              } //ipv6-address

            } //container dns-server

            container domain-name {
              description
                  "Configure the domain name";
              leaf domain-name {
                type string {
                  length "1..127";
                }
              } //domain-name

            } //container domain-name

          } //container options

          list prefix {
            key "ipv6-address-prefix-length";
            description
                "Configure a prefix";
            leaf ipv6-address-prefix-length {
              type string;
              description
                  "ipv6-address x:x:x:x:x:x:x:x (eight 16-bit pieces) 
                   x:x:x:x:x:x:d.d.d.d 
                   x [0..FFFF]H 
                   d [0..255]D 
                   prefix-length [1..128]";
            } //ipv6-address-prefix-length

            leaf failover {
              type enumeration {
                enum local;
                enum remote;
                enum access-driven;
              }
            } //failover

            leaf pd {
              type boolean;
            } //pd

            leaf wan-host {
              type boolean;
            } //wan-host

            leaf drain {
              type boolean;
              description
                  "Configure prefix draining";
            }

            container preferred-lifetime {
              description
                  "Configure time for prefix to remain preferred";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

            } //container preferred-lifetime

            container rebind-timer {
              description
                  "Configure the rebind timer";
              leaf days {
                type uint32 {
                  range "0..14";
                }
              } //days

              leaf hrs {
                type uint32 {
                  range "0..23";
                }
              } //hrs

              leaf min {
                type uint32 {
                  range "0..59";
                }
              } //min

              leaf sec {
                type uint32 {
                  range "0..59";
                }
              } //sec

            } //container rebind-timer

            container renew-timer {
              description
                  "Configure the renew timer";
              leaf days {
                type uint32 {
                  range "0..7";
                }
              } //days

              leaf hrs {
                type uint32 {
                  range "0..23";
                }
              } //hrs

              leaf min {
                type uint32 {
                  range "0..59";
                }
              } //min

              leaf sec {
                type uint32 {
                  range "0..59";
                }
              } //sec

            } //container renew-timer

            container valid-lifetime {
              description
                  "Configure time for prefix to remain valid";
              leaf days {
                type uint32 {
                  range "0..3650";
                }
              } //days

              leaf hrs {
                type uint32 {
                  range "0..23";
                }
              } //hrs

              leaf min {
                type uint32 {
                  range "0..59";
                }
              } //min

              leaf sec {
                type uint32 {
                  range "0..59";
                }
              } //sec

            } //container valid-lifetime

            container options {
              description
                  "Configure prefix-specific DHCP options";
              list custom-option {
                key "option-number";
                description
                    "Configure a DHCP option";
                leaf option-number {
                  type uint32 {
                    range "1..65535";
                  }
                } //option-number

                leaf-list address {
                  type inet:ipv6-address;
                  max-elements 4;
                  description
                      "Attribute ipv6-address for custom-option";
                } //address

                leaf string {
                  type string {
                    length "1..127";
                  }
                } //string

                leaf hex {
                  type string {
                  }
                  description
                      "[0x0..0xFFFFFFFF...(max 254 hex nibbles)]";
                } //hex

                leaf domain {
                  type string {
                    length "1..127";
                  }
                } //domain

              } //list custom-option

              container dns-server {
                description
                    "Configure the DNS server";
                leaf-list ipv6-address {
                  type inet:ipv6-address;
                  max-elements 4;
                  description
                      "Attribute ipv6-address for dns-server";
                } //ipv6-address

              } //container dns-server

              container domain-name {
                description
                    "Configure the domain name";
                leaf domain-name {
                  type string {
                    length "1..127";
                  }
                } //domain-name

              } //container domain-name

            } //container options

            container thresholds {
              description
                  "Configure address prefix thresholds";
              list minimum-free {
                key "prefix-length";
                description
                    "Configure the minimum ratio of free prefixes for a given prefix length";
                leaf prefix-length {
                  type uint32 {
                    range "1..128";
                  }
                } //prefix-length

                leaf depleted-event {
                  type boolean;
                  description
                      "Enable/disable sending an event when the prefixes of this length are depleted";
                }

                container minimum {
                  description
                      "Configure the minimum ratio of free prefixes for a given prefix length";
                  leaf percent {
                    type uint32 {
                      range "0..100";
                    }
                  } //percent

                  leaf number {
                    type uint32;
                  } //number

                } //container minimum

              } //list minimum-free

            } //container thresholds

          } //list prefix

          container thresholds {
            description
                "Configure address pool thresholds";
            list minimum-free {
              key "prefix-length";
              description
                  "Configure the minimum ratio of free prefixes for a given prefix length";
              leaf prefix-length {
                type uint32 {
                  range "1..128";
                }
              } //prefix-length

              leaf depleted-event {
                type boolean;
                description
                    "Enable/disable sending an event when the prefixes of this length are depleted";
              }

              container minimum {
                description
                    "Configure the minimum ratio of free prefixes for a given prefix length";
                leaf percent {
                  type uint32 {
                    range "0..100";
                  }
                } //percent

              } //container minimum

            } //list minimum-free

          } //container thresholds

        } //list pool

      } //list local-dhcp-server

    } //container dhcp6

  } //grouping alu-conf-router-dhcp6-r13

} //module  alu-conf-router-dhcp6-r13
