module alu-conf-svc-vprn-wpp-r13 {
  yang-version "1";

  namespace "urn:alcatel-lucent.com:sros:ns:yang:conf-svc-vprn-wpp-r13";

  prefix "conf-svc-vprn-wpp-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure Web Portal Protocol for VPRN 
       services on SR OS based routers. 
       
       Copyright 2014-2015 Alcatel-Lucent, 2016 Nokia. All rights reserved. 
       Reproduction of this document is authorized on the condition that the 
       foregoing copyright notice is included. 
       
       This alu-conf-svc-vprn-wpp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-12-11";

  grouping alu-conf-svc-vprn-wpp-r13 {
    container wpp {
      presence
          "Configure Web Portal Protocol for VPRN services";
      leaf shutdown {
        type boolean;
        description
            "Enable/disable WPP";
      }

      container portals {
        description
            "Configure WPP portals";
        list portal {
          key "wpp-portal-name";
          description
              "Configure a Web Portal Protocol portal";
          leaf wpp-portal-name {
            type string {
              length "1..32";
            }
          } //wpp-portal-name

          leaf address {
            type inet:ip-address;
            description
                "Attribute ip-address for portal";
          } //address

          container ack-auth-retry-count {
            description
                "Configure the number of retransmissions of an ACK_OUT message";
            leaf ack-auth-retry-count-id {
              type uint32 {
                range "0..5";
              }
            } //ack-auth-retry-count-id

          } //container ack-auth-retry-count

          container ntf-logout-retry-count {
            description
                "Configure the number of retransmissions of an NTF_LOGOUT message";
            leaf ntf-logout-retry-count-id {
              type uint32 {
                range "0..5";
              }
            } //ntf-logout-retry-count-id

          } //container ntf-logout-retry-count

          container port-format {
            description
                "Configure the format of the port in the ACK_INFO message";
            leaf formatting {
              type enumeration {
                enum standard;
                enum vendor-specific;
              }
            } //formatting

          } //container port-format

          container retry-interval {
            description
                "Configure the time interval between two consecutive retransmissions";
            leaf milliseconds {
              type uint32 {
                range "10..2000";
              }
            } //milliseconds

          } //container retry-interval

          container secret {
            description
                "Configure the secret";
            leaf secret {
              type string {
                length "1..500";
              }
              description
                  "password - [64 chars max] 
                   hash-key 
                   hash2-key 
                   custom-key";
            } //secret

            leaf hash-hash2-custom {
              type enumeration {
                enum hash;
                enum hash2;
                enum custom;
              }
            } //hash-hash2-custom

          } //container secret

          leaf shutdown {
            type boolean;
            description
                "Administratively enable or disable a portal";
          }

          container version {
            description
                "Configure the version";
            leaf version {
              type int32 {
                range "1..2";
              }
            } //version

          } //container version

        } //list portal

      } //container portals

    } //container wpp

  } //grouping alu-conf-svc-vprn-wpp-r13

} //module  alu-conf-svc-vprn-wpp-r13
