submodule nokia-conf-svc-ipipe {

    yang-version "1.1";

    belongs-to nokia-conf { prefix "conf"; }

    import ietf-yang-types                { prefix "yang"; }
    import nokia-sros-yang-extensions     { prefix "sros-ext"; }
    import nokia-types-qos                { prefix "types-qos"; }
    import nokia-types-services           { prefix "types-services"; }
    import nokia-types-sros               { prefix "types-sros"; }

    include nokia-conf-aa-group;
    include nokia-conf-application-assurance;
    include nokia-conf-bfd;
    include nokia-conf-eth-cfm;
    include nokia-conf-filter;
    include nokia-conf-groups;
    include nokia-conf-log;
    include nokia-conf-port;
    include nokia-conf-port-eth-access;
    include nokia-conf-port-ethernet;
    include nokia-conf-qos;
    include nokia-conf-service;
    include nokia-conf-system;
    include nokia-conf-system-security;

    sros-ext:sros-major-release "rel26";
    organization "Nokia";
    contact
        "Nokia SR OS Support
         Web: <http://www.nokia.com>";
    description
        "Nokia YANG Data model to configure ipipe services on SR OS based routers.

         Copyright 2016 Nokia. All rights reserved. Reproduction of this document
         is authorized on the condition that the foregoing copyright notice is included.

         This nokia-conf-svc-ipipe YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping conf-svc-ipipe {
        list ipipe {
            key "service-name";
            description "Enter the ipipe list instance";

            leaf service-name {
                type types-services:service-name;
                description "Administrative service name";
            }

            leaf service-id {
                type types-services:external-service-id;
                sros-ext:immutable;
                description "Service ID";
            }

            leaf description {
                type types-sros:description;
                description "Text description";
            }

            leaf customer {
                type leafref {
                    path "../../customer/customer-name";
                }
                sros-ext:immutable;
                mandatory true;
                description "Service customer ID";
            }

            leaf admin-state {
                type types-sros:admin-state;
                default "disable";
                description "Administrative state of the service";
            }

            leaf vpn-id {
                type types-services:vpn-id;
                sros-ext:immutable;
                description "VPN identifier for the service";
            }

            leaf vc-switching {
                type boolean;
                sros-ext:immutable;
                default "false";
                description "Use PW switching signaling for spoke SDPs in service";
            }

            leaf service-mtu {
                type int32 {
                    range "1..9194";
                }
                description "MTU size";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container ce-address-discovery {
                presence "Enable the ce-address-discovery context";
                description "Enable the ce-address-discovery context";

            } // container ce-address-discovery



            list endpoint {
                key "name";
                max-elements 2;
                description "Enter the endpoint list instance";

                leaf name {
                    type types-sros:named-item;
                    description "Service endpoint name";
                }

                leaf description {
                    type types-sros:description;
                    description "Text description";
                }

                leaf revert-time {
                    type types-services:revert-time;
                    default "immediate";
                    description "Time to wait before reverting to primary spoke SDP";
                }

                leaf hold-time-active {
                    type types-services:hold-time-active;
                    description "Time before entering standby when MC-LAG SAP goes down";
                }

                leaf standby-signaling {
                    type enumeration {
                        enum master                         { value 1; }
                    }
                    description "Endpoint behavior for status of sending PW standby bit";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list endpoint

            list sap {
                key "sap-id";
                description "Enter the sap list instance";

                leaf sap-id {
                    type types-sros:sap;
                    description "SAP ID";
                }

                leaf description {
                    type types-sros:long-description;
                    description "Text description";
                }

                leaf admin-state {
                    type types-sros:admin-state;
                    default "enable";
                    description "Administrative state of the SAP";
                }

                leaf accounting-policy {
                    type leafref {
                        path "../../../../log/accounting-policy/policy-id";
                    }
                    description "Accounting policy";
                }

                leaf app-profile {
                    type leafref {
                        path "../../../../application-assurance/group/partition/policy/app-profile/app-profile-name";
                    }
                    description "Application profile name";
                }

                leaf bandwidth {
                    type types-services:sap-bandwidth;
                    units "kilobps";
                    description "SAP bandwidth";
                }

                leaf collect-stats {
                    type boolean;
                    default "false";
                    description "Collect accounting statistics";
                }

                leaf dist-cpu-protection {
                    type leafref {
                        path "../../../../system/security/dist-cpu-protection/policy/policy-name";
                    }
                    description "Distributed CPU protection policy for SAP";
                }

                leaf multi-service-site {
                    type leafref {
                        path "../../../customer/multi-service-site/multi-service-site-name";
                    }
                    description "Multi service site name";
                }

                leaf endpoint {
                    type leafref {
                        path "../../endpoint/name";
                    }
                    description "Endpoint name";
                }

                leaf ce-address {
                    type types-sros:ip-address;
                    description "IP address of the CE device";
                }

                leaf mac-refresh {
                    type uint32 {
                        range "0..65535";
                    }
                    default "14400";
                    description "MAC refresh interval";
                }

                leaf mac {
                    type yang:mac-address;
                    default "00:00:00:00:00:00";
                    description "MAC address of the Ipipe Ethernet SAP";
                }

                leaf use-broadcast-mac {
                    type boolean;
                    default "false";
                    description "Allow broadcast MAC on SAP";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container transit-policy {
                    presence "Enable the transit-policy context";
                    description "Enable the transit-policy context";

                    choice transit-policy {
                        mandatory true;
                        case prefix {

                            leaf prefix {
                                type leafref {
                                    path "../../../../../application-assurance/group/partition/transit-prefix-policy/prefix-policy-id";
                                }
                                sros-ext:immutable;
                                description "IP prefix policy ID";
                            }

                        }
                    }
                } // container transit-policy

                container ingress {
                    description "Enter the ingress context";

                    container qos {
                        description "Enter the qos context";

                        leaf match-qinq-dot1p {
                            type enumeration {
                                enum top                            { value 2; }
                                enum bottom                         { value 3; }
                            }
                            description "Ingress match QinQ Dot1p";
                        }

                        container sap-ingress {
                            description "Enter the sap-ingress context";

                            leaf policy-name {
                                type leafref {
                                    path "../../../../../../../qos/sap-ingress/sap-ingress-policy-name";
                                }
                                description "Policy ID";
                            }

                            leaf queuing-type {
                                type types-services:services-sap-queuing-type;
                                description "Queuing type";
                            }

                            container fp-redirect-group {
                                description "Enter the fp-redirect-group context";

                                leaf group-name {
                                    type leafref {
                                        path "../../../../../../../../qos/queue-group-templates/ingress/queue-group/ingress-queue-group-name";
                                    }
                                    description "Queue group template name created on forwarding plane";
                                }

                                leaf instance {
                                    type types-services:qos-qgrp-instance-id;
                                    description "Queue group instance";
                                }

                            } // container fp-redirect-group

                            container overrides {
                                description "Enter the overrides context";

                                list queue {
                                    key "queue-id";
                                    description "Enter the queue list instance";

                                    leaf queue-id {
                                        type leafref {
                                            path "../../../../../../../../../qos/sap-ingress[sap-ingress-policy-name=current()/../../../policy-name]/queue/queue-id";
                                        }
                                        description "Policer unique ID";
                                    }

                                    leaf cbs {
                                        type union {
                                            type uint32 {
                                                range "0..2097151";
                                            }
                                            type enumeration {
                                                enum auto                           { value -1; }
                                            }
                                        }
                                        units "kilobytes";
                                        description "CBS";
                                    }

                                    leaf mbs {
                                        type union {
                                            type types-qos:bytes {
                                                range "0..2147482624";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                    } // container monitor-queue-depth

                                } // list queue

                                list policer {
                                    key "policer-id";
                                    description "Enter the policer list instance";

                                    leaf policer-id {
                                        type leafref {
                                            path "../../../../../../../../../qos/sap-ingress[sap-ingress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:ingress-per-packet-offset-override;
                                        description "Packet size modification for policing information";
                                    }

                                    leaf stat-mode {
                                        type types-qos:ingress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                            } // container overrides

                        } // container sap-ingress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos

                    container filter {
                        description "Enter the filter context";

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                } // container ingress

                container egress {
                    description "Enter the egress context";

                    choice agg-rate-or-percent-agg-rate {
                        default "agg-rate";
                        case agg-rate {

                            container agg-rate {
                                description "Enter the agg-rate context";

                                leaf limit-unused-bandwidth {
                                    type boolean;
                                    default "false";
                                    description "Enable aggregate rate overrun protection";
                                }

                                leaf rate {
                                    type types-services:agg-rate-rate;
                                    units "kilobps";
                                    description "Enforced aggregate rate for all queues";
                                }

                                leaf burst-limit {
                                    type union {
                                        type types-qos:bytes {
                                            range "1..14000000";
                                        }
                                        type enumeration {
                                            enum auto                           { value -1; }
                                        }
                                    }
                                    default "auto";
                                    description "Shaping burst size when an aggregate shaper is used";
                                }

                                leaf adaptation-rule {
                                    type types-qos:adaptation-rule;
                                    default "closest";
                                    description "Adaptation rule to compute the operational PIR value when an aggregate shaper is used";
                                }

                            } // container agg-rate

                        }
                    }
                    container qos {
                        description "Enter the qos context";

                        leaf qinq-mark-top-only {
                            type boolean;
                            default "false";
                            description "Mark top Q-tags";
                        }

                        container sap-egress {
                            description "Enter the sap-egress context";

                            leaf policy-name {
                                type leafref {
                                    path "../../../../../../../qos/sap-egress/sap-egress-policy-name";
                                }
                                description "Policy ID to associate with SAP for mirrored service";
                            }

                            container port-redirect-group {
                                description "Enter the port-redirect-group context";

                                leaf group-name {
                                    type leafref {
                                        path "../../../../../../../../qos/queue-group-templates/egress/queue-group/egress-queue-group-name";
                                    }
                                    description "Name of the queue group redirect list policy";
                                }

                                leaf instance {
                                    type types-services:qos-qgrp-instance-id;
                                    description "Instance of port queue group";
                                }

                            } // container port-redirect-group

                            container overrides {
                                description "Enter the overrides context";

                                leaf hs-secondary-shaper {
                                    type types-sros:named-item;
                                    description "HS Secondary Shaper";
                                }

                                list queue {
                                    key "queue-id";
                                    description "Enter the queue list instance";

                                    leaf queue-id {
                                        type leafref {
                                            path "../../../../../../../../../qos/sap-egress[sap-egress-policy-name=current()/../../../policy-name]/queue/queue-id";
                                        }
                                        description "Policer unique ID";
                                    }

                                    leaf avg-frame-overhead {
                                        type decimal64 {
                                            range "0.00..100.00";
                                            fraction-digits 2;
                                        }
                                        description "Average packet-to-frame encapsulation overhead";
                                    }

                                    leaf burst-limit {
                                        type union {
                                            type types-qos:bytes {
                                                range "1..14000000";
                                            }
                                            type enumeration {
                                                enum auto                           { value -1; }
                                            }
                                        }
                                        description "Explicit shaping burst size for the queue";
                                    }

                                    leaf cbs {
                                        type union {
                                            type uint32 {
                                                range "0..2097151";
                                            }
                                            type enumeration {
                                                enum auto                           { value -1; }
                                            }
                                        }
                                        units "kilobytes";
                                        description "CBS";
                                    }

                                    leaf mbs {
                                        type union {
                                            type types-qos:bytes {
                                                range "0..2147482624";
                                            }
                                            type enumeration {
                                                enum auto                           { value -1; }
                                            }
                                        }
                                        units "bytes";
                                        description "MBS";
                                    }

                                    leaf monitor-depth {
                                        status obsolete;
                                        type boolean;
                                        default "false";
                                        description "Monitor queue depth";
                                    }

                                    leaf hs-wrr-weight {
                                        type types-qos:hs-wrr-weight-override;
                                        default "1";
                                        description "WRR weight to parent with the queue into the scheduler";
                                    }

                                    leaf hs-class-weight {
                                        type types-qos:hs-class-weight-override;
                                        description "Class weight override for the queue";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice queue-override-rate {
                                        case rate {

                                            container rate {
                                                description "Enter the rate context";

                                                leaf pir {
                                                    type types-services:sap-pir-rate-ovr;
                                                    units "kilobps";
                                                    description "PIR rate";
                                                }

                                                leaf cir {
                                                    type types-services:sap-cir-rate-ovr;
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                    container adaptation-rule {
                                        description "Enter the adaptation-rule context";

                                        leaf pir {
                                            type types-qos:adaptation-rule-override;
                                            description "Constraint used when deriving the operational PIR value";
                                        }

                                        leaf cir {
                                            type types-qos:adaptation-rule-override;
                                            description "Constraint used when deriving the operational CIR value";
                                        }

                                    } // container adaptation-rule

                                    container drop-tail {
                                        description "Enter the drop-tail context";

                                        container low {
                                            description "Enter the low context";

                                            leaf percent-reduction-from-mbs {
                                                type types-qos:burst-percent-or-default-override;
                                                description "Percentage reduction from the MBS for a queue drop tail";
                                            }

                                        } // container low

                                    } // container drop-tail

                                    container parent {
                                        description "Enter the parent context";

                                        leaf weight {
                                            type types-qos:weight-override;
                                            description "PIR parameter that overrides parent for queue group";
                                        }

                                        leaf cir-weight {
                                            type types-qos:weight-override;
                                            description "CIR parameter that overrides parent for queue group";
                                        }

                                    } // container parent

                                    container monitor-queue-depth {
                                        presence "Enable the monitor-queue-depth context";
                                        description "Enable the monitor-queue-depth context";

                                        leaf fast-polling {
                                            type boolean;
                                            default "false";
                                            description "Enable fast polling of the queue depth";
                                        }

                                        leaf violation-threshold {
                                            type decimal64 {
                                                range "0.01..99.99";
                                                fraction-digits 2;
                                            }
                                            description "Threshold for queue depth before violation is raised";
                                        }

                                    } // container monitor-queue-depth

                                    container hs-wred-queue {
                                        description "Enter the hs-wred-queue context";

                                        leaf policy {
                                            type leafref {
                                                path "../../../../../../../../../../qos/slope-policy/slope-policy-name";
                                            }
                                            description "Slope policy applied to the HSQ queue group queue";
                                        }

                                    } // container hs-wred-queue

                                } // list queue

                                list policer {
                                    key "policer-id";
                                    description "Enter the policer list instance";

                                    leaf policer-id {
                                        type leafref {
                                            path "../../../../../../../../../qos/sap-egress[sap-egress-policy-name=current()/../../../policy-name]/policer/policer-id";
                                        }
                                        description "Policer unique ID";
                                    }

                                    leaf cbs {
                                        type types-qos:policer-burst-size-override-max;
                                        description "CBS";
                                    }

                                    leaf mbs {
                                        type types-qos:policer-burst-size-override-max;
                                        description "MBS";
                                    }

                                    leaf packet-byte-offset {
                                        type types-qos:egress-per-packet-offset-override;
                                        description "Packet size modification for policing information";
                                    }

                                    leaf stat-mode {
                                        type types-qos:egress-policer-stat-mode;
                                        description "Mode of statistics collected by the policer";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice policer-override-rate {
                                        case rate {

                                            container rate {
                                                description "Enter the rate context";

                                                leaf pir {
                                                    type union {
                                                        type int64 {
                                                            range "1..6400000000";
                                                        }
                                                        type enumeration {
                                                            enum max                            { value -1; }
                                                        }
                                                    }
                                                    units "kilobps";
                                                    description "PIR rate";
                                                }

                                                leaf cir {
                                                    type union {
                                                        type int64 {
                                                            range "0..6400000000";
                                                        }
                                                        type enumeration {
                                                            enum max                            { value -1; }
                                                        }
                                                    }
                                                    units "kilobps";
                                                    description "CIR rate";
                                                }

                                            } // container rate

                                        }
                                        case percent-rate {

                                            container percent-rate {
                                                description "Enter the percent-rate context";

                                                leaf pir {
                                                    type decimal64 {
                                                        range "0.01..100.00";
                                                        fraction-digits 2;
                                                    }
                                                    description "PIR percent rate";
                                                }

                                                leaf cir {
                                                    type decimal64 {
                                                        range "0.00..100.00";
                                                        fraction-digits 2;
                                                    }
                                                    description "CIR percent rate";
                                                }

                                            } // container percent-rate

                                        }
                                    }
                                } // list policer

                                list hs-wrr-group {
                                    key "group-id";
                                    description "Enter the hs-wrr-group list instance";

                                    leaf group-id {
                                        type leafref {
                                            path "../../../../../../../../../qos/sap-egress[sap-egress-policy-name=current()/../../../policy-name]/hs-wrr-group/group-id";
                                        }
                                        description "HS WRR group identifier";
                                    }

                                    leaf hs-class-weight {
                                        type types-qos:hs-class-weight-override;
                                        description "Class weight override of the WRR group";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    choice rate-or-percent-rate {
                                        case rate {

                                            leaf rate {
                                                type union {
                                                    type uint32 {
                                                        range "1..2000000000";
                                                    }
                                                    type enumeration {
                                                        enum max                            { value -1; }
                                                    }
                                                }
                                                units "kilobps";
                                                description "Scheduling rate override applied to the HS WRR group";
                                            }

                                        }
                                        case percent-rate {

                                            leaf percent-rate {
                                                type decimal64 {
                                                    range "0.01..100.00";
                                                    fraction-digits 2;
                                                }
                                                description "Percent rate override applied to the HS WRR group";
                                            }

                                        }
                                    }
                                } // list hs-wrr-group

                            } // container overrides

                        } // container sap-egress

                        container policer-control-policy {
                            description "Enter the policer-control-policy context";

                            leaf policy-name {
                                type leafref {
                                    path "../../../../../../../qos/policer-control-policy/policer-control-policy-name";
                                }
                                description "Policer control policy name";
                            }

                            container overrides {
                                presence "Enable the overrides context";
                                description "Enable the overrides context";

                                leaf-list apply-groups {
                                    type leafref {
                                        path "../../../../../../../../groups/group/name";
                                    }
                                    max-elements 8;
                                    ordered-by user;
                                    description "Apply a configuration group at this level";
                                }

                                leaf-list apply-groups-exclude {
                                    type leafref {
                                        path "../../../../../../../../groups/group/name";
                                    }
                                    max-elements 8;
                                    ordered-by user;
                                    description "Exclude a configuration group at this level";
                                }

                                container root {
                                    description "Enter the root context";

                                    leaf max-rate {
                                        type types-services:sap-max-rate-ovr;
                                        description "Maximum frame-based bandwidth limit";
                                    }

                                    container priority-mbs-thresholds {
                                        description "Enter the priority-mbs-thresholds context";

                                        leaf min-thresh-separation {
                                            type union {
                                                type types-qos:bytes {
                                                    range "0..16777216";
                                                }
                                                type enumeration {
                                                    enum auto                           { value -1; }
                                                }
                                            }
                                            units "bytes";
                                            description "Minimum amount of separation buffer space";
                                        }

                                        list priority {
                                            key "priority-level";
                                            description "Enter the priority list instance";

                                            leaf priority-level {
                                                type types-qos:hierarchy-level;
                                                description "Priority level";
                                            }

                                            leaf mbs-contribution {
                                                type union {
                                                    type types-qos:bytes {
                                                        range "0..16777216";
                                                    }
                                                    type enumeration {
                                                        enum auto                           { value -1; }
                                                    }
                                                }
                                                units "bytes";
                                                description "Minimum amount of cumulative buffer space allowed";
                                            }

                                            leaf-list apply-groups {
                                                type leafref {
                                                    path "../../../../../../../../../../../groups/group/name";
                                                }
                                                max-elements 8;
                                                ordered-by user;
                                                description "Apply a configuration group at this level";
                                            }

                                            leaf-list apply-groups-exclude {
                                                type leafref {
                                                    path "../../../../../../../../../../../groups/group/name";
                                                }
                                                max-elements 8;
                                                ordered-by user;
                                                description "Exclude a configuration group at this level";
                                            }

                                        } // list priority

                                    } // container priority-mbs-thresholds

                                } // container root

                            } // container overrides

                        } // container policer-control-policy

                        container scheduler-policy {
                            description "Enter the scheduler-policy context";

                            leaf policy-name {
                                type leafref {
                                    path "../../../../../../../qos/scheduler-policy/scheduler-policy-name";
                                }
                                description "Scheduler policy name";
                            }

                            container overrides {
                                description "Enter the overrides context";

                                list scheduler {
                                    key "scheduler-name";
                                    description "Enter the scheduler list instance";

                                    leaf scheduler-name {
                                        type types-sros:named-item;
                                        description "Scheduler name";
                                    }

                                    leaf-list apply-groups {
                                        type leafref {
                                            path "../../../../../../../../../groups/group/name";
                                        }
                                        max-elements 8;
                                        ordered-by user;
                                        description "Apply a configuration group at this level";
                                    }

                                    leaf-list apply-groups-exclude {
                                        type leafref {
                                            path "../../../../../../../../../groups/group/name";
                                        }
                                        max-elements 8;
                                        ordered-by user;
                                        description "Exclude a configuration group at this level";
                                    }

                                    container parent {
                                        description "Enter the parent context";

                                        leaf weight {
                                            type types-qos:weight;
                                            description "Relative weight of the scheduler to feed the queue";
                                        }

                                        leaf cir-weight {
                                            type types-qos:weight;
                                            description "Weight used at the within-CIR port priority level";
                                        }

                                    } // container parent

                                    container rate {
                                        description "Enter the rate context";

                                        leaf pir {
                                            type union {
                                                type int64 {
                                                    range "1..6400000000";
                                                }
                                                type enumeration {
                                                    enum max                            { value -1; }
                                                }
                                            }
                                            units "kilobps";
                                            description "PIR at which the queue is to operate";
                                        }

                                        leaf cir {
                                            type union {
                                                type int64 {
                                                    range "0..6400000000";
                                                }
                                                type enumeration {
                                                    enum sum                            { value -3; }
                                                    enum max                            { value -1; }
                                                }
                                            }
                                            units "kilobps";
                                            description "CIR at which the queue it to operate";
                                        }

                                    } // container rate

                                } // list scheduler

                            } // container overrides

                        } // container scheduler-policy

                    } // container qos

                    container filter {
                        description "Enter the filter context";

                        leaf ip {
                            type leafref {
                                path "../../../../../../filter/ip-filter/filter-name";
                            }
                            description "MAC filter ID";
                        }

                        leaf ipv6 {
                            type leafref {
                                path "../../../../../../filter/ipv6-filter/filter-name";
                            }
                            description "IPv6 filter identifier";
                        }

                    } // container filter

                    container virtual-port {
                        description "Enter the virtual-port context";

                        leaf vport-name {
                            type leafref {
                                path "../../../../../../port/ethernet/access/egress/virtual-port/vport-name";
                            }
                            description "Virtual port assigned to the SAP";
                        }

                    } // container virtual-port

                } // container egress

                container cpu-protection {
                    description "Enter the cpu-protection context";

                    leaf policy-id {
                        type leafref {
                            path "../../../../../system/security/cpu-protection/policy/policy-id";
                        }
                        description "CPM protection policy";
                    }

                    choice monitoring {
                        case mac {

                            leaf mac-monitoring {
                                type empty;
                                description "Monitor MAC for CPU protection";
                            }

                        }
                    }
                } // container cpu-protection

                container lag {
                    description "Enter the lag context";

                    leaf link-map-profile {
                        type types-services:link-map-profile-id;
                        description "LAG link map profile for a SAP or network interface";
                    }

                    container per-link-hash {
                        description "Enter the per-link-hash context";

                        leaf class {
                            type types-services:sap-lag-per-link-hash-class;
                            default "1";
                            description "Class used on LAG egress using weighted per-link-hash";
                        }

                        leaf weight {
                            type types-services:sap-lag-per-link-hash-weight;
                            default "1";
                            description "Weight used on LAG egress using weighted per-link-hash";
                        }

                    } // container per-link-hash

                } // container lag



            } // list sap

            list spoke-sdp {
                key "sdp-bind-id";
                description "Enter the spoke-sdp list instance";

                leaf sdp-bind-id {
                    type types-services:sdp-bind-id;
                    description "SDP binding ID";
                }

                leaf description {
                    type types-sros:description;
                    description "Text description";
                }

                leaf admin-state {
                    type types-sros:admin-state;
                    default "enable";
                    description "Administrative state of the SDP binding to the service";
                }

                leaf control-word {
                    type boolean;
                    default "false";
                    description "Use control word as part of packet encapsulation";
                }

                leaf bandwidth {
                    type types-services:sdp-bind-bandwidth;
                    units "kilobps";
                    default "0";
                    description "Bandwidth that is reserved for this SDP binding";
                }

                leaf app-profile {
                    type leafref {
                        path "../../../../application-assurance/group/partition/policy/app-profile/app-profile-name";
                    }
                    description "Application profile name for this SDP";
                }

                leaf bfd-template {
                    status obsolete;
                    type leafref {
                        path "../../../../bfd/bfd-template/name";
                    }
                    description "BFD template associated with SDP binding";
                }

                leaf ce-address {
                    type types-sros:ip-address;
                    description "IP address of the CE device";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                choice label {
                    case entropy {

                        leaf entropy-label {
                            type empty;
                            description "Enable the use of entropy labels for spoke SDPs";
                        }

                    }
                    case hash {

                        container hash-label {
                            presence "Enable the hash-label context";
                            description "Enable the hash-label context";

                            leaf signal-capability {
                                type empty;
                                description "Signal hash label capability to the remote PE";
                            }

                        } // container hash-label

                    }
                }
                container ingress {
                    description "Enter the ingress context";

                    leaf vc-label {
                        type types-services:ingress-vc-label;
                        sros-ext:auto-restart-to-modify;
                        description "Ingress MPLS VC label to send packets to the far end";
                    }

                    container filter {
                        description "Enter the filter context";

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container fp-redirect-group {
                                description "Enter the fp-redirect-group context";

                                leaf group-name {
                                    type leafref {
                                        path "../../../../../../../../qos/queue-group-templates/ingress/queue-group/ingress-queue-group-name";
                                    }
                                    description "Name of the forwarding plane queue group template";
                                }

                                leaf instance {
                                    type types-services:qos-qgrp-instance-id;
                                    description "Instance of FP ingress queue group for the SDP binding";
                                }

                            } // container fp-redirect-group

                        } // container network

                    } // container qos

                } // container ingress

                container egress {
                    description "Enter the egress context";

                    leaf vc-label {
                        type types-services:egress-vc-label;
                        sros-ext:auto-restart-to-modify;
                        description "Egress MPLS VC label to send packets to the far end";
                    }

                    container filter {
                        description "Enter the filter context";

                        leaf ip {
                            type leafref {
                                path "../../../../../../filter/ip-filter/filter-name";
                            }
                            description "IPv4 filter policy name";
                        }

                        leaf ipv6 {
                            type leafref {
                                path "../../../../../../filter/ipv6-filter/filter-name";
                            }
                            description "IPv6 filter policy name";
                        }

                    } // container filter

                    container qos {
                        description "Enter the qos context";

                        container network {
                            description "Enter the network context";

                            leaf policy-name {
                                type leafref {
                                    path "../../../../../../../qos/network/network-policy-name";
                                }
                                description "Network policy ID";
                            }

                            container port-redirect-group {
                                description "Enter the port-redirect-group context";

                                leaf group-name {
                                    type leafref {
                                        path "../../../../../../../../qos/queue-group-templates/egress/queue-group/egress-queue-group-name";
                                    }
                                    description "Name of the egress port queue group";
                                }

                                leaf instance {
                                    type types-services:qos-qgrp-instance-id;
                                    description "Queue-group instance ID";
                                }

                            } // container port-redirect-group

                        } // container network

                    } // container qos

                } // container egress

                container endpoint {
                    description "Enter the endpoint context";

                    leaf name {
                        type leafref {
                            path "../../../../ipipe[service-name=current()/../../../service-name]/endpoint/name";
                        }
                        sros-ext:auto-restart-to-modify;
                        description "Endpoint name to which SDP bind is attached";
                    }

                    leaf precedence {
                        type types-services:sdp-precedence;
                        default "4";
                        description "Precedence when multiple SDP binds are on one endpoint";
                    }

                } // container endpoint

                container aarp {
                    presence "Enable the aarp context";
                    description "Enable the aarp context";

                    leaf id {
                        type leafref {
                            path "../../../../../application-assurance/aarp/aarp-id";
                        }
                        sros-ext:immutable;
                        mandatory true;
                        description "AARP instance ID";
                    }

                    leaf type {
                        type types-services:l3-bsx-aarp-service-ref-type;
                        sros-ext:immutable;
                        mandatory true;
                        description "Role of the spoke SDP referenced by the AARP";
                    }

                } // container aarp

                container bfd-liveness {
                    status obsolete;
                    presence "Enable the bfd-liveness context";
                    description "Enable the bfd-liveness context";

                    leaf encap {
                        status obsolete;
                        type types-services:bfd-encap;
                        default "ipv4";
                        description "BFD encapsulation used on the SDP binding";
                    }

                } // container bfd-liveness

                container bfd {
                    description "Enter the bfd context";

                    leaf bfd-template {
                        type leafref {
                            path "../../../../../bfd/bfd-template/name";
                        }
                        description "BFD template associated with the SDP binding";
                    }

                    container bfd-liveness {
                        presence "Enable the bfd-liveness context";
                        description "Enable the bfd-liveness context";

                        leaf encap {
                            type types-services:bfd-encap;
                            default "ipv4";
                            description "BFD encapsulation used on the SDP binding";
                        }

                    } // container bfd-liveness

                } // container bfd

                container transit-policy {
                    presence "Enable the transit-policy context";
                    description "Enable the transit-policy context";

                    leaf prefix {
                        type leafref {
                            path "../../../../../application-assurance/group/partition/transit-prefix-policy/prefix-policy-id";
                        }
                        sros-ext:immutable;
                        mandatory true;
                        description "IP prefix policy ID";
                    }

                } // container transit-policy

            } // list spoke-sdp

        } // list ipipe

    } // grouping conf-svc-ipipe

}
