submodule nokia-conf-testoam-service-activation-testhead {

    yang-version "1.1";

    belongs-to nokia-conf { prefix "conf"; }

    import nokia-sros-yang-extensions     { prefix "sros-ext"; }
    import nokia-types-eth-cfm            { prefix "types-eth-cfm"; }
    import nokia-types-oam                { prefix "types-oam"; }
    import nokia-types-sros               { prefix "types-sros"; }

    include nokia-conf-eth-cfm;
    include nokia-conf-groups;
    include nokia-conf-log;

    sros-ext:sros-major-release "rel26";
    organization "Nokia";
    contact
        "Nokia SR OS Support
         Web: <http://www.nokia.com>";
    description
        "Nokia YANG Data model to configure OAM Service Activation Tests (Y.1564) on SR OS based routers.

         Copyright 2016 Nokia. All rights reserved. Reproduction of this document
         is authorized on the condition that the foregoing copyright notice is included.

         This nokia-conf-testoam-service-activation-testhead YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-testoam-service-activation-testhead {
        container service-activation-testhead {
            description "Enter the service-activation-testhead context";

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list acceptance-criteria-template {
                key "ac-template-name";
                max-elements 100;
                description "Enter the acceptance-criteria-template list instance";

                leaf ac-template-name {
                    type types-sros:named-item-64;
                    description "Acceptance criteria template name";
                }

                leaf description {
                    type types-sros:description;
                    description "Text description";
                }

                leaf cir-threshold {
                    type uint32 {
                        range "1..400000000";
                    }
                    units "kilobps";
                    description "CIR threshold";
                }

                leaf pir-threshold {
                    type uint32 {
                        range "1..400000000";
                    }
                    units "kilobps";
                    description "PIR threshold";
                }

                leaf loss-threshold {
                    type types-oam:sath-loss-percent-decimal64;
                    description "Loss threshold for acceptance criteria template";
                }

                leaf loss-threshold-policing {
                    type types-oam:sath-loss-percent-decimal64;
                    description "Frame loss ratio for a policing test";
                }

                leaf delay-threshold {
                    type uint32 {
                        range "1..100000000";
                    }
                    units "microseconds";
                    description "Delay threshold configuration for acceptance criteria template";
                }

                leaf delay-var-threshold {
                    type uint32 {
                        range "1..100000000";
                    }
                    units "microseconds";
                    description "Delay variation threshold configuration for acceptance criteria template";
                }

                leaf m-factor {
                    type uint32 {
                        range "1..400000000";
                    }
                    units "kilobps";
                    description "Throughput margin configuration";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list acceptance-criteria-template

            list frame-size-template {
                key "fs-template-name";
                max-elements 100;
                description "Enter the frame-size-template list instance";

                leaf fs-template-name {
                    type types-sros:named-item-64;
                    description "Frame size template name";
                }

                leaf size-a {
                    type uint32 {
                        range "64..9212";
                    }
                    units "bytes";
                    default "64";
                    description "Size-a";
                }

                leaf size-b {
                    type uint32 {
                        range "64..9212";
                    }
                    units "bytes";
                    default "128";
                    description "Size-b";
                }

                leaf size-c {
                    type uint32 {
                        range "64..9212";
                    }
                    units "bytes";
                    default "256";
                    description "Size-c";
                }

                leaf size-d {
                    type uint32 {
                        range "64..9212";
                    }
                    units "bytes";
                    default "512";
                    description "Size-d";
                }

                leaf size-e {
                    type uint32 {
                        range "64..9212";
                    }
                    units "bytes";
                    default "1024";
                    description "Size-e";
                }

                leaf size-f {
                    type uint32 {
                        range "64..9212";
                    }
                    units "bytes";
                    default "1280";
                    description "Size-f";
                }

                leaf size-g {
                    type uint32 {
                        range "64..9212";
                    }
                    units "bytes";
                    default "1518";
                    description "Size-g";
                }

                leaf size-h {
                    type uint32 {
                        range "64..9212";
                    }
                    units "bytes";
                    default "9212";
                    description "Size-h";
                }

                leaf size-u {
                    type uint32 {
                        range "64..9212";
                    }
                    units "bytes";
                    default "2000";
                    description "Size-u";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list frame-size-template

            list service-test {
                key "test-name";
                max-elements 500;
                description "Enter the service-test list instance";

                leaf test-name {
                    type types-sros:named-item-64;
                    description "Service activation test name";
                }

                leaf admin-state {
                    type types-sros:admin-state;
                    default "disable";
                    description "Administrative state of the service test";
                }

                leaf description {
                    type types-sros:description;
                    description "Text description";
                }

                leaf accounting-policy {
                    type leafref {
                        path "../../../../log/accounting-policy/policy-id";
                    }
                    description "Accounting policy to record service test results";
                }

                leaf service-test-completion-notification {
                    type boolean;
                    default "false";
                    description "Enable SNMP trap generation upon test completion";
                }

                leaf stream-run-type {
                    type enumeration {
                        enum sequential                     { value 1; }
                        enum parallel                       { value 2; }
                    }
                    default "parallel";
                    description "Service stream run order";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container test-duration {
                    description "Enter the test-duration context";

                    container cir {
                        description "Enter the cir context";

                        leaf minutes-seconds {
                            type types-oam:sath-mm-ss-string;
                            default "05:00";
                            description "Duration of the service test CIR tests";
                        }

                    } // container cir

                    container cir-pir {
                        description "Enter the cir-pir context";

                        leaf minutes-seconds {
                            type types-oam:sath-mm-ss-string;
                            default "10:00";
                            description "Duration of the service test CIR-PIR tests";
                        }

                    } // container cir-pir

                    container policing {
                        description "Enter the policing context";

                        leaf minutes-seconds {
                            type types-oam:sath-mm-ss-string;
                            default "10:00";
                            description "Duration of policing tests belonging to the test";
                        }

                    } // container policing

                    container performance {
                        description "Enter the performance context";

                        leaf hours-minutes-seconds {
                            type types-oam:sath-hh-mm-ss-string;
                            default "00:15:00";
                            description "Duration of performance tests belonging to the test";
                        }

                    } // container performance

                } // container test-duration

                list service-stream {
                    key "stream-id";
                    description "Enter the service-stream list instance";

                    leaf stream-id {
                        type uint32 {
                            range "1..8";
                        }
                        description "Service stream ID";
                    }

                    leaf admin-state {
                        type types-sros:admin-state;
                        default "disable";
                        description "Administrative state of the service stream";
                    }

                    leaf description {
                        type types-sros:description;
                        sros-ext:auto-restart-to-modify;
                        description "Text description";
                    }

                    leaf acceptance-criteria-template {
                        type leafref {
                            path "../../../acceptance-criteria-template/ac-template-name";
                        }
                        sros-ext:auto-restart-to-modify;
                        description "Acceptance criteria association to a service stream";
                    }

                    leaf rate-cir {
                        type uint32 {
                            range "0..400000000";
                        }
                        units "kilobps";
                        sros-ext:auto-restart-to-modify;
                        default "0";
                        description "CIR packet transmit rate for the service stream";
                    }

                    leaf rate-pir {
                        type uint32 {
                            range "0..400000000";
                        }
                        units "kilobps";
                        sros-ext:auto-restart-to-modify;
                        default "0";
                        description "PIR packet transmit rate for the service stream";
                    }

                    leaf service-stream-completion-notification {
                        type boolean;
                        sros-ext:auto-restart-to-modify;
                        default "false";
                        description "Enable SNMP trap generation upon test completion";
                    }

                    leaf-list apply-groups {
                        type leafref {
                            path "../../../../../groups/group/name";
                        }
                        max-elements 8;
                        ordered-by user;
                        sros-ext:auto-restart-to-modify;
                        description "Apply a configuration group at this level";
                    }

                    leaf-list apply-groups-exclude {
                        type leafref {
                            path "../../../../../groups/group/name";
                        }
                        max-elements 8;
                        ordered-by user;
                        sros-ext:auto-restart-to-modify;
                        description "Exclude a configuration group at this level";
                    }

                    container frame-mix {
                        sros-ext:auto-restart-to-modify;
                        description "Enter the frame-mix context";

                        leaf frame-size-template {
                            type leafref {
                                path "../../../../frame-size-template/fs-template-name";
                            }
                            sros-ext:auto-restart-to-modify;
                            description "Frame size template for the service stream";
                        }

                        leaf sequence {
                            type string {
                                length "1..16";
                                pattern "[a-hu]" {
                                    error-message "'sequence' must be one character a-h or u per frame-size step";
                                }
                            }
                            sros-ext:auto-restart-to-modify;
                            default "a";
                            description "Sequence of frame sizes for the service stream";
                        }

                    } // container frame-mix

                    container test-types {
                        sros-ext:auto-restart-to-modify;
                        description "Enter the test-types context";

                        leaf cir {
                            type boolean;
                            sros-ext:auto-restart-to-modify;
                            default "false";
                            description "CIR test for the service stream";
                        }

                        leaf cir-pir {
                            type boolean;
                            sros-ext:auto-restart-to-modify;
                            default "false";
                            description "CIR-PIR test for the service stream";
                        }

                        leaf policing {
                            type boolean;
                            sros-ext:auto-restart-to-modify;
                            default "false";
                            description "Policing test for the service stream";
                        }

                        leaf performance {
                            type boolean;
                            sros-ext:auto-restart-to-modify;
                            default "false";
                            description "Performance test for the service stream";
                        }

                    } // container test-types

                    container frame-payload {
                        sros-ext:auto-restart-to-modify;
                        description "Enter the frame-payload context";

                        container data-pattern {
                            sros-ext:auto-restart-to-modify;
                            description "Enter the data-pattern context";

                            leaf repeat {
                                type types-sros:hex-string-or-uint;
                                sros-ext:auto-restart-to-modify;
                                description "Repeated 4-byte pattern to pad each packet sent";
                            }

                        } // container data-pattern

                        container ethernet {
                            sros-ext:auto-restart-to-modify;
                            description "Enter the ethernet context";

                            leaf dst-mac {
                                type types-sros:mac-unicast-address-no-zero;
                                sros-ext:auto-restart-to-modify;
                                description "Destination MAC address of Ethernet frames";
                            }

                            container eth-cfm {
                                sros-ext:auto-restart-to-modify;
                                description "Enter the eth-cfm context";

                                container source {
                                    sros-ext:auto-restart-to-modify;
                                    description "Enter the source context";

                                    leaf mep-id {
                                        type types-eth-cfm:mep-id-type;
                                        sros-ext:auto-restart-to-modify;
                                        description "Source Ethernet maintenance association end point";
                                    }

                                    leaf md-admin-name {
                                        type leafref {
                                            path "../../../../../../../../../eth-cfm/domain/md-admin-name";
                                        }
                                        sros-ext:auto-restart-to-modify;
                                        description "Source Ethernet maintenance domain name";
                                    }

                                    leaf ma-admin-name {
                                        type leafref {
                                            path "../../../../../../../../../eth-cfm/domain[md-admin-name=current()/../md-admin-name]/association/ma-admin-name";
                                        }
                                        sros-ext:auto-restart-to-modify;
                                        description "Source Ethernet maintenance association name";
                                    }

                                } // container source

                            } // container eth-cfm

                            container s-tag {
                                sros-ext:auto-restart-to-modify;
                                description "Enter the s-tag context";

                                leaf dot1p {
                                    type uint32 {
                                        range "0..7";
                                    }
                                    sros-ext:auto-restart-to-modify;
                                    default "7";
                                    description "PCP of Ethernet frames for service stream";
                                }

                                leaf discard-eligible {
                                    type boolean;
                                    sros-ext:auto-restart-to-modify;
                                    default "false";
                                    description "Enable marking of the DEI bit in the VLAN header";
                                }

                            } // container s-tag

                            container c-tag {
                                sros-ext:auto-restart-to-modify;
                                description "Enter the c-tag context";

                                leaf dot1p {
                                    type uint32 {
                                        range "0..7";
                                    }
                                    sros-ext:auto-restart-to-modify;
                                    default "7";
                                    description "PCP of Ethernet frames for service stream";
                                }

                                leaf discard-eligible {
                                    type boolean;
                                    sros-ext:auto-restart-to-modify;
                                    default "false";
                                    description "Enable marking of the DEI bit in the VLAN header";
                                }

                            } // container c-tag

                        } // container ethernet

                    } // container frame-payload

                } // list service-stream

            } // list service-test

        } // container service-activation-testhead

    } // grouping conf-testoam-service-activation-testhead

}
