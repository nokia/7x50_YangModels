submodule nokia-conf-router-p2mp-sr-tree {

    yang-version "1.1";

    belongs-to nokia-conf { prefix "conf"; }

    import nokia-sros-yang-extensions     { prefix "sros-ext"; }
    import nokia-types-sros               { prefix "types-sros"; }

    include nokia-conf-groups;
    include nokia-conf-router;
    include nokia-conf-router-segment-routing;

    sros-ext:sros-major-release "rel26";
    organization "Nokia";
    contact
        "Nokia SR OS Support
         Web: <http://www.nokia.com>";
    description
        "Nokia YANG Data model to configure Base router p2mp-sr-tree on SR OS based routers.

         Copyright 2016 Nokia. All rights reserved. Reproduction of this document
         is authorized on the condition that the foregoing copyright notice is included.

         This nokia-conf-router-p2mp-sr-tree YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-router-p2mp-sr-tree {
        container p2mp-sr-tree {
            when "../router-name = 'Base'" {
                description "only allowed in the Base router";
            }
            presence "Enable the p2mp-sr-tree context";
            description "Enable the p2mp-sr-tree context";

            leaf admin-state {
                type types-sros:admin-state;
                default "disable";
                description "Administrative state of the P2MP SR tree";
            }

            leaf reserved-label-block {
                type leafref {
                    path "../../mpls-labels/reserved-label-block/label-block-name";
                }
                description "Reserved label block name for the P2MP SR tree";
            }

            leaf-list bfd-liveness {
                type enumeration {
                    enum ipv4                           { value 1; }
                    enum ipv6                           { value 2; }
                }
                max-elements 2;
                description "BFD tracking";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list p2mp-policy {
                key "p2mp-policy-name";
                description "Enter the p2mp-policy list instance";

                leaf p2mp-policy-name {
                    type types-sros:named-item;
                    description "P2MP policy name";
                }

                leaf root-address {
                    type types-sros:ip-address;
                    default "0.0.0.0";
                    description "Root node address for the P2MP policy";
                }

                leaf tree-id {
                    type uint32 {
                        range "0|8193..16286";
                    }
                    default "0";
                    description "Tree ID for the P2MP policy";
                }

                leaf admin-state {
                    type types-sros:admin-state;
                    default "disable";
                    description "Administrative state of the P2MP policy";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list candidate-path {
                    key "candidate-path-name";
                    description "Enter the candidate-path list instance";

                    leaf candidate-path-name {
                        type types-sros:named-item;
                        description "Candidate path name";
                    }

                    leaf active-instance {
                        type leafref {
                            path "../path-instances/index";
                        }
                        description "Candidate path active instance";
                    }

                    leaf preference {
                        type uint32 {
                            range "0..1024";
                        }
                        default "100";
                        description "Candidate path preference";
                    }

                    leaf admin-state {
                        type types-sros:admin-state;
                        default "disable";
                        description "Administrative state of the candidate path";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    list path-instances {
                        key "index";
                        description "Enter the path-instances list instance";

                        leaf index {
                            type uint32 {
                                range "1..2";
                            }
                            description "Instance index";
                        }

                        leaf instance-id {
                            type uint32;
                            description "Path instance identifier";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list path-instances

                } // list candidate-path

            } // list p2mp-policy

            list replication-segment {
                key "policy-name";
                description "Enter the replication-segment list instance";

                leaf policy-name {
                    type types-sros:named-item;
                    description "P2MP policy name";
                }

                leaf replication-sid {
                    status obsolete;
                    type uint32;
                    default "0";
                    description "Segment ID of the replication segment";
                }

                leaf instance-id {
                    type uint32;
                    default "0";
                    description "Replication segment instance identifier";
                }

                leaf root-address {
                    type types-sros:ip-address;
                    description "Root node address for the replication segment";
                }

                leaf tree-id {
                    type uint32 {
                        range "0|8193..16286";
                    }
                    default "0";
                    description "Tree ID for the replication segment of the P2MP SR tree";
                }

                leaf admin-state {
                    type types-sros:admin-state;
                    default "disable";
                    description "Administrative state of the replication segment";
                }

                leaf sid-action {
                    status obsolete;
                    type enumeration {
                        enum none                           { value 0; }
                        enum push                           { value 1; }
                        enum pop                            { value 2; }
                        enum swap                           { value 3; }
                    }
                    default "none";
                    description "SID action for replication segment entries";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                list downstream-nodes {
                    status obsolete;
                    key "downstream-index";
                    description "Enter the downstream-nodes list instance";

                    leaf downstream-index {
                        status obsolete;
                        type int32 {
                            range "1..4096";
                        }
                        description "Downstream index";
                    }

                    leaf next-hop-address {
                        status obsolete;
                        type types-sros:ip-address-with-zone;
                        default "0.0.0.0";
                        description "Next-hop address for replication segment next hops";
                    }

                    leaf next-hop-interface-name {
                        status obsolete;
                        type types-sros:interface-name;
                        description "Interface name for replication segment next-hops";
                    }

                    leaf protect-nexthop-id {
                        status obsolete;
                        type leafref {
                            path "../../downstream-nodes/downstream-index";
                        }
                        description "ID of the protection next hop used for FRR";
                    }

                    leaf admin-state {
                        status obsolete;
                        type types-sros:admin-state;
                        default "disable";
                        description "Administrative state of next-hop entries";
                    }

                    leaf-list apply-groups {
                        status obsolete;
                        type leafref {
                            path "../../../../../groups/group/name";
                        }
                        max-elements 8;
                        ordered-by user;
                        description "Apply a configuration group at this level";
                    }

                    leaf-list apply-groups-exclude {
                        status obsolete;
                        type leafref {
                            path "../../../../../groups/group/name";
                        }
                        max-elements 8;
                        ordered-by user;
                        description "Exclude a configuration group at this level";
                    }

                    container label {
                        status obsolete;
                        description "Enter the label context";

                        choice label {
                            status obsolete;
                            default "replication-sid-list";
                            case replication-sid-list {
                                status obsolete;

                                list sid-list {
                                    status obsolete;
                                    key "index";
                                    description "Enter the sid-list list instance";

                                    leaf index {
                                        status obsolete;
                                        type uint32 {
                                            range "1..11";
                                        }
                                        description "SID list index";
                                    }

                                    leaf replication-sid {
                                        status obsolete;
                                        type uint32 {
                                            range "3|16..1048575|4294967295";
                                        }
                                        mandatory true;
                                        description "Segment ID for the SID list entry";
                                    }

                                    leaf-list apply-groups {
                                        status obsolete;
                                        type leafref {
                                            path "../../../../../../../groups/group/name";
                                        }
                                        max-elements 8;
                                        ordered-by user;
                                        description "Apply a configuration group at this level";
                                    }

                                    leaf-list apply-groups-exclude {
                                        status obsolete;
                                        type leafref {
                                            path "../../../../../../../groups/group/name";
                                        }
                                        max-elements 8;
                                        ordered-by user;
                                        description "Exclude a configuration group at this level";
                                    }

                                } // list sid-list

                            }
                        }
                    } // container label

                } // list downstream-nodes

                container segment-routing-mpls {
                    description "Enter the segment-routing-mpls context";

                    leaf incoming-sid {
                        type uint32;
                        sros-ext:auto-restart-to-modify;
                        default "0";
                        description "Incoming MPLS label as the replication SID";
                    }

                    leaf sid-action {
                        type enumeration {
                            enum none                           { value 0; }
                            enum push                           { value 1; }
                            enum pop                            { value 2; }
                            enum swap                           { value 3; }
                        }
                        default "none";
                        description "SID action for the replication segment";
                    }

                    list downstream-nodes {
                        key "downstream-index";
                        description "Enter the downstream-nodes list instance";

                        leaf downstream-index {
                            type int32 {
                                range "1..4096";
                            }
                            description "Downstream node index entry";
                        }

                        leaf next-hop-address {
                            type types-sros:ip-address-with-zone;
                            default "0.0.0.0";
                            description "Next-hop address for replication segment next hop";
                        }

                        leaf next-hop-interface-name {
                            type types-sros:interface-name;
                            description "Interface name for replication segment next hop";
                        }

                        leaf protect-nexthop-id {
                            type leafref {
                                path "../../downstream-nodes/downstream-index";
                            }
                            description "ID of the protection next hop used for FRR";
                        }

                        leaf admin-state {
                            type types-sros:admin-state;
                            default "disable";
                            description "Administrative state of the downstream node";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container label {
                            description "Enter the label context";

                            choice label {
                                default "replication-sid-list";
                                case replication-sid-list {

                                    list sid-list {
                                        key "index";
                                        description "Enter the sid-list list instance";

                                        leaf index {
                                            type uint32 {
                                                range "1..11";
                                            }
                                            description "SID list index";
                                        }

                                        leaf replication-sid {
                                            type uint32 {
                                                range "3|16..1048575|4294967295";
                                            }
                                            mandatory true;
                                            description "Segment ID for the SID list entry";
                                        }

                                        leaf-list apply-groups {
                                            type leafref {
                                                path "../../../../../../../../groups/group/name";
                                            }
                                            max-elements 8;
                                            ordered-by user;
                                            description "Apply a configuration group at this level";
                                        }

                                        leaf-list apply-groups-exclude {
                                            type leafref {
                                                path "../../../../../../../../groups/group/name";
                                            }
                                            max-elements 8;
                                            ordered-by user;
                                            description "Exclude a configuration group at this level";
                                        }

                                    } // list sid-list

                                }
                            }
                        } // container label

                    } // list downstream-nodes

                } // container segment-routing-mpls

                container segment-routing-v6 {
                    description "Enter the segment-routing-v6 context";

                    leaf role {
                        type enumeration {
                            enum none {
                                value 0;
                                description "Do not use a role for this segment";
                            }
                            enum root {
                                value 1;
                                description "Use the neighbor root role for this segment";
                            }
                            enum leaf {
                                value 2;
                                description "Use the leaf area role for this segment";
                            }
                            enum transit {
                                value 3;
                                description "Use the transit role for this segment";
                            }
                        }
                        default "none";
                        description "Role of the SRv6 replication segment entry";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container incoming-sid {
                        description "Enter the incoming-sid context";

                        container locator {
                            description "Enter the locator context";

                            leaf locator-name {
                                type leafref {
                                    path "../../../../../../../router/segment-routing/segment-routing-v6/locator/locator-name";
                                }
                                description "Incoming SID locator name";
                            }

                            leaf function {
                                type enumeration {
                                    enum end-replicate {
                                        value 1;
                                        description "Use the incoming SID to find the replication state";
                                    }
                                }
                                description "Function of the incoming replication SID";
                            }

                            leaf function-value {
                                type uint32 {
                                    range "1..1048575";
                                }
                                description "Incoming SID function value";
                            }

                        } // container locator

                    } // container incoming-sid

                    list downstream-nodes {
                        key "downstream-node-index";
                        description "Enter the downstream-nodes list instance";

                        leaf downstream-node-index {
                            type int32 {
                                range "1..4096";
                            }
                            description "Downstream node index";
                        }

                        leaf replication-sid {
                            type types-sros:ipv6-unicast-address;
                            description "Replication SID for next-hop entries";
                        }

                        leaf admin-state {
                            type types-sros:admin-state;
                            default "disable";
                            description "Administrative state of the downstream next-hop entries";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list downstream-nodes

                } // container segment-routing-v6

            } // list replication-segment

        } // container p2mp-sr-tree

    } // grouping conf-router-p2mp-sr-tree

}
