submodule nokia-state-port-serial {

    yang-version "1.1";

    belongs-to nokia-state { prefix "state"; }

    import ietf-yang-types                { prefix "yang"; }
    import nokia-sros-yang-extensions     { prefix "sros-ext"; }
    import nokia-types-port               { prefix "types-port"; }

    sros-ext:sros-major-release "rel26";
    organization "Nokia";
    contact
        "Nokia SR OS Support
         Web: <http://www.nokia.com>";
    description
        "Nokia YANG Data model with operational state for Serial ports on SR OS based routers.

         Copyright 2016 Nokia. All rights reserved. Reproduction of this document
         is authorized on the condition that the foregoing copyright notice is included.

         This nokia-state-port-serial YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-port-serial {
        container serial {
            description "Enter the serial context";

            container rs232 {
                description "Enter the rs232 context";

                leaf current-alarms {
                    type bits {
                        bit hcm-oof                        { position 1; }
                        bit hcm-rai                        { position 2; }
                        bit ctrl-lead-mon                  { position 3; }
                        bit mon-data-inac                  { position 4; }
                    }
                    description "Indicates the current alarms on the serial port.";
                }

                container control-lead {
                    description "Enter the control-lead context";

                    container control-lead-state {
                        description "Enter the control-lead-state context";

                        container input {
                            description "Enter the input context";

                            leaf dts-dsr {
                                type types-port:control-lead;
                                description "Data Terminal Ready (DTR) or Data Set Ready (DSR) input control lead.";
                            }

                            leaf rts-dcd {
                                type types-port:control-lead;
                                description "Request To Send (RTS) or Data Carrier Detect (DCD) input control lead.";
                            }

                        } // container input

                        container output {
                            description "Enter the output context";

                            leaf cts-alb {
                                type types-port:control-lead;
                                description "Clear To Send (CTS) or Analog Loopback (ALB) output control lead.";
                            }

                            leaf dcd-rts {
                                type types-port:control-lead;
                                description " Data Carrier Detect (DCD) or Request To Send (RTS) output control lead.";
                            }

                            leaf ri-rdl {
                                type types-port:control-lead;
                                description "Ring Indicator (RI) or Remote Digital Loopback (RDL) output control lead.";
                            }

                        } // container output

                    } // container control-lead-state

                    container control-lead-signal {
                        description "Enter the control-lead-signal context";

                        container input {
                            description "Enter the input context";

                            leaf dts-dsr {
                                type types-port:control-lead;
                                description "Data Terminal Ready (DTR) or Data Set Ready (DSR) input control lead.";
                            }

                            leaf rts-dcd {
                                type types-port:control-lead;
                                description "Request To Send (RTS) or Data Carrier Detect (DCD) input control lead.";
                            }

                        } // container input

                        container output {
                            description "Enter the output context";

                            leaf cts-alb {
                                type types-port:control-lead;
                                description "Clear To Send (CTS) or Analog Loopback (ALB) output control lead.";
                            }

                            leaf dcd-rts {
                                type types-port:control-lead;
                                description " Data Carrier Detect (DCD) or Request To Send (RTS) output control lead.";
                            }

                            leaf ri-rdl {
                                type types-port:control-lead;
                                description "Ring Indicator (RI) or Remote Digital Loopback (RDL) output control lead.";
                            }

                        } // container output

                    } // container control-lead-signal

                } // container control-lead

                list socket {
                    key "socket-id";
                    description "Enter the socket list instance";

                    leaf socket-id {
                        type uint32 {
                            range "1";
                        }
                        description "The socket identifier.";
                    }

                    leaf squelch-status {
                        type enumeration {
                            enum on                             { value 1; }
                            enum off                            { value 2; }
                        }
                        description "The squelch status.";
                    }

                    container statistics {
                        description "Enter the statistics context";

                        leaf characters-received {
                            type yang:counter64;
                            description "Number of characters received.";
                        }

                        leaf characters-transmitted {
                            type yang:counter64;
                            description "Number of characters transmitted.";
                        }

                        leaf end-of-packet-idle-timeout {
                            type yang:counter64;
                            description "Number of times an end of packet event occurred due to idle timeout.";
                        }

                        leaf end-of-packet-length {
                            type yang:counter64;
                            description "Number of times an end of packet event occurred due to length.";
                        }

                        leaf end-of-packet-special-character {
                            type yang:counter64;
                            description "Number of times an end of packet event occurred due to special character.";
                        }

                        leaf ingress-forwarded-packets {
                            type yang:counter64;
                            description "Number of ingress packets that were successfully forwarded.";
                        }

                        leaf egress-forwarded-packets {
                            type yang:counter64;
                            description "Number of egress packets that were successfully forwarded.";
                        }

                        leaf ingress-dropped-packets {
                            type yang:counter64;
                            description "Number of ingress packets that were dropped due to errors.";
                        }

                        leaf egress-dropped-packets {
                            type yang:counter64;
                            description "Number of egress packets that were dropped due to errors.";
                        }

                        leaf squelch-activated {
                            type yang:counter64;
                            description "Number of times squelch has been activated.";
                        }

                    } // container statistics

                } // list socket

            } // container rs232

        } // container serial

    } // grouping state-port-serial

}
