submodule nokia-conf-mirror {

    yang-version "1.1";

    belongs-to nokia-conf { prefix "conf"; }

    import ietf-yang-types                { prefix "yang"; }
    import nokia-sros-yang-extensions     { prefix "sros-ext"; }
    import nokia-types-services           { prefix "types-services"; }
    import nokia-types-sros               { prefix "types-sros"; }
    import nokia-types-subscriber-mgmt    { prefix "types-submgt"; }

    include nokia-conf-filter;
    include nokia-conf-groups;
    include nokia-conf-qos;

    sros-ext:sros-major-release "rel26";
    organization "Nokia";
    contact
        "Nokia SR OS Support
         Web: <http://www.nokia.com>";
    description
        "Nokia YANG Data model to configure mirror services on SR OS based routers.

         Copyright 2016 Nokia. All rights reserved. Reproduction of this document
         is authorized on the condition that the foregoing copyright notice is included.

         This nokia-conf-mirror YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-mirror {
        container mirror {
            description "Enter the mirror context";

            leaf global-sampling-rate {
                type uint32 {
                    range "0|2..255";
                }
                default "0";
                description "System wide global sampling rate";
            }

            leaf allow-egress-filter-mirror-source {
                type boolean;
                default "false";
                description "Allow egress filters as mirror sources";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list mirror-dest {
                key "service-name";
                max-elements 255;
                description "Enter the mirror-dest list instance";

                leaf service-name {
                    type types-services:service-name;
                    description "Administrative service name";
                }

                leaf type {
                    type types-services:mirror-type;
                    sros-ext:immutable;
                    default "ether";
                    description "Mirror type information";
                }

                leaf fc {
                    type types-sros:fc-name;
                    default "be";
                    description "Forwarding class for destination traffic";
                }

                leaf slice-size {
                    type uint32 {
                        range "0|128..9216";
                    }
                    default "0";
                    description "Maximum size of the transmitted mirrored frame";
                }

                leaf sampling-rate {
                    type uint32 {
                        range "1..60000";
                    }
                    description "Sampling rate";
                }

                leaf use-global-sampling-rate {
                    type boolean;
                    default "false";
                    description "Enables global sampling rate by mirror destination";
                }

                leaf per-lag-hashing {
                    type boolean;
                    default "false";
                    description "Enable per-LAG hashing on the mirror destination";
                }

                leaf service-id {
                    type types-services:external-service-id;
                    sros-ext:immutable;
                    description "Service ID";
                }

                leaf description {
                    type types-sros:description;
                    description "Text description";
                }

                leaf admin-state {
                    type types-sros:admin-state;
                    default "disable";
                    description "Administrative state of the service";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list endpoint {
                    key "name";
                    max-elements 2;
                    description "Enter the endpoint list instance";

                    leaf name {
                        type types-sros:named-item;
                        description "Service endpoint name";
                    }

                    leaf description {
                        type types-sros:description;
                        description "Text description";
                    }

                    leaf revert-time {
                        type types-services:revert-time;
                        default "immediate";
                        description "Time to wait before reverting back to primary spoke SDP";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list endpoint

                list sap {
                    key "sap-id";
                    max-elements 1;
                    description "Enter the sap list instance";

                    leaf sap-id {
                        type types-sros:sap;
                        description "SAP ID";
                    }

                    leaf endpoint {
                        type leafref {
                            path "../../endpoint/name";
                        }
                        description "Service endpoint name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container egress {
                        description "Enter the egress context";

                        container qos {
                            description "Enter the qos context";

                            container sap-egress {
                                description "Enter the sap-egress context";

                                leaf policy-name {
                                    type leafref {
                                        path "../../../../../../../qos/sap-egress/sap-egress-policy-name";
                                    }
                                    description "Policy ID to associate with SAP for mirrored service";
                                }

                                container port-redirect-group {
                                    description "Enter the port-redirect-group context";

                                    leaf group-name {
                                        type leafref {
                                            path "../../../../../../../../qos/queue-group-templates/egress/queue-group/egress-queue-group-name";
                                        }
                                        description "Name of the queue group redirect list policy";
                                    }

                                    leaf instance {
                                        type types-services:qos-qgrp-instance-id;
                                        description "Port queue group instance";
                                    }

                                } // container port-redirect-group

                            } // container sap-egress

                        } // container qos

                        container ip-mirror {
                            description "Enter the ip-mirror context";

                            container mac {
                                description "Enter the mac context";

                                leaf source {
                                    type types-sros:mac-unicast-address;
                                    description "Source MAC address";
                                }

                                leaf destination {
                                    type yang:mac-address;
                                    description "Destination MAC address";
                                }

                            } // container mac

                        } // container ip-mirror

                    } // container egress


                } // list sap

                container remote-source {
                    presence "Enable the remote-source context";
                    description "Enable the remote-source context";

                    list far-end {
                        key "far-end-addr";
                        description "Enter the far-end list instance";

                        leaf far-end-addr {
                            type types-sros:ipv4-address;
                            description "Far end IP address";
                        }

                        leaf vc-id {
                            type uint32 {
                                range "1..max";
                            }
                            mandatory true;
                            description "Virtual circuit ID associated with the remote source";
                        }

                        leaf icb {
                            type boolean;
                            default "false";
                            description "Remote source as an inter-chassis backup";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        choice ingress-label {
                            default "label-signaling";
                            case label-signaling {

                                leaf label-signaling {
                                    type enumeration {
                                        enum tldp                           { value 2; }
                                    }
                                    default "tldp";
                                    description "Protocol to obtain the ingress labels";
                                }

                            }
                            case ing-vc-label {

                                leaf ing-vc-label {
                                    type types-services:ingress-vc-label;
                                    description "Ingress virtual circuit label";
                                }

                            }
                        }
                    } // list far-end

                    list spoke-sdp {
                        key "sdp-bind-id";
                        description "Enter the spoke-sdp list instance";

                        leaf sdp-bind-id {
                            type types-services:sdp-bind-id;
                            description "SDP ID number";
                        }

                        leaf admin-state {
                            type types-sros:admin-state;
                            default "enable";
                            description "Administrative state of the service SDP binding";
                        }

                        leaf control-word {
                            type boolean;
                            default "false";
                            description "Enable the PW control word on spoke SDPs";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container ingress {
                            description "Enter the ingress context";

                            leaf vc-label {
                                type types-services:ingress-vc-label;
                                sros-ext:auto-restart-to-modify;
                                description "MPLS VC label that sends packets to the far end device";
                            }

                            container l2tpv3 {
                                description "Enter the l2tpv3 context";

                                container cookie {
                                    description "Enter the cookie context";

                                    leaf cookie1 {
                                        type types-services:cookie-value;
                                        description "Value of the first cookie for the tunnel";
                                    }

                                    leaf cookie2 {
                                        type types-services:cookie-value;
                                        description "Value of the second cookie for the tunnel";
                                    }

                                } // container cookie

                            } // container l2tpv3

                        } // container ingress

                        container egress {
                            description "Enter the egress context";

                            leaf vc-label {
                                type types-services:egress-vc-label;
                                sros-ext:auto-restart-to-modify;
                                description "MPLS VC label that sends packets to the far end device";
                            }

                        } // container egress

                        container endpoint {
                            description "Enter the endpoint context";

                            leaf name {
                                type leafref {
                                    path "../../../../endpoint/name";
                                }
                                description "SAP-associated endpoint name";
                            }

                            leaf icb {
                                type boolean;
                                sros-ext:auto-restart-to-modify;
                                default "false";
                                description "Bind the SDP as the Inter-Chassis Backup (ICB) type";
                            }

                        } // container endpoint

                    } // list spoke-sdp

                } // container remote-source

                list spoke-sdp {
                    key "sdp-bind-id";
                    description "Enter the spoke-sdp list instance";

                    leaf sdp-bind-id {
                        type types-services:sdp-bind-id;
                        description "SDP ID number";
                    }

                    leaf admin-state {
                        type types-sros:admin-state;
                        default "enable";
                        description "Administrative state of the service SDP binding";
                    }

                    leaf control-word {
                        type boolean;
                        default "false";
                        description "Enable the PW control word on spoke SDPs";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container ingress {
                        description "Enter the ingress context";

                        leaf vc-label {
                            type types-services:ingress-vc-label;
                            sros-ext:auto-restart-to-modify;
                            description "MPLS VC label that sends packets to the far end device";
                        }

                    } // container ingress

                    container egress {
                        description "Enter the egress context";

                        leaf vc-label {
                            type types-services:egress-vc-label;
                            sros-ext:auto-restart-to-modify;
                            description "MPLS VC label that sends packets to the far end device";
                        }

                        container l2tpv3 {
                            description "Enter the l2tpv3 context";

                            leaf cookie {
                                type types-services:cookie-value;
                                description "RX or TX cookie for L2TPv3 spoke SDPs";
                            }

                        } // container l2tpv3

                    } // container egress

                    container endpoint {
                        description "Enter the endpoint context";

                        leaf name {
                            type leafref {
                                path "../../../endpoint/name";
                            }
                            description "Endpoint name associated with the SAP";
                        }

                        leaf precedence {
                            type types-services:sdp-precedence;
                            default "4";
                            description "Precedence when multiple SDP binds are on one endpoint";
                        }

                        leaf icb {
                            type boolean;
                            sros-ext:auto-restart-to-modify;
                            default "false";
                            description "Bind the SDP as the Inter-Chassis Backup (ICB) type";
                        }

                    } // container endpoint

                } // list spoke-sdp

                container encap {
                    description "Enter the encap context";

                    container layer-3-encap {
                        presence "Enable the layer-3-encap context";
                        description "Enable the layer-3-encap context";

                        leaf header-type {
                            type enumeration {
                                enum ip-udp-shim                    { value 1; }
                                enum ip-gre                         { value 2; }
                                enum ip-udp-shim-sampled            { value 4; }
                            }
                            sros-ext:immutable;
                            mandatory true;
                            description "Header type for Layer 3 encapsulation";
                        }

                        leaf direction-bit {
                            type boolean;
                            default "false";
                            description "Use the highest bit to specify traffic flow direction";
                        }

                        leaf router-instance {
                            type string;
                            default "Base";
                            description "Router instance to use with routed encapsulation";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container gateway {
                            presence "Enable the gateway context";
                            description "Enable the gateway context";

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container ip-address {
                                description "Enter the ip-address context";

                                leaf source {
                                    type types-sros:ipv4-unicast-address;
                                    description "IPv4 source address for the gateway";
                                }

                                leaf destination {
                                    type types-sros:ipv4-unicast-address;
                                    description "IPv4 destination address for the gateway";
                                }

                            } // container ip-address

                            container udp-port {
                                description "Enter the udp-port context";

                                leaf source {
                                    type types-sros:tcp-udp-port;
                                    default "0";
                                    description "UDP source port to use with the gateway";
                                }

                                leaf destination {
                                    type types-sros:tcp-udp-port;
                                    default "0";
                                    description "UDP destination port to use with the gateway";
                                }

                            } // container udp-port

                        } // container gateway

                    } // container layer-3-encap

                } // container encap

                list pcap {
                    key "session-name";
                    max-elements 1;
                    description "Enter the pcap list instance";

                    leaf session-name {
                        type types-sros:named-item;
                        description "PCAP session name";
                    }

                    leaf file-url {
                        type types-sros:ts-url-or-sftp-512;
                        description "URL and file name for packet capture transfer";
                    }

                    leaf router-instance {
                        type types-sros:named-item-64;
                        description "Router name used for FTP transmission of the PCAP file";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list pcap

            } // list mirror-dest

            list mirror-source {
                key "service-name";
                description "Enter the mirror-source list instance";

                leaf service-name {
                    type types-services:service-name;
                    description "Administrative service name";
                }

                leaf admin-state {
                    type types-sros:admin-state;
                    default "enable";
                    description "Administrative state of the mirror service";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list port {
                    key "port-id";
                    description "Enter the port list instance";

                    leaf port-id {
                        type types-services:mirror-source-port-lag-key;
                        description "Port ID";
                    }

                    leaf ingress {
                        type boolean;
                        default "false";
                        description "Mirror ingress packets";
                    }

                    leaf egress {
                        type boolean;
                        default "false";
                        description "Mirror egress packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list port

                list sap {
                    key "sap-id";
                    description "Enter the sap list instance";

                    leaf sap-id {
                        type types-sros:sap;
                        description "SAP ID";
                    }

                    leaf ingress {
                        type boolean;
                        default "false";
                        description "Mirror ingress packets";
                    }

                    leaf egress {
                        type boolean;
                        default "false";
                        description "Mirror egress packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list sap

                list ip-filter {
                    key "filter-name";
                    description "Enter the ip-filter list instance";

                    leaf filter-name {
                        type leafref {
                            path "../../../../filter/ip-filter/filter-name";
                        }
                        description "IP filter name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "entry-id";
                        min-elements 1;
                        description "Add a list entry for entry";

                        leaf entry-id {
                            type uint32 {
                                range "1..2097151";
                            }
                            description "IP filter entry ID";
                        }

                    } // list entry

                } // list ip-filter

                list ipv6-filter {
                    key "filter-name";
                    description "Enter the ipv6-filter list instance";

                    leaf filter-name {
                        type leafref {
                            path "../../../../filter/ipv6-filter/filter-name";
                        }
                        description "IPv6 filter name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "entry-id";
                        min-elements 1;
                        description "Add a list entry for entry";

                        leaf entry-id {
                            type uint32 {
                                range "1..2097151";
                            }
                            description "IPv6 filter entry ID";
                        }

                    } // list entry

                } // list ipv6-filter

                list mac-filter {
                    key "filter-name";
                    description "Enter the mac-filter list instance";

                    leaf filter-name {
                        type leafref {
                            path "../../../../filter/mac-filter/filter-name";
                        }
                        description "MAC filter name";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    list entry {
                        key "entry-id";
                        min-elements 1;
                        description "Add a list entry for entry";

                        leaf entry-id {
                            type uint32 {
                                range "1..2097151";
                            }
                            description "MAC filter entry ID";
                        }

                    } // list entry

                } // list mac-filter

                list subscriber {
                    key "subscriber-id";
                    description "Enter the subscriber list instance";

                    leaf subscriber-id {
                        type types-submgt:subscriber-id;
                        description "Subscriber ID";
                    }

                    leaf-list fc {
                        type enumeration {
                            enum be                             { value 0; }
                            enum l2                             { value 1; }
                            enum af                             { value 2; }
                            enum l1                             { value 3; }
                            enum h2                             { value 4; }
                            enum ef                             { value 5; }
                            enum h1                             { value 6; }
                            enum nc                             { value 7; }
                        }
                        max-elements 8;
                        description "The forwarding classes traffic which should be mirrored";
                    }

                    leaf ingress {
                        type boolean;
                        default "false";
                        description "Mirror ingress packets";
                    }

                    leaf egress {
                        type boolean;
                        default "false";
                        description "Mirror egress packets";
                    }

                    leaf host-type {
                        type enumeration {
                            enum ipoe                           { value 2; }
                            enum ppp                            { value 3; }
                        }
                        description "Host type for mirroring";
                    }

                    leaf ip-family {
                        type enumeration {
                            enum ipv4                           { value 2; }
                            enum ipv6                           { value 3; }
                        }
                        description "IP family for mirroring";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice host-identification {
                        case sap-id {

                            leaf sap-id {
                                type types-sros:sap;
                                description "Subscriber SAP ID";
                            }

                            leaf mac-address {
                                type yang:mac-address;
                                description "MAC address for the subscriber";
                            }

                            leaf ip-address {
                                type types-sros:ipv4-address;
                                description "Service IP address of remote device sending LI traffic";
                            }

                        }
                        case sla-profile {

                            leaf sla-profile {
                                type types-sros:named-item;
                                description "SLA profile name";
                            }

                        }
                    }
                } // list subscriber

                list vlan {
                    key "vlan-id";
                    description "Enter the vlan list instance";

                    leaf vlan-id {
                        type types-sros:port-and-encap;
                        description "Unique VLAN ID for the mirror-source element";
                    }

                    leaf ingress {
                        type boolean;
                        default "false";
                        description "Mirror ingress packets";
                    }

                    leaf egress {
                        type boolean;
                        default "false";
                        description "Mirror egress packets";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                } // list vlan

            } // list mirror-source

        } // container mirror

    } // grouping conf-mirror

}
