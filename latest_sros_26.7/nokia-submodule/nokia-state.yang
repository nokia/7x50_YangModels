module nokia-state {

    yang-version "1.1";

    namespace "urn:nokia.com:sros:ns:yang:sr:state";

    prefix "state";

    import nokia-sros-yang-extensions     { prefix "sros-ext"; }

    include nokia-state-aa-group;
    include nokia-state-aaa;
    include nokia-state-anysec;
    include nokia-state-application-assurance;
    include nokia-state-aps;
    include nokia-state-bfd;
    include nokia-state-call-trace;
    include nokia-state-card;
    include nokia-state-card-fp;
    include nokia-state-cflowd;
    include nokia-state-chassis;
    include nokia-state-cpm;
    include nokia-state-dms;
    include nokia-state-esa;
    include nokia-state-eth-cfm;
    include nokia-state-eth-ring;
    include nokia-state-filter;
    include nokia-state-filter-ip-exception;
    include nokia-state-group-encryption;
    include nokia-state-ipsec;
    include nokia-state-isa;
    include nokia-state-isa-application-assurance-group;
    include nokia-state-isa-video-group;
    include nokia-state-lag;
    include nokia-state-log;
    include nokia-state-macsec;
    include nokia-state-mcast-cac;
    include nokia-state-mcast-mgmt;
    include nokia-state-mirror;
    include nokia-state-oam-pm;
    include nokia-state-openflow;
    include nokia-state-policy-options;
    include nokia-state-port;
    include nokia-state-port-access;
    include nokia-state-port-dwdm;
    include nokia-state-port-dwdm-coherent;
    include nokia-state-port-eth-access;
    include nokia-state-port-eth-dot1x;
    include nokia-state-port-eth-efm-oam;
    include nokia-state-port-eth-egress;
    include nokia-state-port-eth-lldp;
    include nokia-state-port-eth-network;
    include nokia-state-port-ethernet;
    include nokia-state-port-gnss;
    include nokia-state-port-network;
    include nokia-state-port-otu;
    include nokia-state-port-serial;
    include nokia-state-port-sonet;
    include nokia-state-port-tdm;
    include nokia-state-pw-port;
    include nokia-state-pxc;
    include nokia-state-python;
    include nokia-state-qos;
    include nokia-state-redundancy;
    include nokia-state-router;
    include nokia-state-router-bgp;
    include nokia-state-router-bier;
    include nokia-state-router-dhcp-server;
    include nokia-state-router-fib-telemetry;
    include nokia-state-router-igmp;
    include nokia-state-router-isis;
    include nokia-state-router-l2tp;
    include nokia-state-router-ldp;
    include nokia-state-router-mld;
    include nokia-state-router-mpls;
    include nokia-state-router-msdp;
    include nokia-state-router-nat;
    include nokia-state-router-origin-validation;
    include nokia-state-router-ospf;
    include nokia-state-router-ospf3;
    include nokia-state-router-p2mp-sr-tree;
    include nokia-state-router-pcep;
    include nokia-state-router-pim;
    include nokia-state-router-radius;
    include nokia-state-router-rib-api;
    include nokia-state-router-rip;
    include nokia-state-router-ripng;
    include nokia-state-router-rsvp;
    include nokia-state-router-segment-routing;
    include nokia-state-router-static-route;
    include nokia-state-router-twamp-light;
    include nokia-state-router-wpp;
    include nokia-state-saa;
    include nokia-state-satellite;
    include nokia-state-service;
    include nokia-state-sfm;
    include nokia-state-submgt-gtp;
    include nokia-state-submgt-isa-filter;
    include nokia-state-submgt-local-user-db;
    include nokia-state-submgt-service-chaining;
    include nokia-state-submgt-subscriber;
    include nokia-state-submgt-vrgw;
    include nokia-state-submgt-wlangw;
    include nokia-state-subscriber-mgmt;
    include nokia-state-svc-cpipe;
    include nokia-state-svc-epipe;
    include nokia-state-svc-ies;
    include nokia-state-svc-ies-grp-if-wlangw;
    include nokia-state-svc-ies-sub-if;
    include nokia-state-svc-ies-sub-if-wlangw;
    include nokia-state-svc-ies-vdo-if;
    include nokia-state-svc-ipipe;
    include nokia-state-svc-nat;
    include nokia-state-svc-sdp;
    include nokia-state-svc-vpls;
    include nokia-state-svc-vprn;
    include nokia-state-svc-vprn-dhcp-server;
    include nokia-state-svc-vprn-grp-if-wlangw;
    include nokia-state-svc-vprn-isis;
    include nokia-state-svc-vprn-msdp;
    include nokia-state-svc-vprn-ospf;
    include nokia-state-svc-vprn-ospf3;
    include nokia-state-svc-vprn-radius;
    include nokia-state-svc-vprn-rib-api;
    include nokia-state-svc-vprn-rip;
    include nokia-state-svc-vprn-ripng;
    include nokia-state-svc-vprn-sub-if;
    include nokia-state-svc-vprn-sub-if-wlangw;
    include nokia-state-svc-vprn-twamp-light;
    include nokia-state-svc-vprn-vdo-if;
    include nokia-state-system;
    include nokia-state-system-bluetooth;
    include nokia-state-system-bootup;
    include nokia-state-system-central-frequency-clock;
    include nokia-state-system-cron;
    include nokia-state-system-licensing;
    include nokia-state-system-ptp;
    include nokia-state-system-script-control;
    include nokia-state-system-security;
    include nokia-state-system-security-aaa;
    include nokia-state-system-security-cpm;
    include nokia-state-system-security-management-access-filter;
    include nokia-state-system-security-pki;
    include nokia-state-system-security-ssh;
    include nokia-state-system-security-tls;
    include nokia-state-system-security-user-parameters;
    include nokia-state-system-telemetry;
    include nokia-state-system-time;
    include nokia-state-test-oam;
    include nokia-state-testoam-service-activation-testhead;
    include nokia-state-users;
    include nokia-state-video;
    include nokia-state-vrrp;

    sros-ext:sros-major-release "rel26";
    organization "Nokia";
    contact
        "Nokia SR OS Support
         Web: <http://www.nokia.com>";
    description
        "Nokia YANG Data model with operational state for all data on SR OS based routers.

         Copyright 2016 Nokia. All rights reserved. Reproduction of this document
         is authorized on the condition that the foregoing copyright notice is included.

         This nokia-state YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    container state {
        config false;
        description "Show state information";

        uses state-aaa;
        uses state-anysec;
        uses state-application-assurance;
        uses state-aps;
        uses state-bfd;
        uses state-call-trace;
        uses state-card;
        uses state-cflowd;
        uses state-chassis;
        uses state-cpm;
        uses state-dms-defender-mitigation-system;
        uses state-esa;
        uses state-eth-cfm;
        uses state-eth-ring;
        uses state-filter;
        uses state-pxc-fwd-path-ext;
        uses state-group-encryption;
        uses state-ipsec;
        uses state-isa;
        uses state-lag;
        uses state-log;
        uses state-macsec;
        uses state-mcast-cac-mcac;
        uses state-mirror;
        uses state-mcast-mgmt-multicast-management;
        uses state-router-mvpn-extranet;
        uses state-oam-pm;
        uses state-openflow;
        uses state-policy-options;
        uses state-port;
        uses state-pxc-port-xc;
        uses state-pw-port;
        uses state-python;
        uses state-qos;
        uses state-redundancy;
        uses state-router;
        uses state-saa;
        uses state-satellite;
        uses state-service;
        uses state-sfm;
        uses state-subscriber-mgmt;
        uses state-system;
        uses state-test-oam;
        uses state-users;
        uses state-video;
        uses state-vrrp;
    } // container state

}
