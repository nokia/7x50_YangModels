submodule nokia-conf-submgt-isa-filter {

    yang-version "1.1";

    belongs-to nokia-conf { prefix "conf"; }

    import nokia-sros-yang-extensions     { prefix "sros-ext"; }
    import nokia-types-filter             { prefix "types-filter"; }
    import nokia-types-sros               { prefix "types-sros"; }

    include nokia-conf-groups;

    sros-ext:sros-major-release "rel26";
    organization "Nokia";
    contact
        "Nokia SR OS Support
         Web: <http://www.nokia.com>";
    description
        "Nokia YANG Data model to configure subscriber management isa filter on SR OS based routers.

         Copyright 2016 Nokia. All rights reserved. Reproduction of this document
         is authorized on the condition that the foregoing copyright notice is included.

         This nokia-conf-submgt-isa-filter YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-09-02";

    grouping conf-submgt-isa-filter {
        list isa-filter {
            key "name";
            description "Enter the isa-filter list instance";

            leaf name {
                type types-sros:named-item {
                    pattern "[^_].*" {
                        error-message "'identifier' must not start with _ (reserved for internal use)";
                    }
                }
                description "ISA filter name";
            }

            leaf type {
                type enumeration {
                    enum dsm {
                        value 0;
                        description "Limited to DSM applications";
                    }
                }
                sros-ext:immutable;
                default "dsm";
                description "Limit what the ISA filter can be used for";
            }

            leaf description {
                type types-sros:description;
                description "Text description";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container ipv4 {
                description "Enter the ipv4 context";

                leaf default-action {
                    type types-filter:isa-filter-default-action;
                    description "Action for non-matching entry";
                }

                list entry {
                    key "id";
                    description "Enter the entry list instance";

                    leaf id {
                        type uint16 {
                            range "1..1024";
                        }
                        description "ISA filter entry ID";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container action {
                        presence "Enable the action context";
                        description "Enable the action context";

                        choice action {
                            mandatory true;
                            case drop {

                                leaf drop {
                                    type empty;
                                    description "A packet matching the entry will be dropped";
                                }

                            }
                            case forward {

                                leaf forward {
                                    type empty;
                                    description "A packet matching the entry will be forwarded";
                                }

                            }
                            case http-redirect {

                                container http-redirect {
                                    presence "Enable the http-redirect context";
                                    description "Enable the http-redirect context";

                                    leaf url {
                                        type types-sros:http-redirect-url;
                                        sros-ext:immutable;
                                        mandatory true;
                                        description "HTTP URL to which the matching traffic is redirected";
                                    }

                                } // container http-redirect

                            }
                        }
                    } // container action

                    container match {
                        description "Enter the match context";

                        leaf protocol {
                            type enumeration {
                                enum icmp {
                                    value 1;
                                    description "Match only ICMP packets";
                                }
                                enum tcp {
                                    value 6;
                                    description "Match only TCP packets";
                                }
                                enum udp {
                                    value 17;
                                    description "Match only UDP packets";
                                }
                                enum gre {
                                    value 47;
                                    description "Match only GRE packets";
                                }
                            }
                            description "Protocol";
                        }

                        leaf dst-ip {
                            type types-sros:ipv4-prefix;
                            description "Destination IPv4 prefix";
                        }


                        container dst-port {
                            description "Enter the dst-port context";

                            choice operator-choices {
                                case equals {

                                    leaf equals {
                                        type types-sros:tcp-udp-port;
                                        description "Exact port number";
                                    }

                                }
                            }
                        } // container dst-port

                    } // container match

                } // list entry

            } // container ipv4

            container ipv6 {
                description "Enter the ipv6 context";

                leaf default-action {
                    type types-filter:isa-filter-default-action;
                    description "Action for non-matching entry";
                }

                list entry {
                    key "id";
                    description "Enter the entry list instance";

                    leaf id {
                        type uint16 {
                            range "1..1024";
                        }
                        description "ISA filter entry ID";
                    }

                    leaf description {
                        type types-sros:description;
                        description "Text description";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container action {
                        presence "Enable the action context";
                        description "Enable the action context";

                        choice action {
                            mandatory true;
                            case drop {

                                leaf drop {
                                    type empty;
                                    description "A packet matching the entry will be dropped";
                                }

                            }
                            case forward {

                                leaf forward {
                                    type empty;
                                    description "A packet matching the entry will be forwarded";
                                }

                            }
                            case http-redirect {

                                container http-redirect {
                                    presence "Enable the http-redirect context";
                                    description "Enable the http-redirect context";

                                    leaf url {
                                        type types-sros:http-redirect-url;
                                        sros-ext:immutable;
                                        mandatory true;
                                        description "HTTP URL to which the matching traffic is redirected";
                                    }

                                } // container http-redirect

                            }
                        }
                    } // container action

                    container match {
                        description "Enter the match context";

                        leaf protocol {
                            type enumeration {
                                enum icmp {
                                    value 1;
                                    description "Match only ICMP packets";
                                }
                                enum tcp {
                                    value 6;
                                    description "Match only TCP packets";
                                }
                                enum udp {
                                    value 17;
                                    description "Match only UDP packets";
                                }
                                enum gre {
                                    value 47;
                                    description "Match only GRE packets";
                                }
                            }
                            description "Protocol";
                        }

                        leaf dst-ip {
                            type types-sros:ipv6-prefix;
                            description "Destination IPv6 prefix";
                        }


                        container dst-port {
                            description "Enter the dst-port context";

                            choice operator-choices {
                                case equals {

                                    leaf equals {
                                        type types-sros:tcp-udp-port;
                                        description "Exact port number";
                                    }

                                }
                            }
                        } // container dst-port

                    } // container match

                } // list entry

            } // container ipv6

        } // list isa-filter

    } // grouping conf-submgt-isa-filter

}
