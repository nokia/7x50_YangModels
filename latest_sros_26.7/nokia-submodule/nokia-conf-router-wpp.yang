submodule nokia-conf-router-wpp {

    yang-version "1.1";

    belongs-to nokia-conf { prefix "conf"; }

    import nokia-sros-yang-extensions     { prefix "sros-ext"; }
    import nokia-types-sros               { prefix "types-sros"; }

    include nokia-conf-groups;

    sros-ext:sros-major-release "rel26";
    organization "Nokia";
    contact
        "Nokia SR OS Support
         Web: <http://www.nokia.com>";
    description
        "Nokia YANG Data model to configure wpp on SR OS based routers.

         Copyright 2016 Nokia. All rights reserved. Reproduction of this document
         is authorized on the condition that the foregoing copyright notice is included.

         This nokia-conf-router-wpp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping conf-router-wpp {
        container wpp {
            presence "Enable the wpp context";
            description "Enable the wpp context";

            leaf admin-state {
                type types-sros:admin-state;
                default "disable";
                description "Administrative state of WPP";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            list portal {
                key "name";
                description "Enter the portal list instance";

                leaf name {
                    type types-sros:named-item;
                    description "Web portal name";
                }

                leaf address {
                    type types-sros:ip-unicast-without-local-address;
                    sros-ext:immutable;
                    mandatory true;
                    description "WPP portal address";
                }

                leaf admin-state {
                    type types-sros:admin-state;
                    default "disable";
                    description "Administrative state of the WPP portal server";
                }

                leaf secret {
                    type types-sros:encrypted-leaf {
                        length "1..166";
                    }
                    description "Message authentication between portal and BRAS by applying the secret used by WPPv2";
                }

                leaf version {
                    type uint32 {
                        range "1|2";
                    }
                    default "1";
                    description "Protocol version to be expected by the WPP portal";
                }

                leaf retry-interval {
                    type uint32 {
                        range "10..2000";
                    }
                    units "milliseconds";
                    default "2000";
                    description "Time between two consecutive retransmissions";
                }

                leaf ntf-logout-retry-count {
                    type uint32 {
                        range "0..5";
                    }
                    default "5";
                    description "Number of retransmissions of an NTF_LOGOUT message";
                }

                leaf ack-auth-retry-count {
                    type uint32 {
                        range "0..5";
                    }
                    default "5";
                    description "Number of retransmissions of an ACK_OUT message";
                }

                leaf port-format {
                    type enumeration {
                        enum standard                       { value 1; }
                        enum vendor-specific                { value 2; }
                    }
                    default "standard";
                    description "Format of the port in the ACK_INO message";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // list portal

        } // container wpp

    } // grouping conf-router-wpp

}
