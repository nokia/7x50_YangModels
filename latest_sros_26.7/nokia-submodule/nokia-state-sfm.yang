submodule nokia-state-sfm {

    yang-version "1.1";

    belongs-to nokia-state { prefix "state"; }

    import ietf-yang-types                { prefix "yang"; }
    import nokia-sros-yang-extensions     { prefix "sros-ext"; }
    import nokia-types-chassis            { prefix "types-chassis"; }
    import nokia-types-sfm                { prefix "types-sfm"; }
    import nokia-types-sros               { prefix "types-sros"; }

    sros-ext:sros-major-release "rel26";
    organization "Nokia";
    contact
        "Nokia SR OS Support
         Web: <http://www.nokia.com>";
    description
        "Nokia YANG Data model with operational state for switch fabric modules on SR OS based routers.

         Copyright 2016 Nokia. All rights reserved. Reproduction of this document
         is authorized on the condition that the foregoing copyright notice is included.

         This nokia-state-sfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    grouping state-sfm {
        list sfm {
            key "sfm-slot";
            description "Enter the sfm list instance";

            leaf sfm-slot {
                type uint32 {
                    range "1..16";
                }
                description
                    "The unique value which identifies this SFM slot within a
                     chassis in the system.";
            }

            leaf equipped-type {
                type types-sfm:sros-sfm-type-state;
                description
                    "Indicates the switch fabric card type that is physically
                     inserted into this slot in this chassis.";
            }

            container hardware-data {
                description "Enter the hardware-data context";

                leaf part-number {
                    type string {
                        length "0..32";
                    }
                    description "Indicates the part number information.";
                }

                leaf serial-number {
                    type string {
                        length "0..32";
                    }
                    description "Indicates the serial number of the hardware component.";
                }

                leaf manufacturing-date {
                    type string {
                        length "0..8";
                    }
                    description "Indicates the manufacturing date of the hardware component.";
                }

                leaf common-language-equipment-identifier {
                    type string {
                        length "0..10";
                    }
                    description
                        "Indicates the CLEI, a unique 10-character identifier fixed
                         by the manufacturer.";
                }

                leaf field-replaceable-unit {
                    type boolean;
                    description
                        "Indicates whether the hardware component is a field
                         replaceable unit or not.";
                }

                leaf contained-in {
                    type types-sros:named-item-or-empty;
                    description
                        "Indicates the hardware component that contains this
                         component. An empty string indicates that this component is not
                         contained in any other component.";
                }

                leaf oper-state {
                    type types-chassis:hw-oper-state;
                    description "Indicates the operational status of the hardware component.";
                }

                leaf failure-reason {
                    type string {
                        length "0..255";
                    }
                    description
                        "Indicates the reason why a hardware component 'failed' as
                         indicated in oper-state.";
                }

                leaf contains-temperature-sensor {
                    type boolean;
                    description
                        "Indicates whether or not this hardware component contains
                         a temperature sensor.";
                }

                leaf temperature {
                    type int32;
                    description
                        "Indicates the current temperature in degrees celsius from
                         the temperature sensor.";
                }

                leaf temperature-threshold {
                    type int32;
                    description
                        "Indicates the temperature threshold for this hardware
                         component in degrees celsius.";
                }

                leaf alarm-state {
                    type enumeration {
                        enum unknown                        { value 0; }
                        enum alarm-active                   { value 1; }
                        enum alarm-cleared                  { value 2; }
                    }
                    description
                        "Indicates the current alarm state for this hardware
                         component.";
                }

                leaf manufacturing-deviations {
                    type string {
                        length "0..255";
                    }
                    description
                        "Indicates the record of changes done by the manfacturing
                         to the hardware or software which is outside the normal
                         revision control process.";
                }

                leaf equipped-platform-type {
                    type types-chassis:equipped-platform-type;
                    description
                        "Indicates the platform type of the installed hardware
                         component, as read from the EEPROM.";
                }

                leaf manufacturing-assembly-number {
                    type string {
                        length "0..32";
                    }
                    description
                        "Indicates an assembly number indicating manufacturing
                         differences for a given part number.";
                }

                leaf power-zone-location {
                    type uint32 {
                        range "0..32";
                    }
                    description
                        "Indicates the managed power zone that this hardware
                         component resides.";
                }

                leaf base-mac-address {
                    type yang:mac-address;
                    description "Indicates the base MAC address of the hardware component.";
                }

                leaf boot-code-version {
                    type string {
                        length "0..255";
                    }
                    description "Indicates the version number of boot eprom.";
                }

                leaf software-code-version {
                    type string {
                        length "0..255";
                    }
                    description
                        "Indicates the software product release version number for the
                         software image currently running.";
                }

                leaf software-last-boot-time {
                    type yang:date-and-time;
                    description
                        "This indicates the date and time the software running on this
                         hardware component was last rebooted.";
                }

                leaf software-image-source {
                    type enumeration {
                        enum unknown                        { value 0; }
                        enum primary                        { value 1; }
                        enum secondary                      { value 2; }
                        enum tertiary                       { value 3; }
                    }
                    description
                        "Indicates the location in the Boot Options File (BOF)
                         where the software image file was found when the system last
                         rebooted.";
                }

                leaf firmware-code-version {
                    type string {
                        length "0..255";
                    }
                    description
                        "Indicates the software product release version number
                         associated with the firmware version currently programmed.";
                }

                leaf firmware-revision-status {
                    type enumeration {
                        enum not-applicable                 { value 0; }
                        enum acceptable                     { value 1; }
                        enum not-acceptable                 { value 2; }
                        enum upgrade-pending                { value 3; }
                        enum upgrading                      { value 4; }
                        enum upgrade-next-hard-reset        { value 5; }
                        enum power-cycle-required           { value 6; }
                    }
                    description
                        "Indicates the firmware/FPGA revision status for the
                         hardware component.";
                }

            } // container hardware-data

            container hardware-resource {
                description "Enter the hardware-resource context";

                container amperage {
                    description "Enter the amperage context";

                    leaf current {
                        type int32;
                        units "milliamperes";
                        description
                            "Indicates the current amperage use of the managed hardware component
                             in milli-Amperes (mA).";
                    }

                    leaf minimum {
                        type int32;
                        units "milliamperes";
                        description
                            "Indicates the lowest amperage use of the managed hardware component
                             in milli-Amperes (mA), recorded at the time indicated by
                             minimum-time";
                    }

                    leaf minimum-time {
                        type yang:date-and-time;
                        description "Indicates the time and date at which minimum amperage was last updated.";
                    }

                    leaf peak {
                        type int32;
                        units "milliamperes";
                        description
                            "Indicates the peak amperage use of the managed hardware component
                             in milli-Amperes (mA), recorded at the time indicated by
                             peak-time.";
                    }

                    leaf peak-time {
                        type yang:date-and-time;
                        description "Indicates the time and date at which peak amperage was last updated";
                    }

                } // container amperage

                container voltage {
                    description "Enter the voltage context";

                    leaf current {
                        type int32;
                        units "millivolts";
                        description
                            "Indicates the current voltage use of the managed hardware component
                             in milli-Volts (mV).";
                    }

                    leaf minimum {
                        type int32;
                        units "millivolts";
                        description
                            "Indicates the lowest voltage use of the managed hardware component
                             in milli-Volts (mV), last recorded at the time indicated by
                             minimum-time";
                    }

                    leaf minimum-time {
                        type yang:date-and-time;
                        description "Indicates the time and date at which minimum voltage was last updated.";
                    }

                    leaf peak {
                        type int32;
                        units "millivolts";
                        description
                            "Indicates the peak voltage use of the managed hardware component
                             in milli-Volts (mV), last recorded at the time indicated by
                             peak-time.";
                    }

                    leaf peak-time {
                        type yang:date-and-time;
                        description "Indicates the time and date at which peak voltage was last updated";
                    }

                } // container voltage

                container wattage {
                    description "Enter the wattage context";

                    leaf current {
                        type int32;
                        units "milliwatts";
                        description
                            "Indicates the current wattage use of the managed hardware component
                             in milli-Watts (mW).";
                    }

                    leaf minimum {
                        type int32;
                        units "milliwatts";
                        description
                            "Indicates the lowest wattage use of the managed hardware component
                             in milli-Watts (mW), last recorded at the time indicated by
                             minimum-time";
                    }

                    leaf minimum-time {
                        type yang:date-and-time;
                        description "Indicates the time and date at which minimum wattage was last updated.";
                    }

                    leaf peak {
                        type int32;
                        units "milliwatts";
                        description
                            "Indicates the peak wattage use of the managed hardware component
                             in milli-Watts (mW), last recorded at the time indicated by
                             peak-time.";
                    }

                    leaf peak-time {
                        type yang:date-and-time;
                        description "Indicates the time and date at which was last updated";
                    }

                    leaf required {
                        type int32;
                        units "milliwatts";
                        description
                            "Indicates the wattage required by the managed hardware component
                             in milli-Watts (mW).";
                    }

                } // container wattage

            } // container hardware-resource

        } // list sfm

    } // grouping state-sfm

}
