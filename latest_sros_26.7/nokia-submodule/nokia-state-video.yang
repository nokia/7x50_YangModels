submodule nokia-state-video {

    yang-version "1.1";

    belongs-to nokia-state { prefix "state"; }

    import nokia-sros-yang-extensions     { prefix "sros-ext"; }

    include nokia-state-service;
    include nokia-state-svc-ies;
    include nokia-state-svc-ies-vdo-if;
    include nokia-state-svc-vprn;
    include nokia-state-svc-vprn-vdo-if;

    sros-ext:sros-major-release "rel26";
    organization "Nokia";
    contact
        "Nokia SR OS Support
         Web: <http://www.nokia.com>";
    description
        "Nokia YANG Data model with operational state for Video telemetry on SR OS based routers.

         Copyright 2016 Nokia. All rights reserved. Reproduction of this document
         is authorized on the condition that the foregoing copyright notice is included.

         This nokia-state-video YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    grouping state-video {
        container video {
            description "Enter the video context";

            container vqm {
                description "Enter the vqm context";

                container service {
                    description "Enter the service context";

                    list ies {
                        key "service-name";
                        description "Enter the ies list instance";

                        leaf service-name {
                            type leafref {
                                path "../../../../../service/ies/service-name";
                            }
                            description "Name of the service";
                        }

                        list video-interface {
                            key "interface-name";
                            description "Enter the video-interface list instance";

                            leaf interface-name {
                                type leafref {
                                    path "../../../../../../service/ies/video-interface/interface-name";
                                }
                                description "[29 chars max] (must start with a letter).";
                            }

                            container channels {
                                description "Enter the channels context";

                                list channel {
                                    key "mcast-address source";
                                    description "Enter the channel list instance";

                                    leaf mcast-address {
                                        type leafref {
                                            path "../../../../../../../../service/ies/video-interface/channel[source=current()/../source]/mcast-address";
                                        }
                                        description "a.b.c.d - multicast channel address.";
                                    }

                                    leaf source {
                                        type leafref {
                                            path "../../../../../../../../service/ies/video-interface/channel[mcast-address=current()/../mcast-address]/source";
                                        }
                                        description "a.b.c.d - unicast source address.";
                                    }

                                    leaf severity {
                                        type enumeration {
                                            enum no-errors                      { value 0; }
                                            enum traffic-loss                   { value 3; }
                                        }
                                        description "MC channel health condition.";
                                    }

                                } // list channel

                            } // container channels

                        } // list video-interface

                    } // list ies

                    list vprn {
                        key "service-name";
                        description "Enter the vprn list instance";

                        leaf service-name {
                            type leafref {
                                path "../../../../../service/vprn/service-name";
                            }
                            description "Name of the service";
                        }

                        list video-interface {
                            key "interface-name";
                            description "Enter the video-interface list instance";

                            leaf interface-name {
                                type leafref {
                                    path "../../../../../../service/vprn/video-interface/interface-name";
                                }
                                description "[29 chars max] (must start with a letter).";
                            }

                            container channels {
                                description "Enter the channels context";

                                list channel {
                                    key "mcast-address source";
                                    description "Enter the channel list instance";

                                    leaf mcast-address {
                                        type leafref {
                                            path "../../../../../../../../service/vprn/video-interface/channel[source=current()/../source]/mcast-address";
                                        }
                                        description "a.b.c.d - multicast channel address.";
                                    }

                                    leaf source {
                                        type leafref {
                                            path "../../../../../../../../service/vprn/video-interface/channel[mcast-address=current()/../mcast-address]/source";
                                        }
                                        description "a.b.c.d - unicast source address.";
                                    }

                                    leaf severity {
                                        type enumeration {
                                            enum no-errors                      { value 0; }
                                            enum traffic-loss                   { value 3; }
                                        }
                                        description "MC channel health condition.";
                                    }

                                } // list channel

                            } // container channels

                        } // list video-interface

                    } // list vprn

                } // container service

            } // container vqm

        } // container video

    } // grouping state-video

}
