module nokia-types-sros {

    yang-version "1.1";

    namespace "urn:nokia.com:sros:ns:yang:sr:types-sros";

    prefix "types-sros";

    import ietf-inet-types                { prefix "inet"; }
    import nokia-sros-yang-extensions     { prefix "sros-ext"; }

    sros-ext:sros-major-release "rel26";
    organization "Nokia";
    contact
        "Nokia SR OS Support
         Web: <http://www.nokia.com>";
    description
        "Common data-types data types used in the SR OS management system.

         Copyright 2016 Nokia. All rights reserved. Reproduction of this document
         is authorized on the condition that the foregoing copyright notice is included.

         This nokia-types-sros YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    typedef string-not-all-spaces {
        type string {
            pattern "(.*\\S.*)|()" {
                error-message "'string-not-all-spaces' must contain at least one non-space character";
            }
        }
    }

    typedef ieee-address {
        type string {
            pattern "([0-9a-fA-F]{2}(:[0-9a-fA-F]{2}){5})|([0-9a-fA-F]{2}(-[0-9a-fA-F]{2}){5})" {
                error-message "'ieee-address' must be 6 hex byte pairs with ':' or '-' (e.g. 00:11:22:33:44:55)";
            }
        }
        description "The ieee-address type represents an IEEE 802 MAC address.";
    }

    typedef action-type {
        type enumeration {
            enum do-action                      { value 1; }
            enum not-applicable                 { value 2; }
        }
        description
            "action-type specifies a set and forget field where one can trigger
             an event.";
    }

    typedef admin-state {
        type enumeration {
            enum enable                         { value 1; }
            enum disable                        { value 2; }
        }
        description
            "admin-state specifies the general administrative state for the
             typical SR OS entity that supports administrative states.";
    }

    typedef enabled-disabled {
        type enumeration {
            enum enabled                        { value 1; }
            enum disabled                       { value 2; }
        }
        description
            "enabled-disabled specifies the general administrative state for the
             typical SR OS entity that supports administrative states.";
    }

    typedef admin-state-with-inherit {
        type enumeration {
            enum enable                         { value 1; }
            enum disable                        { value 2; }
        }
        description
            "admin-state specifies the general administrative state
             for the typical SR OS entity that supports administrative states.";
    }

    typedef date-time {
        type string;
        description "Like IETF Yang and ISO8601 date-and-time; can be empty.";
    }

    typedef description {
        type string-not-all-spaces {
            length "1..80";
        }
        description
            "description is the standard description type, which is an 80
             character printable ASCII style string. This string supports the
             following characteristics:
                1. Only 7-bit printable ascii characters are supported.";
    }

    typedef description-or-empty {
        type string-not-all-spaces {
            length "0..80";
        }
        description
            "description is the standard description type, which is an 80
             character printable ASCII style string or empty string.
             This string supports the following characteristics:
                1. Only 7-bit printable ascii characters are supported.";
    }

    typedef long-description {
        type string-not-all-spaces {
            length "1..160";
        }
        description
            "description is the standard description type, which is an 80
             character printable ASCII style string. This string supports the
             following characteristics:
                1. Only 7-bit printable ascii characters are supported.";
    }

    typedef very-long-description {
        type string-not-all-spaces {
            length "1..255";
        }
        description
            "description is an 255
             character printable ASCII style string. This string supports the
             following characteristics:
                1. Only 7-bit printable ascii characters are supported.";
    }

    typedef very-long-description-or-empty {
        type string-not-all-spaces {
            length "0..255";
        }
        description
            "description is a 255 character printable ASCII style string. This string
             supports the following characteristics:
                1. Only 7-bit printable ascii characters are supported.";
    }

    typedef clli-description {
        type string-not-all-spaces {
            length "11";
        }
        description "Common Language Location Identifier (CLLI)";
    }

    typedef description-allow-all-white-spaces {
        type string {
            length "1..80";
        }
        description
            "description is the standard description type, which is an 80
             character printable ASCII style string. This string supports the
             following characteristics:
                1. Only 7-bit printable ascii characters are supported.";
    }

    typedef direction {
        type enumeration {
            enum ingress                        { value 1; }
            enum egress                         { value 2; }
        }
        description
            "direction is the standard networking 'direction' attribute
             specifying the data-path direction for traffic.";
    }

    typedef hex-string {
        type string {
            pattern "0x[a-fA-F0-9]+" {
                error-message "'hex-string' must be hexadecimal with prefix 0x (e.g. 0x1a2b)";
            }
        }
        description "A string containing only hexadecimal characters with prefix '0x'";
    }

    typedef encrypted-leaf {
        type string;
        description
            "The encrypted-leaf type is used to store data that may require encryption
             to keep the value secret.

             The value of this type matches one of the forms:

               <clear text password>
               <encrypted password> hash
               <encrypted password> hash2
               <encrypted password> hash3
               <encrypted password> custom

             Input is accepted in clear text or encrypted formats. Some examples include:

               my-secret-key-value-in-clear-text
               041t1ZLCi1aNcsCFfuXzNcxsaFqo7gYK2k9W1/CxzrDuFpGHciA9W2iuwRFr19pC hash
               g5ZC+XrkjBR/VZcLujUQSfXheGWw6/XyKp8uok+DMyEx9HE6pjgEY0tP7vdv4QD21A== hash2
               qz3ZeWKSSynD8BRHx2fdzxNhu/QqEwygE8cIXoYI6dZsZEO5UJhug4y4EhwX4KPXasWKxDWHqa6U hash3

             The output format (for a get/read or generation of configuration files) is
             controlled by configuration and can be set to always return encrypted values.";
    }

    typedef encrypted-leaf-hex {
        type encrypted-leaf {
            pattern "0x[a-fA-F0-9]+|.{1,416}( hash| hash2| hash3| custom)" {
                error-message "'encrypted-leaf-hex' must have clear text in hex with prefix 0x or end with hash/hash2/hash3/custom";
            }
        }
        description
            "Extension of type 'encrypted-leaf' allowing only hexadecimal characters with
             prefix '0x'";
    }

    typedef encrypted-leaf-hex-without-prefix {
        type encrypted-leaf {
            pattern "[a-fA-F0-9]+|.{1,416}( hash| hash2| hash3| custom)" {
                error-message "'encrypted-leaf-hex-without-prefix' must have clear text in hex without 0x or end with hash/hash2/hash3/custom";
            }
        }
        description
            "Extension of type 'encrypted-leaf' allowing only hexadecimal characters without
             prefix '0x'.";
    }

    typedef static-encrypted-state-leaf {
        type string;
        description
            "The static-encrypted-state-leaf type is used for operational
             state data that is output in an encrypted format.";
    }

    typedef bof-static-encrypted-leaf {
        type string;
        description
            "The bof-static-encrypted-leaf type is used to store bof
             configuration data that requires encryption to keep the value secret.

             The value of this type matches one of the forms:

                 <clear text password>
                 <encrypted password> hash2

             Input is accepted in clear text or encrypted formats. Some examples include:

                 my-secret-key-value-in-clear-text
                 g5ZC+XrkjBR/VZcLujUQSfXheGWw6/XyKp8uok+DMyEx9HE6pjgEY0tP7vdv4QD21A== hash2

             The output format for a get/read or generation of the BOF configuration
             file is always encrypted.";
    }

    typedef li-static-encrypted-leaf {
        type string;
        description
            "The li-static-encrypted-leaf type is used to store lawful intercept
             configuration data that requires encryption to keep the value secret.

             The value of this type matches one of the forms:

                 <clear text password>
                 <encrypted password> hash2
                 <encrypted password> hash3

             Input is accepted in clear text or encrypted formats. Some examples include:

                 my-secret-key-value-in-clear-text
                 g5ZC+XrkjBR/VZcLujUQSfXheGWw6/XyKp8uok+DMyEx9HE6pjgEY0tP7vdv4QD21A== hash2
                 qz3ZeWKSSynD8BRHx2fdzxNhu/QqEwygE8cIXoYI6dZsZEO5UJhug4y4EhwX4KPXasWKxDWHqa6U hash3

             The output format (for a get/read or generation of configuration files) is
             always encrypted.";
    }

    typedef li-static-encrypted-leaf-hex {
        type li-static-encrypted-leaf {
            pattern "0x[a-fA-F0-9]+|.{1,416}( hash2| hash3)" {
                error-message "'li-static-encrypted-leaf-hex' must have clear text in hex with prefix 0x or end with hash2/hash3";
            }
        }
        description
            "Extension of type 'li-static-encrypted-leaf' allowing only hexadecimal characters with
             prefix '0x'";
    }

    typedef hashed-leaf {
        type string;
        description
            "The hashed-leaf type is used to store secret irreversible passwords.

             The value of this type matches one of the forms:

                 <clear text password>
                 <hashed password>

             Input is accepted in clear text or hashed formats. Some examples include:
                 my-secret-password-in-clear-text
                 $2y$10$CHfBh4mZdqbPay7oWQvYA.LMBirkS/tDCSNUzi185/Y2H4MOMR/LG

             The output format (for a get/read or generation of configuration files) is always
             the hashed form.";
    }

    typedef named-item {
        type string-not-all-spaces {
            length "1..32";
        }
        description "Named item used for naming instances of entities.";
    }

    typedef named-item-or-empty {
        type string-not-all-spaces {
            length "0..32";
        }
        description "Named item used for naming instances of entities.";
    }

    typedef named-item-or-space {
        type string {
            length "1..32";
        }
        description "Named item used for naming instances of entities.";
    }

    typedef named-item-64 {
        type string-not-all-spaces {
            length "1..64";
        }
        description "Named item used for naming instances of entities.";
    }

    typedef named-item-64-or-empty {
        type string-not-all-spaces {
            length "0..64";
        }
        description "Named item used for naming instances of entities.";
    }

    typedef named-item-255 {
        type string-not-all-spaces {
            length "1..255";
        }
        description "The extra long name of an item.";
    }

    typedef named-item-255-or-empty {
        type string-not-all-spaces {
            length "0..255";
        }
        description "The extra long name of an item.";
    }

    typedef external-named-item {
        type named-item;
        description "Named item used for naming external instances of entities.";
    }

    typedef interface-name {
        type string {
            length "1..32";
        }
        description
            "Named item used for naming interfaces.

             If the interface is configured by the user, it must start
             with a letter.

             If the interface is an internal interface,
             its name starts with '_tmnx_'.";
    }

    typedef time-duration {
        type uint32;
        units "seconds";
        description
            "time-duration specifies a duration of time specified in 'seconds'.
             By use of the units attribute one may specify a different base
             unit.
             By use of the pattern attribute Time-duration may be enhanced to
             specify the following time attributes. Each attribute may not
             exceed the maximum base unit value.

             Allowable date units:
                microseconds, milliseconds, seconds, minutes, hours, days,
                months, years.

             example:
                 units microseconds;

             Allowable date patterns:
                 Y - years         'years        <1..Y>'
                 M - months        'months       <1..M>'
                 D - days          'days         <1..D>'
                 h - hours         'hours        <1..h>'
                 m - minutes       'minutes      <1..m>'
                 s - seconds       'seconds      <1..s>'
                 l - milli-seconds 'milliseconds <1..l>'
                 u - micro-seconds 'microseconds <1..u>'

             example:
                pattern 'Dhms';
                   'days <D> hours <h> minutes <m> seconds <s>'
             ";
    }

    typedef time-duration-64 {
        type uint64;
        units "seconds";
        description
            "time-duration specifies a duration of time specified in 'seconds'.
             By use of the units attribute one may specify a different base
             unit.

             This is a unit64 based version of time-duration type.

             By use of the pattern attribute Time-duration may be enhanced to
             specify the following time attributes. Each attribute may not
             exceed the maximum base unit value.

             Allowable date units:
                microseconds, milliseconds, seconds, minutes, hours, days,
                months, years.

             example:
                 units microseconds;

             Allowable date patterns:
                 Y - years         'years        <1..Y>'
                 M - months        'months       <1..M>'
                 D - days          'days         <1..D>'
                 h - hours         'hours        <1..h>'
                 m - minutes       'minutes      <1..m>'
                 s - seconds       'seconds      <1..s>'
                 l - milli-seconds 'milliseconds <1..l>'
                 u - micro-seconds 'microseconds <1..u>'

             example:
                pattern 'Dhms';
                   'days <D> hours <h> minutes <m> seconds <s>'
             ";
    }

    typedef buffer-size-delay-time {
        type int32 {
            range "0..1000000";
        }
        units "seconds";
        description " Measure delay-time for the buffer size.";
    }

    typedef ip-address {
        type inet:ip-address-no-zone;
        description "An IP address.";
    }

    typedef ipv4-address {
        type inet:ipv4-address-no-zone {
            pattern "[0-9\\.]*" {
                error-message "'ipv4-address' must use only digits and dots (no %zone)";
            }
            pattern "(([0-9]|[1-9][0-9]|1[0-9][0-9]|2[0-4][0-9]|25[0-5])\\.){3}([0-9]|[1-9][0-9]|1[0-9][0-9]|2[0-4][0-9]|25[0-5])" {
                error-message "'ipv4-address' must be a.b.c.d with each octet 0-255 (no zone-id)";
            }
        }
        description "An IPv4 address.";
    }

    typedef ipv6-address {
        type inet:ipv6-address-no-zone;
        description "An IPv6 address.";
    }

    typedef ip-unicast-address {
        type ip-address;
        description "A unicast IP address.";
    }

    typedef ip-unicast-without-local-address {
        type ip-address;
        description "A unicast IP address but not V6 site- or unique-local";
    }

    typedef ipv4-unicast-address {
        type ipv4-address;
        description "A unicast IPv4 address.";
    }

    typedef ipv4-unicast-or-zero-address {
        type ipv4-address;
        description "A unicast IPv4 address.";
    }

    typedef ipv6-unicast-address {
        type ipv6-address;
        description "A unicast IPv6 address.";
    }

    typedef ipv6-unicast-or-zero-address {
        type ipv6-address;
        description "A unicast IPv6 address.";
    }

    typedef ipv6-unicast-without-local-address {
        type ipv6-address;
        description "A unicast IPv6 address but not site- or unique-local";
    }

    typedef ipv6-unicast-or-linklocal-address {
        type ipv6-address;
        description "A global or link-local unicast IPv6 address.";
    }

    typedef ipv6-unicast-or-linklocal-or-zero-address {
        type ipv6-address;
        description "A global or link-local unicast IPv6 address.";
    }

    typedef ip-multicast-address {
        type ip-address;
        description "A multicast IP address.";
    }

    typedef ip-unicast-or-linklocal-without-site-or-unique-local-address {
        type ip-address;
        description "A global or link-local unicast IP address but not V6 site- or unique-local";
    }

    typedef ipv4-multicast-address {
        type ipv4-address {
            pattern "((22[4-9]|23[0-9])\\.)(([0-9]|[1-9][0-9]|1[0-9][0-9]|2[0-4][0-9]|25[0-5])\\.){2}([0-9]|[1-9][0-9]|1[0-9][0-9]|2[0-4][0-9]|25[0-5])(%[\\p{N}\\p{L}]+)?" {
                error-message "'ipv4-multicast-address' must be in 224.0.0.0-239.255.255.255 range with valid dotted-quad form";
            }
        }
        description "A multicast IPv4 address.";
    }

    typedef ipv6-multicast-address {
        type ipv6-address;
        description "A multicast IPv6 address.";
    }

    typedef ip-prefix {
        type inet:ip-prefix;
        description "An IP prefix.";
    }

    typedef ipv4-prefix {
        type inet:ipv4-prefix;
        description "An IPv4 prefix.";
    }

    typedef ipv6-prefix {
        type inet:ipv6-prefix;
        description "An IPv6 prefix.";
    }

    typedef ip-unicast-prefix {
        type ip-prefix;
        description
            "A unicast IP prefix.
             The prefix length is taken into account during unicast check.";
    }

    typedef ipv4-unicast-prefix {
        type ipv4-prefix;
        description
            "A unicast IPv4 prefix.
             The prefix length is taken into account during unicast check.";
    }

    typedef ipv6-unicast-prefix {
        type ipv6-prefix;
        description
            "A unicast IPv6 prefix.
             The prefix length is taken into account during unicast check.";
    }

    typedef ip-multicast-prefix {
        type ip-prefix;
        description "A multicast IP address.";
    }

    typedef ipv4-multicast-prefix {
        type ipv4-prefix;
        description
            "A multicast IP prefix.
             The prefix length is taken into account during multicast check.";
    }

    typedef ipv6-multicast-prefix {
        type ipv6-prefix;
        description
            "A multicast IP prefix.
             The prefix length is taken into account during multicast check.";
    }

    typedef ip-prefix-with-host-bits {
        type union {
            type ipv4-prefix-with-host-bits;
            type ipv6-prefix-with-host-bits;
        }
        description "An IP prefix, possibly with non-zero host bits in the address.";
    }

    typedef ipv4-prefix-with-host-bits {
        type string {
            pattern "(([0-9]|[1-9][0-9]|1[0-9][0-9]|2[0-4][0-9]|25[0-5])\\.){3}([0-9]|[1-9][0-9]|1[0-9][0-9]|2[0-4][0-9]|25[0-5])/(([0-9])|([1-2][0-9])|(3[0-2]))" {
                error-message "'ipv4-prefix-with-host-bits' must be a.b.c.d/prefix with prefix length 0..32";
            }
        }
        description "An IPv4 prefix, possibly with non-zero host bits in the address.";
    }

    typedef ipv6-prefix-with-host-bits {
        type string {
            pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(/(([0-9])|([0-9]{2})|(1[0-1][0-9])|(12[0-8])))" {
                error-message "'ipv6-prefix-with-host-bits' must be IPv6 address/prefix with length 0..128";
            }
            pattern "(([^:]+:){6}(([^:]+:[^:]+)|(.*\\..*)))|((([^:]+:)*[^:]+)?::(([^:]+:)*[^:]+)?)(/.+)" {
                error-message "'ipv6-prefix-with-host-bits' must be IPv6 address/prefix with length 0..128";
            }
        }
        description "An IPv6 prefix, possibly with non-zero host bits in the address.";
    }

    typedef ip-address-and-mask {
        type union {
            type ipv4-address-and-mask;
            type ipv6-address-and-mask;
        }
        description "An IP address and mask.";
    }

    typedef ipv4-address-and-mask {
        type string {
            pattern "(([0-9]|[1-9][0-9]|1[0-9][0-9]|2[0-4][0-9]|25[0-5])\\.){3}([0-9]|[1-9][0-9]|1[0-9][0-9]|2[0-4][0-9]|25[0-5]) (([0-9]|[1-9][0-9]|1[0-9][0-9]|2[0-4][0-9]|25[0-5])\\.){3}([0-9]|[1-9][0-9]|1[0-9][0-9]|2[0-4][0-9]|25[0-5])" {
                error-message "'ipv4-address-and-mask' must be two IPv4 dotted addresses separated by a space";
            }
        }
        description "An IPv4 address and mask.";
    }

    typedef ipv6-address-and-mask {
        type string {
            pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9]))) ((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))" {
                error-message "'ipv6-address-and-mask' must be two IPv6 addresses separated by a space";
            }
            pattern "((([^:]+:){6}(([^:]+:[^:]+)|(.*\\..*)))|((([^:]+:)*[^:]+)?::(([^:]+:)*[^:]+)?)) ((([^:]+:){6}(([^:]+:[^:]+)|(.*\\..*)))|((([^:]+:)*[^:]+)?::(([^:]+:)*[^:]+)?))" {
                error-message "'ipv6-address-and-mask' must be two IPv6 addresses separated by a space";
            }
        }
        description "An IPv6 address and mask.";
    }

    typedef ip-address-with-zone {
        type union {
            type ipv4-address-with-zone;
            type ipv6-address-with-zone;
        }
        description "An IP address which may include a zone identifier.";
    }

    typedef ip-unicast-address-with-zone {
        type inet:ip-address;
        description "An IP unicast address which may include a zone identifier.";
    }

    typedef ipv4-address-with-zone {
        type string {
            pattern "(([0-9]|[1-9][0-9]|1[0-9][0-9]|2[0-4][0-9]|25[0-5])\\.){3}([0-9]|[1-9][0-9]|1[0-9][0-9]|2[0-4][0-9]|25[0-5])(%(([\\p{N}\\p{L}]+)|(\\p{L}.*)|(_tmnx_.*)))?" {
                error-message "'ipv4-address-with-zone' must be a.b.c.d with optional %zone-id";
            }
        }
        description "An IPv4 address which may include a zone identifier.";
    }

    typedef ipv6-address-with-zone {
        type string {
            pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(%(([\\p{N}\\p{L}]+)|(\\p{L}.*)|(_tmnx_.*)))?" {
                error-message "'ipv6-address-with-zone' must be valid IPv6 with optional %zone-id";
            }
            pattern "(([^:]+:){6}(([^:]+:[^:]+)|(.*\\..*)))|((([^:]+:)*[^:]+)?::(([^:]+:)*[^:]+)?)(%.+)?" {
                error-message "'ipv6-address-with-zone' must be valid IPv6 with optional %zone-id";
            }
        }
        description "An IPv6 address which may include a zone identifier.";
    }

    typedef prefix-length {
        type uint32 {
            range "0..128";
        }
        description "Prefix length.";
    }

    typedef display-string {
        type string {
            length "1..255";
        }
        description
            "Represents textual information taken from the NVT ASCII
             character set, as defined in pages 4, 10-11 of RFC 854.

             To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

             Any object defined using this syntax may not exceed 255
             characters in length.";
    }

    typedef display-string-or-empty {
        type string {
            length "0..255";
        }
        description
            "Represents textual information taken from the NVT ASCII
             character set, as defined in pages 4, 10-11 of RFC 854.

             To summarize RFC 854, the NVT ASCII repertoire specifies:

              - the use of character codes 0-127 (decimal)

              - the graphics characters (32-126) are interpreted as
                US ASCII

              - NUL, LF, CR, BEL, BS, HT, VT and FF have the special
                meanings specified in RFC 854

              - the other 25 codes have no standard interpretation

              - the sequence 'CR LF' means newline

              - the sequence 'CR NUL' means carriage-return

              - an 'LF' not preceded by a 'CR' means moving to the
                same column on the next line.

              - the sequence 'CR x' for any x other than LF or NUL is
                illegal.  (Note that this also means that a string may
                end with either 'CR LF' or 'CR NUL', but not with CR.)

             Any object defined using this syntax may not exceed 255
             characters in length and can contains an empty string.";
    }

    typedef fully-qualified-domain-name {
        type string {
            length "1..255";
        }
        description "A Fully Qualified Domain Name as in RFC 1035";
    }

    typedef url {
        type string {
            length "1..180";
        }
        description
            "URL specifies a url in the following format:
             http://path/to/target[:<optional-port>]
             ftp://[<user>:<password>]@<ip-address>/path/to/target";
    }

    typedef http-url {
        type string {
            length "1..255";
        }
        description
            "URL specifies a url in the following format:
             http://[<login>:<pswd>]@[ <hostname> | <ipv4-address> | <ipv6-address> ]:[<port>]";
    }

    typedef bof-cflash-and-url {
        type string {
            length "1..199";
        }
        description
            "URL specifies a url in the following format:
             local-url    - [<cflash-id>/][<file-path>]
             remote-url   - [{ftp://|tftp://}<login>:<pswd>@<remote-locn>/][<file-path>] 180 chars max
             remote-locn  - [ <hostname> | <ipv4-address> | <ipv6-address> ]
             ipv4-address - a.b.c.d
             ipv6-address - x:x:x:x:x:x:x:x[-interface]
                            x:x:x:x:x:x:d.d.d.d[-interface]
                            x - [0..FFFF]H
                            d - [0..255]D
                            interface - 32 chars max, for link
                            local addresses
             cflash-id    - [cf1-4:]|[[cf1-4]-[A-D:]]";
    }

    typedef cflash-and-url {
        type string {
            length "1..180";
        }
        description
            "URL specifies a url in the following format:
             local-url    - [<cflash-id>/][<file-path>]
             remote-url   - [{ftp://|tftp://}<login>:<pswd>@<remote-locn>/][<file-path>] 180 chars max
             remote-locn  - [ <hostname> | <ipv4-address> | <ipv6-address> ]
             ipv4-address - a.b.c.d
             ipv6-address - x:x:x:x:x:x:x:x[-interface]
                            x:x:x:x:x:x:d.d.d.d[-interface]
                            x - [0..FFFF]H
                            d - [0..255]D
                            interface - 32 chars max, for link
                            local addresses
             cflash-id    - [cf1-4:]|[[cf1-4]-[A-D:]]";
    }

    typedef ts-url {
        type cflash-and-url;
    }

    typedef ts-url-or-sftp-512 {
        type string {
            length "1..512";
        }
        description
            "URL specifies a url in the following format:
             local-url    - [<cflash-id>/][<file-path>]
             remote-url   - [{ftp://|tftp://}<login>:<pswd>@<remote-locn>/][<file-path>] 180 chars max
             remote-locn  - [ <hostname> | <ipv4-address> | <ipv6-address> ]
             ipv4-address - a.b.c.d
             ipv6-address - x:x:x:x:x:x:x:x[-interface]
                            x:x:x:x:x:x:d.d.d.d[-interface]
                            x - [0..FFFF]H
                            d - [0..255]D
                            interface - 32 chars max, for link
                            local addresses
             cflash-id    - [cf1-4:]|[[cf1-4]-[A-D:]]
             sftp         - sftp://[<login>:<pswd>@<remote-locn>/][<file-path>] 512 chars max";
    }

    typedef ts-url-string {
        type union {
            type ts-sat-url;
            type cflash-url {
                length "1..180";
            }
            type string {
                length "1..180";
                pattern "(.*\\S.*)|()" {
                    error-message "'ts-url-string' must contain at least one non-space character";
                }
            }
        }
        description
            "URL specifies a url in the following format:
             local-url    - [<cflash-id>/][<file-path>]
             remote-url   - [{ftp://|tftp://}<login>:<pswd>@<remote-locn>/][<file-path>] 180 chars max
             remote-locn  - [ <hostname> | <ipv4-address> | <ipv6-address> ]
             ipv4-address - a.b.c.d
             ipv6-address - x:x:x:x:x:x:x:x[-interface]
                            x:x:x:x:x:x:d.d.d.d[-interface]
                            x - [0..FFFF]H
                            d - [0..255]D
                            interface - 32 chars max, for link
                            local addresses
             cflash-id    - [cf1-4:]|[[cf1-4]-[A-D:]]";
    }

    typedef file-url-consistent-backslashes {
        type string {
            length "1..200";
        }
        description "A string that will have all its slashes changed to backslashes";
    }

    typedef file-url-consistent-forward-slashes {
        type string {
            length "1..200";
        }
        description "A string that will have all its backslashes changed to forward slashes";
    }

    typedef path-to-file-absolute {
        type string {
            length "1..200";
            pattern "(\\\\|/).*" {
                error-message "'path-to-file-absolute' must start with / or \\ (absolute path)";
            }
        }
        description "A string representing an absolute path to a file.";
    }

    typedef filename {
        type string {
            length "1..180";
            pattern "[^\\\\/]+" {
                error-message "'filename' must not contain / or \\\\ (no path separators)";
            }
            pattern "(.*\\S.*)|()" {
                error-message "'filename' must not be all spaces";
            }
        }
        description "A string representing the name of a file.";
    }

    typedef filename-255 {
        type string {
            length "1..255";
            pattern "[^\\\\/]+" {
                error-message "'filename-255' must not contain / or \\\\ (no path separators)";
            }
            pattern "(.*\\S.*)|()" {
                error-message "'filename-255' must not be all spaces";
            }
        }
        description "A string representing the name of a file.";
    }

    typedef sat-url {
        type string {
            length "1..200";
            pattern "sat:.*" {
                error-message "'sat-url' must start with sat: (e.g. sat:path/to/file)";
            }
        }
        description "A string representing a sat URL.";
    }

    typedef thresholds-cflash-url {
        type string {
            length "1..200";
            pattern "cf[1-4]-[A-Da-d]:" {
                error-message "'thresholds-cflash-url' must be cf1-4 with slot A-D (e.g. cf1-A:)";
            }
        }
        description "Compact flash drive on the CPM for rmon thresholds.";
    }

    typedef cflash-url {
        type string {
            length "1..200";
            pattern "cf[1-4](-[A-Da-d])?:.*" {
                error-message "'cflash-url' must start with cf1-4, optional slot A-D, then path (e.g. cf1:/path or cf1-A:/path)";
            }
            pattern ".*:([\\\\]?[a-zA-Z0-9._\\-\\s]{1,99})(\\\\[a-zA-Z0-9._\\-\\s]{1,99})*" {
                error-message "'cflash-url' must have each path segment at most 99 characters";
            }
        }
        description "A string representing a cflash URL.";
    }

    typedef cflash-id {
        type string {
            length "4..6";
            pattern "cf[1-4](-[A-Da-d])?:" {
                error-message "'cflash-id' must be cf1-4: or cf1-4-A-D: (e.g. cf1: or cf2-B:)";
            }
        }
        description "A string representing a cflash ID.";
    }

    typedef cflash-without-slot-url {
        type string {
            length "1..200";
            pattern "cf[1-4]:.*" {
                error-message "'cflash-without-slot-url' must be cf1-4: followed by path (e.g. cf1:/path)";
            }
        }
        description "A string representing a cflash URL.";
    }

    typedef ts-sat-url {
        type string {
            length "1..180";
            pattern "sat:.*" {
                error-message "'ts-sat-url' must start with sat: (e.g. sat:path/to/file)";
            }
        }
        description "A string representing a sat URL.";
    }

    typedef ftp-tftp-url {
        type string {
            length "1..199";
            pattern "(ftp|tftp):(\\\\|/){2}.*(\\\\|/).*" {
                error-message "'ftp-tftp-url' must be ftp:// or tftp:// with host and path (e.g. ftp://user:pass@hostname.domain/path/file)";
            }
            pattern "(ftp|tftp):(\\\\|/){2}([^:@?/]*:[^:@?/]*@)?((\\w|(\\w(\\w|\\.\\w|-\\w|[%]\\w)*))\\.\\w(\\w|-\\w|[%]\\w)*)((\\\\|/)[^;?]*)?" {
                error-message "'ftp-tftp-url' must have valid hostname and optional path after scheme";
            }
        }
        description "A string representing an FTP/TFTP URL.";
    }

    typedef ftp-url {
        type string {
            length "1..180";
            pattern "[^ <>{}|^\"`]*" {
                error-message "'ftp-url' must not contain illegal characters";
            }
            pattern "(ftp):(\\\\|/){2}([^:@?/]*:[^:@?/]*@)?((\\w|(\\w(\\w|\\.\\w|-\\w|[%]\\w)*))\\.\\w(\\w|-\\w|[%]\\w)*)((\\\\|/)[^;?]*)?" {
                error-message "'ftp-url' must be ftp:// with optional user:pass@, hostname and path (e.g. ftp://user:pass@hostname.domain/path/file)";
            }
        }
        description "A string representing an FTP URL.";
    }

    typedef scp-url {
        type string {
            length "1..180";
            pattern "[^ <>{}|^\"`]*" {
                error-message "'scp-url' must not contain < > { } | ^ or space or quote or backtick";
            }
            pattern "(scp):(\\\\|/){2}([^:@?/]*:[^:@?/]*@)?((\\w|(\\w(\\w|\\.\\w|-\\w|[%]\\w)*))\\.\\w(\\w|-\\w|[%]\\w)*)((\\\\|/)[^;?]*)?" {
                error-message "'scp-url' must be scp:// with optional user:pass@, hostname and path (e.g. scp://user:pass@hostname.domain/path/file)";
            }
        }
        description "A string representing an SCP URL.";
    }

    typedef sftp-url {
        type string {
            length "1..512";
            pattern "[^ <>{}|^\"`]*" {
                error-message "'sftp-url' must not contain illegal characters";
            }
            pattern "(sftp):(\\\\|/){2}([^:@?/]*:[^:@?/]*@)?((\\d{1,3}\\.){3}\\d{1,3}|(\\[[^\\]]+\\])|(\\w[\\w%-]*)(\\.(\\w[\\w%-]*))*)((\\\\|/)[^;?]*)?" {
                error-message "'sftp-url' must be sftp:// with optional user:pass@, hostname and path (e.g. sftp://user:pass@hostname.domain/path/file)";
            }
        }
        description "A string representing an SFTP URL.";
    }

    typedef http-url-loose {
        type string {
            length "1..180";
            pattern "[hH][tT][tT][pP]:[\\\\/]{2}([^@]*@)?((\\[[^\\]]+\\])|([^\\\\/:])+)(:([0-9]{1,4}|[0-5][0-9]{4}|6[0-4][0-9]{3}|65[0-4][0-9]{2}|655[0-2][0-9]|6553[0-5]))?([\\\\/].*)?" {
                error-message "'http-url-loose' must be http:// with host and optional port and path (e.g. http://hostname.domain/path)";
            }
        }
        description
            "A string representing an HTTP URL that is loosely
             defined for backward compatibility.";
    }

    typedef http-or-https-url-loose {
        type string {
            length "1..180";
            pattern "[hH][tT][tT][pP][sS]?:[\\\\/]{2}([^@]*@)?((\\[[^\\]]+\\])|([^\\\\/:])+)(:([0-9]{1,4}|[0-5][0-9]{4}|6[0-4][0-9]{3}|65[0-4][0-9]{2}|655[0-2][0-9]|6553[0-5]))?([\\\\/].*)?" {
                error-message "'http-or-https-url-loose' must be http:// or https:// with host and optional port and path (e.g. https://hostname.domain/path)";
            }
        }
        description "A string representing an HTTP(S) URL that is loosely defined.";
    }

    typedef http-url-path-loose {
        type http-url-loose {
            pattern "\\w[\\w+-.]*:[\\\\/]{2}[^\\\\/]+[\\\\/].*" {
                error-message "'http-url-path-loose' must include path after host (e.g. http://host/path)";
            }
        }
        description
            "A string representing an HTTP URL that is loosely
             defined for backward compatibility, but the path
             component is mandatory.";
    }

    typedef http-optional-url-loose {
        type string {
            length "1..180";
            pattern "([hH][tT][tT][pP]:[\\\\/]{2})?([^@]*@)?((\\[[^\\]]+\\])|([^\\\\/:])+)(:([0-9]{1,4}|[0-5][0-9]{4}|6[0-4][0-9]{3}|65[0-4][0-9]{2}|655[0-2][0-9]|6553[0-5]))?([\\\\/].*)?" {
                error-message "'http-optional-url-loose' must be http:// or host-only, with optional port and path (e.g. http://hostname.domain/path)";
            }
        }
        description
            "A string representing an HTTP URL that is loosely
             defined for backward compatibility and the HTTP scheme
             is implied if not specified.";
    }

    typedef local-file-url {
        type union {
            type sat-url;
            type cflash-url;
            type string-not-all-spaces {
                length "1..200";
            }
        }
        description "A string representing a local URL - cflash or sat.";
    }

    typedef remote-file-url {
        type union {
            type ftp-tftp-url;
            type http-url-loose;
        }
        description "A string representing a remote URL - FTP, TFTP or HTTP.";
    }

    typedef http-redirect-url {
        type string-not-all-spaces {
            length "1..255";
        }
        description
            "A string that represents an HTTP URL
             configured for HTTP redirection.

             The string may contain a macro '$URL' that specifies
             substitution of '$URL' by another string; the origin
             of that string is documented where this textual
             convention is used.

             The string may contain a macro '$MAC' that specifies
             substitution of '$MAC' by another string, representing
             a MAC address; the origin of that string is documented
             where this textual convention is used.

             The string may contain a macro '$IP' that specifies
             substitution of '$IP' by another string, representing
             an IP address; the origin of that string is documented
             where this textual convention is used.

             The string may contain a macro '$SUB' that specifies
             substitution of '$SUB' by another string, representing
             an subscriber ID; the origin of that string is documented
             where this textual convention is used.

             The string may contain a macro '$SAP' that specifies
             substitution of '$SAP' by another string, representing
             a SAP (Service Access Point); the origin of that string is documented
             where this textual convention is used.

             The string may contain a macro '$SAPDESC' that specifies
             substitution of '$SAPDESC' by another string; the origin
             of that string is documented where this textual
             convention is used.

             The string may contain a macro '$CID' that specifies
             substitution of '$CID' by a bytestring, representing
             a circuit-id or interface-id; the origin of that string is documented
             where this textual convention is used.

             The string may contain a macro '$RID' that specifies
             substitution of '$RID' by a bytestring, representing
             a remote-id; the origin of that string is documented
             where this textual convention is used.

             Not all substitition macro's are supported in every situation;
             an unsupported macro is ignored (substitued with nothing);
             the set of supported macro's should be documented where this
             textual convention is used.";
    }

    typedef vrtr-id-or-zero {
        type int32 {
            range "0..10240";
        }
        description
            "A number used to identify a virtual router instance in the system.
             The number 0 will have special significance in the context the typedef
             is used.";
    }

    typedef vrtr-id {
        type vrtr-id-or-zero {
            range "1..10240";
        }
        description "A number used to identify a virtual router instance in the system.";
    }

    typedef router-instance {
        type string {
            length "1..64";
        }
        default "Base";
        description "Specifies a router instance such as 'Base', 'management' or a VPRN service name";
    }

    typedef router-instance-base-management-loose {
        type string {
            length "1..32";
        }
        description
            "A virtual router instance as a string. Any router name
             (e.g. 'Base', 'management') can be specified.";
    }

    typedef router-instance-base-management-vprn-loose {
        type string {
            length "1..64";
        }
        description
            "A virtual router instance. Any router name (e.g. 'Base', 'management') or
             service name (e.g. VPRN service name) can be specified.";
    }

    typedef router-instance-base-vprn-loose {
        type string {
            length "1..64";
        }
        description
            "A virtual router instance. Any router name (e.g. 'Base') or service
             name (e.g. VPRN service name) can be specified.";
    }

    typedef oper-state {
        type enumeration {
            enum unknown                        { value 1; }
            enum up                             { value 2; }
            enum down                           { value 3; }
            enum transition                     { value 4; }
        }
        description
            "Oper-state specifies the general operational state for the
             average SR OS entity that supports operational states.";
    }

    typedef lag-interface {
        type string {
            length "1..27";
            pattern "lag-.+" {
                error-message "'lag-interface' must be lag- followed by number 1-800 or up to 23 chars (e.g. lag-1 or lag-my-lag)";
            }
        }
        description "The unique name identifying a LAG interface.";
    }

    typedef port {
        type string;
        description "A physical or logical port.";
    }

    typedef port-named {
        type string;
        description "A physical or logical port.";
    }

    typedef regular-expression-not-all-spaces {
        type string {
            length "1..255";
            pattern "(.*\\S.*)" {
                error-message "'regular-expression-not-all-spaces' must contain at least one non-space character";
            }
        }
        description "A regular expression string.";
    }

    typedef mcs-encap {
        type string {
            length "1..11";
        }
        description "An encap formatted string";
    }

    typedef port-and-encap {
        type string {
            length "1..45";
        }
        description "A port and encap formatted string used for sap and router-port.";
    }

    typedef qtag {
        type uint32 {
            range "1..4094";
        }
        description
            "A 12-bit integer tag used to identify a service. The values 0 and
             4095 are not allowed.";
    }

    typedef qtag-full-range {
        type int32 {
            range "0..4095";
        }
        description
            "A 12-bit integer tag used to identify a service. The whole range of
             possible values is allowed.";
    }

    typedef vlan-id {
        type int32 {
            range "1..4094";
        }
        description "VLAN Id";
    }

    typedef vlan-encap {
        type string {
            length "1..11";
            pattern "(([0-9]|[1-9][0-9]{1,2}|[1-3][0-9]{3}|40[0-8][0-9]|409[0-4]))|(([1-9]|[1-9][0-9]{1,2}|[1-3][0-9]{3}|40[0-8][0-9]|409[0-4]))\\.((([0-9]|[1-9][0-9]{1,2}|[1-3][0-9]{3}|40[0-8][0-9]|409[0-4]))|\\*)" {
                error-message "'vlan-encap' must be Q-tag or dot1q form (0-4094 or 1-4094.0-4094 or *)";
            }
        }
        description "An encap formatted string.";
    }

    typedef eth-tunnel-path-tag {
        type string {
            length "1..9";
            pattern "(([0-9]|[1-9][0-9]{1,2}|[1-3][0-9]{3}|40[0-8][0-9]|409[0-4])|\\*)|((([0-9]|[1-9][0-9]{1,2}|[1-3][0-9]{3}|40[0-8][0-9]|409[0-4]))|\\*)\\.((([0-9]|[1-9][0-9]{1,2}|[1-3][0-9]{3}|40[0-8][0-9]|409[0-4]))|\\*)" {
                error-message "'eth-tunnel-path-tag' must match Q-tag or dot1q encap rules for tunnel path";
            }
        }
        description "Ethernet tunnel path tag formatted string.";
    }

    typedef ext-vlan-encap {
        type string {
            length "1..11";
            pattern "((([0-9]|[1-9][0-9]{1,2}|[1-3][0-9]{3}|40[0-8][0-9]|409[0-4]))|\\*)|(([1-9]|[1-9][0-9]{1,2}|[1-3][0-9]{3}|40[0-8][0-9]|409[0-4]))\\.((([0-9]|[1-9][0-9]{1,2}|[1-3][0-9]{3}|40[0-8][0-9]|409[0-4]))|\\*)|0\\.\\*" {
                error-message "'ext-vlan-encap' must match extended VLAN encap or 0.*";
            }
        }
        description "An encap formatted string.";
    }

    typedef atm-or-vlan-encap {
        type string {
            length "1..11";
            pattern "((([0-9]|[1-9][0-9]{1,2}|[1-3][0-9]{3}|40[0-8][0-9]|409[0-5]))|\\*)/(((1|2|[5-9]|[1-9][0-9]{1,3}|[1-5][0-9]{4}|6[0-4][0-9]{3}|65[0-4][0-9]{2}|655[0-2][0-9]|6553[0-5]))|\\*)|(([0-9]|[1-9][0-9]{1,2}|[1-3][0-9]{3}|40[0-8][0-9]|409[0-4]))|((([0-9]|[1-9][0-9]{1,2}|[1-3][0-9]{3}|40[0-8][0-9]|409[0-4]))|\\*)\\.((([0-9]|[1-9][0-9]{1,2}|[1-3][0-9]{3}|40[0-8][0-9]|409[0-4]))|\\*)" {
                error-message "'atm-or-vlan-encap' must be ATM VPI/VCI or VLAN encap format";
            }
        }
        description "An encap formatted string.";
    }

    typedef single-vlan-encap {
        type string {
            length "1..11";
            pattern "((([0-9]|[1-9][0-9]{1,2}|[1-3][0-9]{3}|40[0-8][0-9]|409[0-4]))|\\*)" {
                error-message "'single-vlan-encap' must be Q-tag or *";
            }
        }
        description "An encap formatted string.";
    }

    typedef double-vlan-encap {
        type string {
            length "1..11";
            pattern "((([1-9]|[1-9][0-9]{1,2}|[1-3][0-9]{3}|40[0-8][0-9]|409[0-4]))|\\*)\\.((([0-9]|[1-9][0-9]{1,2}|[1-3][0-9]{3}|40[0-8][0-9]|409[0-4]))|\\*)" {
                error-message "'double-vlan-encap' must be inner.outer Q-tag or * form";
            }
        }
        description "An encap formatted string.";
    }

    typedef one-or-two-vlan-tags {
        type string {
            length "1..9";
            pattern "(([0-9]|[1-9][0-9]{1,2}|[1-3][0-9]{3}|40[0-8][0-9]|409[0-4]))|((([0-9]|[1-9][0-9]{1,2}|[1-3][0-9]{3}|40[0-8][0-9]|409[0-4]))\\.(([0-9]|[1-9][0-9]{1,2}|[1-3][0-9]{3}|40[0-8][0-9]|409[0-4])))" {
                error-message "'one-or-two-vlan-tags' must be one Q-tag or inner.outer pair";
            }
        }
        description "An encap formatted string.";
    }

    typedef sap {
        type port-and-encap;
        description "A service-access-point. Absence of the leaf means no sap is specified";
    }

    typedef ip-prefix-mask {
        type int32 {
            range "0..128";
        }
    }

    typedef time-interval {
        type int32 {
            range "0..2147483647";
        }
        description "A period of time, measured in units of centiseconds.";
    }

    typedef svc-isid {
        type int32 {
            range "0..16777215";
        }
        description
            "The svc-isid specifies a 24 bit (0..16777215) service instance
             identifier for the service. As part of the Provider Backbone Bridging
             frames, it is used at the destination PE as a demultiplexor field.";
    }

    typedef svc-isid-non-zero {
        type int32 {
            range "1..16777215";
        }
        description
            "The svc-isid specifies a 24 bit (1..16777215) service instance
             identifier for the service. As part of the Provider Backbone Bridging
             frames, it is used at the destination PE as a demultiplexor field.";
    }

    typedef encap-val {
        type uint32;
        description
            "The value of the label used to identify the entity using the
             specified encapsulation value on a specific port.

             The format of this object depends on the encapsulation type
             defined on this port.

             When the encapsulation is nullEncap the value of this object
             must be zero.

             31                                   0
             +--------+--------+--------+--------+
             |00000000 00000000 00000000 00000000|
             +--------+--------+--------+--------+

             When the encapsulation is dot1qEncap the value of this object
             is equal to the 12-bit IEEE 802.1Q VLAN ID.

             31                                   0
             +--------+--------+--------+--------+
             |00000000 00000000 0000XXXX XXXXXXXX|
             +--------+--------+--------+--------+

             When the encapsulation is mplsEncap the value of this object
             is equal to the 20-bit LSP ID.

             31                                   0
             +--------+--------+--------+--------+
             |00000000 0000XXXX XXXXXXXX XXXXXXXX|
             +--------+--------+--------+--------+

             When the encapsulation is frEncap, the value of this object is
             equal to the 10-bit Frame Relay DLCI.

             31                                   0
             +--------+--------+--------+--------+
             |00000000 00000000 000000XX XXXXXXXX|
             +--------+--------+--------+--------+

             When the encapsulation is qinqEncap, the value of the outer
             802.1Q VLAN ID is encoded in the least significant 16 bits,
             and the value of the inner VLAN ID is encoded in the most
             significant 16 bits.

             31                                   0
             +--------+--------+--------+--------+
             |0000YYYY YYYYYYYY 0000XXXX XXXXXXXX|
             +--------+--------+--------+--------+

             where:
                - '*' is represented as 4095.
                - '0' is represented as 0.
                - any other value in between as a valid tag.
                - '*.null' is represented in the following way:

                  31                                  0
                  +--------+--------+--------+--------+
                  |10000000 00000000 00001111 11111111|
                  +--------+--------+--------+--------+

             When the encapsulation is atmEncap, the value
             of the ATM VCI is encoded in the least significant
             16 bits, and the value of the ATM VPI is encoded
             in the next 12 bits.

             For ATM VCs, the top 3 bits are 000.  The value of
             the ATM VCI is encoded in the least significant 16
             bits, and the value of the ATM VPI is encoded in the next
             12 bits.

             31                                   0
             +--------+--------+--------+--------+
             |0000YYYY YYYYYYYY XXXXXXXX XXXXXXXX|
             +--------+--------+--------+--------+

             For ATM capture VCs, bits 0 and 28 are 1.

             31                                   0
             +--------+--------+--------+--------+
             |00010000 00000000 00000000 00000001|
             +--------+--------+--------+--------+

             For ATM VPs, the top 3 bits are 010.  The value of
             the ATM VPI is encoded in the least significant 12 bits.

             31                                   0
             +--------+--------+--------+--------+
             |01000000 00000000 0000XXXX XXXXXXXX|
             +--------+--------+--------+--------+

             For ATM VP ranges, the top 3 bits are 100.  The value of
             the start of the ATM VPI range is encoded in the least significant
             12 bits, and the value of the end of the ATM VP range is encoded
             in the next 12 bits.

             31                                   0
             +--------+--------+--------+--------+
             |10000000 YYYYYYYY YYYYXXXX XXXXXXXX|
             +--------+--------+--------+--------+

             For ATM ports, the top 3 bits are 110, and the rest of the bits
             must be zero.

             31                                   0
             +--------+--------+--------+--------+
             |11000000 00000000 00000000 00000000|
             +--------+--------+--------+--------+

             For ATM CPs, the top 3 bits are 001.  The value of
             the ATM CP is encoded in the least significant 13 bits.

             31                                   0
             +--------+--------+--------+--------+
             |00100000 00000000 000XXXXX XXXXXXXX|
             +--------+--------+--------+--------+

             When the encapsulation is wanMirrorEncap the value of this
             object is equal to the 12-bit value.

             31                                   0
             +--------+--------+--------+--------+
             |00000000 00000000 0000XXXX XXXXXXXX|
             +--------+--------+--------+--------+

             Some ports have a restrictions to the encapsulation types that
             they can support and hence impose restrictions on the respective
             formats defined above.";
    }

    typedef sdp-id {
        type uint32 {
            range "0..32767";
        }
        description
            "A 16-bit number used to identify a Service Destination Point.
             This ID must be unique only within the ESR where it is defined.
             The value 0 is used as the null ID.";
    }

    typedef vc-id-or-none {
        type uint32;
        description
            "A 32 bit number is used to identify a VC(Virtual Circuit).
             A value of 0 indicates no VC ID is configured or available.";
    }

    typedef reference-bandwidth {
        type uint64 {
            range "1..4000000000";
        }
        description
            "A number that specifies the reference bandwidth used for cost calculation.

             The formula is:  Cost = reference-bandwidth / bandwidth.

             The unit is 1000 bps.";
    }

    typedef reference-bandwidth-ext {
        type uint64 {
            range "1..max";
        }
        description
            "A number that specifies the reference bandwidth used for cost calculation.

             The formula is:  Cost = reference-bandwidth / bandwidth.

             The unit is 1000 bps.";
    }

    typedef ip-option {
        type int32 {
            range "0..255";
        }
        description
            "IP packet options octet.  explanation of the octet bits:

             IP OPTION NUMBERS

             The Internet Protocol (IP) has provision for optional header fields
             identified by an option type field.  Options 0 and 1 are exactly one
             octet which is their type field.  All other options have their one
             octet type field, followed by a one octet length field, followed by
             length-2 octets of option data.  The option type field is sub-divided
             into a one bit copied flag, a two bit class field, and a five bit
             option number.  These taken together form an eight bit value for the
             option type field.  IP options are commonly referred to by this value.


             Copy Class Number Value Name                Reference
             ---- ----- ------ ----- ------------------------------- ---------
                0     0      0     0 EOOL   - End of Options List    [RFC791,JBP]
                0     0      1     1 NOP    - No Operation           [RFC791,JBP]
                1     0      2   130 SEC    - Security                  [RFC1108]
                1     0      3   131 LSR    - Loose Source Route     [RFC791,JBP]
                0     2      4    68 TS     - Time Stamp             [RFC791,JBP]
                1     0      5   133 E-SEC  - Extended Security         [RFC1108]
                1     0      6   134 CIPSO  - Commercial Security           [???]
                0     0      7     7 RR     - Record Route           [RFC791,JBP]
                1     0      8   136 SID    - Stream ID              [RFC791,JBP]
                1     0      9   137 SSR    - Strict Source Route    [RFC791,JBP]
                0     0     10    10 ZSU    - Experimental Measurement      [ZSu]
                0     0     11    11 MTUP   - MTU Probe                 [RFC1191]*
                0     0     12    12 MTUR   - MTU Reply                 [RFC1191]*
                1     2     13   205 FINN   - Experimental Flow Control    [Finn]
                1     0     14   142 VISA   - Experimental Access Control [Estrin]
                0     0     15    15 ENCODE - ???                      [VerSteeg]
                1     0     16   144 IMITD  - IMI Traffic Descriptor        [Lee]
                1     0     17   145 EIP    - Extended Internet Protocol[RFC1385]
                0     2     18    82 TR     - Traceroute        [RFC1393]
                1     0     19   147 ADDEXT - Address Extension    [Ullmann IPv7]
                1     0     20   148 RTRALT - Router Alert              [RFC2113]
                1     0     21   149 SDB    - Selective Directed Broadcast[Graff]
                1     0     22   150 NSAPA  - NSAP Addresses          [Carpenter]
                1     0     23   151 DPS    - Dynamic Packet State        [Malis]
                1     0     24   152 UMP    - Upstream Multicast Pkt. [Farinacci]

             [Note, an asterisk (*) denotes an obsoleted IP Option Number.]
                ";
    }

    typedef class-index {
        type uint32 {
            range "1..255";
        }
        description "Source/Destination class index.";
    }

    typedef protocol-status {
        type enumeration {
            enum create                         { value 1; }
            enum delete                         { value 2; }
        }
        description
            "This typedef is an enumerated integer that describes the values used
             to identify the current status of functional modules in the system such
             as OSPF and MPLS protocols. Setting this variable to 'create' causes
             instantiation of the feature in the system.  Setting it to 'delete'
             removes the instance and all associated configuration information.";
    }

    typedef address-state {
        type enumeration {
            enum unknown                        { value 0; }
            enum tentative                      { value 1; }
            enum duplicated                     { value 2; }
            enum inaccessible                   { value 3; }
            enum deprecated                     { value 4; }
            enum preferred                      { value 5; }
        }
        description "The state of an IP/IPv6 address.";
    }

    typedef tcp-udp-port {
        type int32 {
            range "0|1..65535";
        }
        description
            "The number of a TCP or UDP port.
             Well known port numbers include
             ftp-data(20), ftp(21), telnet(23), smtp(25), http(80),
             pop3(110), nntp(119), snmp(161), snmptrap(162), etc.";
    }

    typedef tcp-udp-port-non-zero {
        type tcp-udp-port {
            range "1..65535";
        }
        description
            "The number of a TCP or UDP port.
             Well known port numbers include
             ftp-data(20), ftp(21), telnet(23), smtp(25), http(80),
             pop3(110), nntp(119), snmp(161), snmptrap(162), etc.";
    }

    typedef creation-origin {
        type enumeration {
            enum unknown                        { value 0; }
            enum manual                         { value 1; }
            enum bgp-l2vpn                      { value 2; }
            enum radius                         { value 3; }
            enum bgp-signal-l2-vpn              { value 4; }
            enum multi-segment-pw               { value 5; }
            enum vpls-pmsi                      { value 6; }
            enum dyn-script                     { value 7; }
            enum bof                            { value 8; }
            enum bgp-signal-vpws                { value 9; }
            enum vsd                            { value 12; }
            enum evpn                           { value 13; }
            enum vsd-sd                         { value 14; }
            enum satellites                     { value 15; }
            enum fpe                            { value 16; }
            enum evpn-isa                       { value 17; }
            enum gre-bridged                    { value 18; }
            enum tli                            { value 19; }
            enum pdn                            { value 20; }
            enum vmhost                         { value 21; }
            enum dhcp-client                    { value 22; }
            enum ipsec                          { value 23; }
            enum esa                            { value 24; }
            enum pfcp-cups                      { value 25; }
            enum manual-mci                     { value 26; }
        }
        description "Indicates the entity that created the entry.";
    }

    typedef percent {
        type uint32 {
            range "0..100";
        }
        units "percent";
        description "Integer number used to specify the percentage value.";
    }

    typedef up-down-status {
        type enumeration {
            enum up                             { value 1; }
            enum down                           { value 2; }
        }
        description "Indicates operational status.";
    }

    typedef bool-with-inherit {
        type enumeration {
            enum false                          { value 0; }
            enum true                           { value 1; }
        }
        description "The entity could also be inherited along with the boolean values.";
    }

    typedef priority {
        type enumeration {
            enum low                            { value 1; }
            enum high                           { value 2; }
        }
        description
            "The priority to apply to a packet.
             When set to undefined(0), the priority is not applicable.";
    }

    typedef adjacency-set-family-type {
        type enumeration {
            enum ipv4                           { value 0; }
            enum ipv6                           { value 1; }
        }
        description "Specifies type of adjacency set family";
    }

    typedef resolution-type {
        type enumeration {
            enum none                           { value 0; }
            enum filter                         { value 1; }
            enum any                            { value 2; }
            enum match-family-ip                { value 3; }
        }
        default "none";
        description "Specify resolution state for IGP shortcut tunnels.";
    }

    typedef fc-name {
        type enumeration {
            enum be {
                value 0;
                description "Best Effort";
            }
            enum l2 {
                value 1;
                description "Low 2 (best effort)";
            }
            enum af {
                value 2;
                description "Assured Forwarding (assured)";
            }
            enum l1 {
                value 3;
                description "Low 1 (assured)";
            }
            enum h2 {
                value 4;
                description "High 2 (high priority)";
            }
            enum ef {
                value 5;
                description "Expedited Forwarding (high priority)";
            }
            enum h1 {
                value 6;
                description "High 1 (high priority)";
            }
            enum nc {
                value 7;
                description "Network Control (high priority)";
            }
        }
        description "Specifies different Forwarding Classes (FC).";
    }

    typedef community {
        type string {
            length "1..72";
        }
        description "Specifies different community patterns used by routing policies";
    }

    typedef member-community {
        type string {
            length "1..72";
        }
        description "Specifies different community patterns used by routing policies";
    }

    typedef expression-community {
        type string {
            length "1..900";
        }
        description "Specifies different community expressions used by routing policies";
    }

    typedef policy-as-path-regexp {
        type string {
            length "1..255";
        }
        description "Specifies AS Path regular expression used by policies";
    }

    typedef policy-community-name {
        type string {
            length "1..64";
            pattern "(.*\\S.*)|()" {
                error-message "'policy-community-name' must not be all spaces";
            }
        }
        description "Specifies community name.";
    }

    typedef cga-modifier {
        type string {
            length "34";
        }
        default "0x00000000000000000000000000000000";
    }

    typedef include-exclude-type {
        type enumeration {
            enum include                        { value 1; }
            enum exclude                        { value 2; }
        }
        description "Specifies whether the specified functionality will be included or excluded.";
    }

    typedef mac-address {
        type ieee-address;
        description "A MAC address.";
    }

    typedef mac-unicast-address {
        type ieee-address;
        description "A unicast MAC address.";
    }

    typedef mac-unicast-address-no-zero {
        type ieee-address;
        description "A unicast MAC address.";
    }

    typedef mac-multicast-address {
        type ieee-address;
        description "A multicast MAC address.";
    }

    typedef ascii-specification {
        type string {
            length "1..255";
        }
        description
            "The type ascii-specification is a format string
             that specifies how to form a target ASCII string.

             The format is as follows:
             <ascii-specification> ::= <char-specification>+
             <char-specification>  ::= <ascii-char> | <char-origin>
             <char-origin>         ::= '%' <origin>
             <ascii-char> refers to a printable ASCII character.

             Examples and supported char-origin specifiers are supplied with the
             object definitions.";
    }

    typedef binary-specification {
        type string {
            length "1..255";
        }
        description
            "The type binary-specification is a format string
             that specifies how to form a target ASCII string.

             The format is as follows:
             <binary-specification> ::= <bit-specification>+
             <bit-specification>    ::= '0' | '1' | <bit-origin>
             <bit-origin>           ::= '*' <number-of-bits> <origin>
             <number-of-bits>       ::= [1..32]

             Examples and supported bit-origin specifiers are supplied with the
             object definitions.";
    }

    typedef tunnel-id {
        type uint32;
        description
            "Indicates the value for a tunnel.

             Depending on the tunnel type the associated tunnel-id may be an sdp-id,
             an lsp-id or zero(0).";
    }

    typedef cbf-classes {
        type bits {
            bit be                             { position 0; }
            bit l2                             { position 1; }
            bit af                             { position 2; }
            bit l1                             { position 3; }
            bit h2                             { position 4; }
            bit ef                             { position 5; }
            bit h1                             { position 6; }
            bit nc                             { position 7; }
            bit default-lsp                    { position 8; }
        }
        description "Indicates a set of forwarding classes.";
    }

    typedef pw-port {
        type uint32 {
            range "1..32767";
        }
        description "Indicates range for the pseudo-wire identifiers.";
    }

    typedef mpls-label-or-zero {
        type uint32 {
            range "32..1048575";
        }
        description
            "Indicates range for MPLS label. The value 0 indicates that no
             MPLS label is specified.";
    }

    typedef mpls-label {
        type uint32 {
            range "32..1048575";
        }
        description "Indicates range for MPLS label.";
    }

    typedef mpls-label-full-range {
        type uint32 {
            range "0..1048575";
        }
        description "Indicates the full range for a MPLS label.";
    }

    typedef prefix-sid-full-range {
        type uint32 {
            range "0..1048575";
        }
        description
            "Indicates the full range of possible values for a Prefix SID
             index or label.

             The maximum supported range can be [0..524287] or [0..1048575]
             depending on the platform.

             The available Prefix SID range is restricted by the configured
             MPLS SR label range.";
    }

    typedef isa-scaling-profile {
        type enumeration {
            enum profile1                       { value 1; }
            enum profile2                       { value 2; }
            enum profile3                       { value 3; }
        }
        description
            "The identifier of one of the pre-defined
             ISA (Integrated Service Adaptor) scaling profiles.

             The meaning of each profile is explained in the customer documentation.
             ISA scaling profiles are only used in a virtual machine implementation.";
    }

    typedef match-ip-protocol-legacy {
        type union {
            type int32 {
                range "0..255";
            }
            type enumeration {
                enum tcp-udp                        { value -2; }
                enum icmp                           { value 1; }
                enum igmp                           { value 2; }
                enum ip                             { value 4; }
                enum tcp                            { value 6; }
                enum egp                            { value 8; }
                enum igp                            { value 9; }
                enum udp                            { value 17; }
                enum rdp                            { value 27; }
                enum ipv6                           { value 41; }
                enum ipv6-route                     { value 43; }
                enum ipv6-frag                      { value 44; }
                enum idrp                           { value 45; }
                enum rsvp                           { value 46; }
                enum gre                            { value 47; }
                enum ipv6-icmp                      { value 58; }
                enum ipv6-no-nxt                    { value 59; }
                enum ipv6-opts                      { value 60; }
                enum iso-ip                         { value 80; }
                enum eigrp                          { value 88; }
                enum ospf-igp                       { value 89; }
                enum ether-ip                       { value 97; }
                enum encap                          { value 98; }
                enum pnni                           { value 102; }
                enum pim                            { value 103; }
                enum vrrp                           { value 112; }
                enum l2tp                           { value 115; }
                enum stp                            { value 118; }
                enum ptp                            { value 123; }
                enum isis                           { value 124; }
                enum crtp                           { value 126; }
                enum crudp                          { value 127; }
                enum sctp                           { value 132; }
            }
        }
        description
            "IP protocol number. Well known protocol numbers include ICMP(1),
             TCP(6), UDP(17).";
    }

    typedef match-ip-protocol {
        type union {
            type int32 {
                range "0..255";
            }
            type enumeration {
                enum tcp-udp                        { value -2; }
                enum icmp                           { value 1; }
                enum igmp                           { value 2; }
                enum ip                             { value 4; }
                enum tcp                            { value 6; }
                enum egp                            { value 8; }
                enum igp                            { value 9; }
                enum udp                            { value 17; }
                enum rdp                            { value 27; }
                enum ipv6                           { value 41; }
                enum ipv6-route                     { value 43; }
                enum ipv6-frag                      { value 44; }
                enum idrp                           { value 45; }
                enum rsvp                           { value 46; }
                enum gre                            { value 47; }
                enum ipv6-icmp                      { value 58; }
                enum ipv6-no-nxt                    { value 59; }
                enum ipv6-opts                      { value 60; }
                enum iso-ip                         { value 80; }
                enum eigrp                          { value 88; }
                enum ospf-igp                       { value 89; }
                enum ether-ip                       { value 97; }
                enum encap                          { value 98; }
                enum pnni                           { value 102; }
                enum pim                            { value 103; }
                enum vrrp                           { value 112; }
                enum l2tp                           { value 115; }
                enum stp                            { value 118; }
                enum ptp                            { value 123; }
                enum isis                           { value 124; }
                enum crtp                           { value 126; }
                enum crudp                          { value 127; }
                enum sctp                           { value 132; }
            }
        }
        description
            "IP protocol number. Well known protocol numbers include ICMP(1),
             TCP(6), UDP(17).";
    }

    typedef ip-protocol {
        type union {
            type int32 {
                range "0..255";
            }
            type enumeration {
                enum icmp                           { value 1; }
                enum igmp                           { value 2; }
                enum ip                             { value 4; }
                enum tcp                            { value 6; }
                enum egp                            { value 8; }
                enum igp                            { value 9; }
                enum udp                            { value 17; }
                enum rdp                            { value 27; }
                enum ipv6                           { value 41; }
                enum ipv6-route                     { value 43; }
                enum ipv6-frag                      { value 44; }
                enum idrp                           { value 45; }
                enum rsvp                           { value 46; }
                enum gre                            { value 47; }
                enum ipv6-icmp                      { value 58; }
                enum ipv6-no-nxt                    { value 59; }
                enum ipv6-opts                      { value 60; }
                enum iso-ip                         { value 80; }
                enum eigrp                          { value 88; }
                enum ospf-igp                       { value 89; }
                enum ether-ip                       { value 97; }
                enum encap                          { value 98; }
                enum pnni                           { value 102; }
                enum pim                            { value 103; }
                enum vrrp                           { value 112; }
                enum l2tp                           { value 115; }
                enum stp                            { value 118; }
                enum ptp                            { value 123; }
                enum isis                           { value 124; }
                enum crtp                           { value 126; }
                enum crudp                          { value 127; }
                enum sctp                           { value 132; }
            }
        }
        description
            "IP protocol number. Well known protocol numbers include ICMP(1),
             TCP(6), UDP(17).";
    }

    typedef datastore-name {
        type string {
            pattern "candidate|running" {
                error-message "'datastore-name' must be candidate or running";
            }
        }
        description "The name of the datastore.";
    }

    typedef configuration-region {
        type enumeration {
            enum configure                      { value 1; }
            enum li                             { value 2; }
            enum bof                            { value 3; }
            enum debug                          { value 4; }
        }
        description "The name of the region in the command tree.";
    }

    typedef model-management {
        type enumeration {
            enum nokia {
                value 1;
                description "Configuration managed by Nokia models";
            }
            enum openconfig {
                value 2;
                description "Configuration managed by OpenConfig models";
            }
            enum openconfig-nokia {
                value 3;
                description "Configuration managed by OpenConfig and Nokia models";
            }
        }
        description "Models that can manage the configuration";
    }

    typedef big-integer {
        type string {
            length "1..55";
            pattern "[0-9]+" {
                error-message "'big-integer' must be decimal digits only (1..55 digits)";
            }
        }
        description "big-integer";
    }

    typedef mpls-tunnel-mode {
        type enumeration {
            enum uniform                        { value 0; }
            enum pipe                           { value 1; }
        }
        description "Specifies MPLS tunnel mode.";
    }

    typedef uuid {
        type string {
            length "36";
        }
        description "Specifies a Universally Unique Identifier.";
    }

    typedef dist-cpu-protection-protocol {
        type enumeration {
            enum arp                            { value 1; }
            enum dhcp                           { value 2; }
            enum http-redirect                  { value 3; }
            enum icmp                           { value 4; }
            enum igmp                           { value 5; }
            enum mld                            { value 6; }
            enum ndis                           { value 7; }
            enum pppoe-pppoa                    { value 8; }
            enum all-unspecified                { value 9; }
            enum mpls-ttl                       { value 10; }
            enum bfd-cpm                        { value 11; }
            enum bgp                            { value 12; }
            enum eth-cfm                        { value 13; }
            enum isis                           { value 14; }
            enum ldp                            { value 15; }
            enum ospf                           { value 16; }
            enum pim                            { value 17; }
            enum rsvp                           { value 18; }
            enum icmp-ping-check                { value 19; }
            enum lacp                           { value 21; }
            enum vrrp                           { value 22; }
            enum multi-chassis                  { value 23; }
            enum multi-chassis-sync             { value 24; }
        }
        description "Protocols supported for the Distributed CPU Protection Policy.";
    }

    typedef vrf-policy {
        type string {
            length "1..255";
            pattern "(.{1,64})|(.*[\\[].*)" {
                error-message "'vrf-policy' must be at most 64 characters or a valid expression containing [";
            }
        }
        description "Virtual Routing and Forwarding policy";
    }

    typedef policy-expr-string {
        type string {
            length "1..255";
            pattern ".*[\\[].*" {
                error-message "'policy-expr-string' must contain [ for a bracketed policy name in a routing policy logical expression (e.g. [policyA])";
            }
        }
        description "Routing policy expression";
    }

    typedef cam-state {
        type enumeration {
            enum operational                    { value 1; }
            enum near-full                      { value 2; }
            enum overload                       { value 3; }
        }
        description "CAM state";
    }

    typedef srv6-error-status {
        type enumeration {
            enum no-error                       { value 0; }
            enum error                          { value 1; }
            enum no-resource                    { value 2; }
            enum locator-admin-down             { value 3; }
            enum no-interface-configured        { value 4; }
            enum fpe-oper-down                  { value 5; }
            enum micro-seg-block-admin-down     { value 6; }
        }
        description "Srv6 Error status";
    }

    typedef srv6-route-resolution {
        type enumeration {
            enum route-table                    { value 0; }
            enum tunnel-table                   { value 1; }
            enum fallback-tunnel-to-route-table { value 2; }
        }
        description
            "Route resolution options. The options are as follows:

             route-table: only resolve to an IPv6 route in RTM. If none is found, then resolution
             will fail.

             tunnel-table: only try to resolve the route to a tunnel in TTMv6 i.e. the system will
             try to find an SRv6 policy with a matching color and endpoint locator for BGP routes
             received with an SRv6 TLV and therefore containing an SRv6 service SID in TTMv6. If
             none is found, then resolution will fail.

             fallback-tunnel-to-route-table: First try to resolve the route to a tunnel in TTMv6. If none
             is found, then fall back to resolution in RTM. If none is still found, then resolution
             will fail.";
    }

    typedef hex-string-or-uint {
        type union {
            type hex-string {
                length "10";
            }
            type uint32;
        }
        default "0x00000000";
        description "A type that accommodates '0x'-prefixed hex or integer";
    }

    typedef tls-protocol-version {
        type enumeration {
            enum tls-version-all                { value 1; }
            enum tls-version-12                 { value 2; }
            enum tls-version-13                 { value 3; }
        }
        description "TLS version";
    }

    typedef tls-status-verify {
        type enumeration {
            enum revoked                        { value 0; }
            enum good                           { value 1; }
        }
        description "TLS status of certificate";
    }

    typedef tls-cert-revocation-status {
        type enumeration {
            enum crl                            { value 1; }
            enum ocsp                           { value 2; }
        }
        description "The certification revocation status.";
    }

    typedef tls-cert-revocation-status-with-none {
        type enumeration {
            enum none                           { value 0; }
            enum crl                            { value 1; }
            enum ocsp                           { value 2; }
        }
        description "The certification revocation status or none.";
    }

    typedef attribute-set-import {
        type enumeration {
            enum ignore                         { value 1; }
            enum accept                         { value 2; }
            enum drop                           { value 3; }
        }
        description
            "ATTR_SET import options. The options are as follows:

             -ignore    (1): instructs BGP to ignore ATTR_SET in VPN-IP routes when
                     importing them into this specific VPRN; the ATTR_SET attribute
                     is transmitted unchanged to the CE (default for backwards compatibility).
             -accept    (2): instructs BGP to process ATTR_SET in VPN-IP routes when importing them
                     into this specific VPRN; as part of the normal processing, the ATTR_SET
                     attribute is removed before the route is advertised to CEs.
             -drop      (3): instructs BGP to ignore ATTR_SET in VPN-IP routes when importing them
                     into this specific VPRN; the ATTR_SET attribute is removed before
                     the route is advertised to CEs";
    }

    typedef strm-ctrl-traffic-type {
        type enumeration {
            enum broadcast                      { value 1; }
            enum multicast                      { value 2; }
            enum unicast                        { value 3; }
            enum unknown                        { value 4; }
        }
        description "Storm control traffic type";
    }

    typedef untagged-route-type {
        type enumeration {
            enum none {
                value 0;
                description "Untagged routes can bind to tagged or untagged LSPs";
            }
            enum untagged-tunnel {
                value 1;
                description "Untagged routes only bind to LSPs without an admin tag";
            }
        }
        description "Type of untagged route type to resolve";
    }

    typedef comment-text-type {
        type string {
            length "0..2048";
        }
        description "Type of text of configuration comment that is added or that is replacing the existing comment for the configuration element";
    }

    typedef bridge-id {
        type hex-string;
        description "Type of bridge identifier";
    }

}
