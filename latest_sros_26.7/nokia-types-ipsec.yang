module nokia-types-ipsec {

    yang-version "1.1";

    namespace "urn:nokia.com:sros:ns:yang:sr:types-ipsec";

    prefix "types-ipsec";

    import nokia-sros-yang-extensions     { prefix "sros-ext"; }

    sros-ext:sros-major-release "rel26";
    organization "Nokia";
    contact
        "Nokia SR OS Support
         Web: <http://www.nokia.com>";
    description
        "Common ipsec data types used in the SR OS management system.

         Copyright 2016 Nokia. All rights reserved. Reproduction of this document
         is authorized on the condition that the foregoing copyright notice is included.

         This nokia-types-ipsec YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    typedef ike-transform-id {
        type uint32 {
            range "1..4096";
        }
        description "The identification number of an IKE transform.";
    }

    typedef ike-policy-id {
        type uint32 {
            range "1..2048";
        }
        description "The identification number of an IKE policy.";
    }

    typedef dh-group {
        type enumeration {
            enum group-1                        { value 1; }
            enum group-2                        { value 2; }
            enum group-5                        { value 5; }
            enum group-14                       { value 14; }
            enum group-15                       { value 15; }
            enum group-19                       { value 19; }
            enum group-20                       { value 20; }
            enum group-21                       { value 21; }
        }
        description "The Diffie-Hellman (DH) groups.";
    }

    typedef ike-auth-algorithms {
        type enumeration {
            enum md-5                           { value 2; }
            enum sha-1                          { value 3; }
            enum sha-256                        { value 4; }
            enum sha-384                        { value 5; }
            enum sha-512                        { value 6; }
            enum aes-xcbc                       { value 7; }
            enum auth-encryption                { value 8; }
        }
        description "IPsec IKE authentication algorithms.";
    }

    typedef ike-encryption-algorithms {
        type enumeration {
            enum des                            { value 2; }
            enum des-3                          { value 3; }
            enum aes-128                        { value 4; }
            enum aes-192                        { value 5; }
            enum aes-256                        { value 6; }
            enum aes128-gcm8                    { value 7; }
            enum aes128-gcm16                   { value 9; }
            enum aes256-gcm8                    { value 13; }
            enum aes256-gcm16                   { value 15; }
        }
        description "IPsec IKE encryption algorithms.";
    }

    typedef auth-algorithms {
        type enumeration {
            enum null                           { value 1; }
            enum md-5                           { value 2; }
            enum sha-1                          { value 3; }
            enum sha-256                        { value 4; }
            enum sha-384                        { value 5; }
            enum sha-512                        { value 6; }
            enum aes-xcbc                       { value 7; }
            enum auth-encryption                { value 8; }
        }
        description "IPsec authentication algorithms.";
    }

    typedef encryption-algorithms {
        type enumeration {
            enum null                           { value 1; }
            enum des                            { value 2; }
            enum des-3                          { value 3; }
            enum aes-128                        { value 4; }
            enum aes-192                        { value 5; }
            enum aes-256                        { value 6; }
            enum aes128-gcm8                    { value 7; }
            enum aes128-gcm12                   { value 8; }
            enum aes128-gcm16                   { value 9; }
            enum aes192-gcm8                    { value 10; }
            enum aes192-gcm12                   { value 11; }
            enum aes192-gcm16                   { value 12; }
            enum aes256-gcm8                    { value 13; }
            enum aes256-gcm12                   { value 14; }
            enum aes256-gcm16                   { value 15; }
            enum null-aes128-gmac               { value 16; }
            enum null-aes192-gmac               { value 17; }
            enum null-aes256-gmac               { value 18; }
        }
        description "IPsec encryption algorithms.";
    }

    typedef lifetime {
        type uint32 {
            range "1200..31536000";
        }
        units "seconds";
        description "The lifetime for an IKE phase 1 or phase 2 key.";
    }

    typedef tunnel-template-id {
        type uint32 {
            range "1..2048";
        }
        description "The identification number of a tunnel template.";
    }

    typedef cert-revocation-status {
        type enumeration {
            enum crl                            { value 1; }
            enum ocsp                           { value 2; }
        }
        description "The certification revocation status.";
    }

    typedef cert-revocation-status-with-none {
        type enumeration {
            enum none                           { value 0; }
            enum crl                            { value 1; }
            enum ocsp                           { value 2; }
        }
        description "The certification revocation status or none.";
    }

    typedef oper-state {
        type enumeration {
            enum unknown                        { value 1; }
            enum up                             { value 2; }
            enum down                           { value 3; }
            enum transition                     { value 4; }
            enum limited                        { value 5; }
        }
        description "Oper-state specifies the IPsec operational states.";
    }

    typedef keying-type {
        type enumeration {
            enum none                           { value 0; }
            enum manual                         { value 1; }
            enum dynamic                        { value 2; }
        }
        description "The type of the IPsec keying.";
    }

    typedef multicast-protocol {
        type bits {
            bit mld                            { position 0; }
            bit igmp                           { position 1; }
        }
        description
            "Represents the multicast protocol types supported by the IPsec application.

             Value descriptions:
                 mld  - Multicast Listener Discovery
                 igmp - Internet Group Management Protocol";
    }

    typedef prf-algorithms {
        type enumeration {
            enum md-5                           { value 2; }
            enum sha-1                          { value 3; }
            enum sha-256                        { value 4; }
            enum sha-384                        { value 5; }
            enum sha-512                        { value 6; }
            enum aes-xcbc                       { value 7; }
            enum same-as-auth                   { value 8; }
        }
        description "IPsec authentication algorithms.";
    }

    typedef bfd-session-state {
        type enumeration {
            enum connected                      { value 2; }
            enum broken                         { value 3; }
            enum peer-detects-down              { value 4; }
            enum not-configured                 { value 5; }
            enum no-resources                   { value 6; }
        }
        description
            "The values used to identify the operational state of a BFD session
             the instance is relying upon for its fast triggering mechanism.";
    }

    typedef direction {
        type enumeration {
            enum inbound                        { value 1; }
            enum outbound                       { value 2; }
        }
        description "The values used to identify the direction of an IPsec tunnel.";
    }

    typedef ts-side {
        type enumeration {
            enum local                          { value 1; }
            enum remote                         { value 2; }
        }
        description "The values used to identify the side of a traffic selector entry.";
    }

}
