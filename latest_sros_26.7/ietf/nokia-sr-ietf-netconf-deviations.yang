module nokia-sr-ietf-netconf-deviations {

    yang-version "1.1";

    namespace "urn:nokia.com:sros:ns:yang:sr:ietf-netconf-deviations";

    prefix "nokia-nc-devs";

    import ietf-netconf                   { prefix "nc"; }
    import nokia-sros-yang-extensions     { prefix "sros-ext"; }

    sros-ext:sros-major-release "rel26";
    organization "Nokia";
    contact
        "Nokia SR OS Support
         Web: <http://www.nokia.com>";
    description
        "This module contains the list of deviations against the ietf-netconf
         module for the Nokia SR OS based routers.

         Copyright 2016 Nokia. All rights reserved. Reproduction of this document
         is authorized on the condition that the foregoing copyright notice is included.

         This nokia-sr-ietf-netconf-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    deviation /nc:get-config/nc:input/nc:source/nc:config-source/nc:startup {
        description "get-config operation from startup datastore is not supported.";
        deviate not-supported;
    }

    deviation /nc:edit-config/nc:input/nc:edit-content/nc:url {
        description "URL-based config content option for edit-config operation is not supported.";
        deviate not-supported;
    }

    deviation /nc:copy-config/nc:input/nc:target/nc:config-target/nc:running {
        description "copy-config operation to running datastore is not supported.";
        deviate not-supported;
    }

    deviation /nc:validate/nc:input/nc:source/nc:config-source/nc:startup {
        description "validate operation for startup datastore is not supported.";
        deviate not-supported;
    }

    deviation /nc:validate/nc:input/nc:source/nc:config-source/nc:url {
        description "validate operation for URL-based config content is not supported.";
        deviate not-supported;
    }

}
