module nokia-sr-ietf-netconf-nmda-augments {

    yang-version "1.1";

    namespace "urn:nokia.com:sros:ns:yang:sr:ietf-netconf-nmda-augments";

    prefix "nokia-ncds-augs";

    import ietf-netconf-nmda              { prefix "ncds"; }
    import nokia-sros-yang-extensions     { prefix "sros-ext"; }
    import nokia-types-sros               { prefix "types-sros"; }

    sros-ext:sros-major-release "rel26";
    organization "Nokia";
    contact
        "Nokia SR OS Support
         Web: <http://www.nokia.com>";
    description
        "This module contains the list of augments against the ietf-netconf-nmda
         module for the Nokia SR OS based routers.

         Copyright 2016 Nokia. All rights reserved. Reproduction of this document
         is authorized on the condition that the foregoing copyright notice is included.

         This nokia-sr-ietf-netconf-nmda-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    augment /ncds:get-data/ncds:input {
        leaf configuration-region {
            type enumeration {
                enum configure {
                    value 0;
                    description "primary configuration region";
                }
                enum li {
                    value 1;
                    description "Lawful Intercept (LI) configuration region";
                }
                enum bof {
                    value 2;
                    description "BOF configuration region";
                }
                enum debug {
                    value 3;
                    description "debug configuration region";
                }
            }
            description "SR OS configuration region";
        }

        leaf format {
            type enumeration {
                enum xml {
                    value 0;
                    description "XML output format";
                }
                enum json {
                    value 1;
                    description "JSON IETF output format";
                }
                enum md-cli {
                    value 2;
                    description "MD-CLI output format";
                }
            }
            description "Output format of data";
        }

        leaf with-managed {
            type empty;
            description "Annotate which model manages the configuration";
        }

        leaf-list managed-filter {
            type types-sros:model-management;
            description "Which model manages the configuration";
        }

    }

}
