module nokia-sr-openconfig-if-ip-augments {

    namespace "urn:nokia.com:sros:ns:yang:sr:openconfig-if-ip-augments";

    prefix "nokia-oc-ip-augs";

    import nokia-sros-yang-extensions     { prefix "sros-ext"; }
    import openconfig-if-ip               { prefix "oc-ip"; }
    import openconfig-interfaces          { prefix "oc-if"; }

    sros-ext:sros-major-release "rel26";
    organization "Nokia";
    contact
        "Nokia SR OS Support
         Web: <http://www.nokia.com>";
    description
        "This module contains the list of augments against the openconfig-if-ip
         module for the Nokia SR OS based routers.

         Copyright 2016 Nokia. All rights reserved. Reproduction of this document
         is authorized on the condition that the foregoing copyright notice is included.

         This nokia-sr-openconfig-if-ip-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    augment /oc-if:interfaces/oc-if:interface/oc-if:subinterfaces/oc-if:subinterface/oc-ip:ipv4/oc-ip:config {
        description "Adds additional primary-address configuration under sub-interface ipv4 configuration";

        leaf primary-address {
            type leafref {
                path "/oc-if:interfaces/oc-if:interface/oc-if:subinterfaces/oc-if:subinterface/oc-ip:ipv4/oc-ip:addresses/oc-ip:address/oc-ip:ip";
            }
            description
                "Select primary address from the list of ipv4 addresses.
                 When not configured the first address in the list becomes primary";
        }

    }

    augment /oc-if:interfaces/oc-if:interface/oc-if:subinterfaces/oc-if:subinterface/oc-ip:ipv4/oc-ip:state {
        description "State for additional primary-address configuration under sub-interface ipv4 configuration";

        leaf primary-address {
            type leafref {
                path "/oc-if:interfaces/oc-if:interface/oc-if:subinterfaces/oc-if:subinterface/oc-ip:ipv4/oc-ip:addresses/oc-ip:address/oc-ip:ip";
            }
            description
                "Select primary address from the list of ipv4 addresses.
                 When not configured the first address in the list becomes primary";
        }

    }

}
