module nokia-sr-openconfig-transport-types-augments {

    namespace "urn:nokia.com:sros:ns:yang:sr:openconfig-transport-types-augments";

    prefix "nokia-oc-opt-types-augs";

    import nokia-sros-yang-extensions     { prefix "sros-ext"; }
    import openconfig-transport-types     { prefix "oc-opt-types"; }

    sros-ext:sros-major-release "rel26";
    organization "Nokia";
    contact
        "Nokia SR OS Support
         Web: <http://www.nokia.com>";
    description
        "This module contains the list of augments against the openconfig-transport-types
         module for the Nokia SR OS based routers.

         Copyright 2016 Nokia. All rights reserved. Reproduction of this document
         is authorized on the condition that the foregoing copyright notice is included.

         This nokia-sr-openconfig-transport-types-augments YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    identity QSFP_DD {
        base oc-opt-types:TRANSCEIVER_FORM_FACTOR_TYPE;
        description
            "Double density QSFP56 form-factor pluggable transceiver
             supporting up to 400G signal";
    }

    identity SFP_DD {
        base oc-opt-types:TRANSCEIVER_FORM_FACTOR_TYPE;
        description
            "Double density SFP28 form-factor pluggable transceiver
             supporting up to 100G signal";
    }

    identity CFP2_DCO {
        base oc-opt-types:TRANSCEIVER_FORM_FACTOR_TYPE;
        description
            "CFP2 digital coherent optics transceiver supporting
             100G or 200G signal.";
    }

}
