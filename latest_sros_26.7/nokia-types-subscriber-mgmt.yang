module nokia-types-subscriber-mgmt {

    yang-version "1.1";

    namespace "urn:nokia.com:sros:ns:yang:sr:types-subscriber-mgmt";

    prefix "types-subscriber-mgmt";

    import nokia-sros-yang-extensions     { prefix "sros-ext"; }
    import nokia-types-filter             { prefix "types-filter"; }
    import nokia-types-services           { prefix "types-services"; }
    import nokia-types-sros               { prefix "types-sros"; }

    sros-ext:sros-major-release "rel26";
    organization "Nokia";
    contact
        "Nokia SR OS Support
         Web: <http://www.nokia.com>";
    description
        "Common subscriber-mgmt data types used in the SR OS management system.

         Copyright 2016 Nokia. All rights reserved. Reproduction of this document
         is authorized on the condition that the foregoing copyright notice is included.

         This nokia-types-subscriber-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-07-08";

    typedef sla-profile-host-limit {
        type int32 {
            range "1..131071";
        }
        description
            "This type indicates the maximum number of hosts using a given SLA
             profile.
             0 is not allowed.";
    }

    typedef sla-profile-host-limit-with-zero {
        type int32 {
            range "0..131071";
        }
        description
            "This type indicates the maximum number of hosts using a given SLA
             profile.
             0 is allowed.";
    }

    typedef queue-or-policer {
        type enumeration {
            enum queue                          { value 1; }
            enum policer                        { value 2; }
        }
        description
            "This type indicates whether the data applies to a queue or a
             policer.";
    }

    typedef queue-or-policer-id {
        type uint32 {
            range "1..63";
        }
        description "This type indicates the queue or policer-id.";
    }

    typedef subscriber-id {
        type types-sros:string-not-all-spaces {
            length "1..64";
        }
        description "The string identifying a subscriber.";
    }

    typedef session-type {
        type enumeration {
            enum ipoe                           { value 1; }
            enum ppp                            { value 2; }
            enum single-stack                   { value 3; }
            enum pfcp                           { value 4; }
        }
        description "Session type";
    }

    typedef session-id {
        type uint64;
        description "Session identifier";
    }

    typedef host-id {
        type enumeration {
            enum ipv4                           { value 1; }
            enum ipv6-na                        { value 2; }
            enum ipv6-slaac                     { value 3; }
            enum ipv6-pd                        { value 4; }
        }
        description "ID of a host within a session";
    }

    typedef pfcp-session-id {
        type string {
            length "16";
            pattern "([a-fA-F0-9]){0,16}" {
                error-message "'pfcp-session-id' must be 64-bit hex, 16 chars (e.g. 0a1b2c3d4e5f6078)";
            }
        }
        description "PFCP Session Identifier";
    }

    typedef pfcp-te-id {
        type string {
            length "8";
            pattern "([a-fA-F0-9]){0,8}" {
                error-message "'pfcp-te-id' must be 32-bit hex, 8 chars (e.g. 0a1b2c3d)";
            }
        }
        description "PFCP Traffic Endpoint Identifier";
    }

    typedef pfcp-pdr-id {
        type string {
            length "4";
            pattern "([a-fA-F0-9]){0,4}" {
                error-message "'pfcp-pdr-id' must be 16-bit hex, 4 chars (e.g. 0a1b)";
            }
        }
        description "PFCP Packet Data Rule Identifier";
    }

    typedef mac-specification {
        type string {
            length "2..7";
            pattern "([A-Z]{2}[^\\w\\s]?)|([a-z]{2}[^\\w\\s]?)|([a-z]{4}[^\\w\\s]?)|([A-Z]{4}[^\\w\\s]?)|([a-z]{6}[^\\w\\s]?)|([A-Z]{6}[^\\w\\s]?)" {
                error-message "'mac-specification' must be ab:, XY-, mmmm. or xx (e.g. ab: for 00:0c:f1:99:85:b8)";
            }
        }
        description
            "This type is a string of ASCII characters that specifies how to
             format a string that represents a MAC address.

             The format is as follows:

             <mac-specification> ::= <alpha-string> [<delimiter-char>]

             <alpha-string>      ::= <ucase-alpha>+ | <lcase-alpha>+
             <ucase-alpha>       ::= 'A' | 'B' | 'B' ... | 'Z'
             <lcase-alpha>       ::= 'a' | 'b' | 'c' ... | 'z'

             <delimiter-char>    any ASCII character that is not an <alpha-char>
                                 or a decimal digit

             Only the number of alphabetic characters and the case is relevant.
             Examples:

             'ab:'               00:0c:f1:99:85:b8  Nokia SROS style
             'XY-'               00-0C-F1-99-85-B8  IEEE canonical style
             'mmmm.'             0002.03aa.abff     Cisco style.
             'xx'                000cf19985b8";
    }

    typedef ancp-string {
        type string {
            length "1..63";
        }
        description "This type identifies a valid ANCP string.";
    }

    typedef ancp-string-or-empty {
        type string {
            length "0..63";
        }
        description "This type identifies a valid ANCP string.";
    }

    typedef gtp-chg-chars {
        type enumeration {
            enum bit0                           { value 0; }
            enum bit1                           { value 1; }
            enum bit2                           { value 2; }
            enum bit3                           { value 3; }
            enum bit4                           { value 4; }
            enum bit5                           { value 5; }
            enum bit6                           { value 6; }
            enum bit7                           { value 7; }
            enum bit8                           { value 8; }
            enum bit9                           { value 9; }
            enum bit10                          { value 10; }
            enum bit11                          { value 11; }
            enum bit12                          { value 12; }
            enum bit13                          { value 13; }
            enum bit14                          { value 14; }
            enum bit15                          { value 15; }
        }
        description
            "specifies Charging Characteristics bits
             The meaning of the bits is opaque to this system.";
    }

    typedef sub-id-key-ipoe {
        type enumeration {
            enum mac                            { value 1; }
            enum sap-id                         { value 2; }
            enum circuit-id                     { value 3; }
            enum remote-id                      { value 4; }
            enum dual-stack-remote-id           { value 6; }
            enum service-name                   { value 7; }
        }
        description "Possible keys for auto-generated sub-id keys for IPoE hosts";
    }

    typedef sub-id-key-ppp {
        type enumeration {
            enum mac                            { value 1; }
            enum sap-id                         { value 2; }
            enum circuit-id                     { value 3; }
            enum remote-id                      { value 4; }
            enum session-id                     { value 5; }
        }
        description "Possible keys for auto-generated sub-id keys for PPP hosts";
    }

    typedef user-name-format-domain-operation {
        type enumeration {
            enum append                         { value 1; }
            enum strip                          { value 2; }
            enum replace                        { value 3; }
            enum default                        { value 4; }
        }
    }

    typedef sap-subscriber-limit {
        type union {
            type enumeration {
                enum no-limit                       { value 0; }
            }
            type uint32 {
                range "1..131071";
            }
        }
        description
            "The sap-subscriber-limit type specifies the maximum number
             of subscribers allowed on a SAP.";
    }

    typedef sap-host-limit {
        type uint32 {
            range "1..131071";
        }
        description
            "The sap-host-limit type specifies the maximum number
             of subscriber hosts allowed on a SAP.";
    }

    typedef sap-lease-state-limit {
        type uint32 {
            range "1..131071";
        }
        description
            "The sap-lease-state-limit type specifies the maximum number
             of ipv4 leases allowed on a SAP.";
    }

    typedef activity-threshold {
        type uint32 {
            range "1..100000000";
        }
        units "kilobps";
        description
            "Indicates the threshold in Kbps that is applied to determine
             if a subscriber is active.

             If the traffic volume is below the threshold, the subscriber is idle.

             Otherwise, the subscriber is active.";
    }

    typedef host-connectivity-verify-action {
        type enumeration {
            enum alarm                          { value 1; }
            enum remove                         { value 2; }
        }
        description
            "The host-connectivity-verify-action data type is an enumerated
             integer that describes the values used to identify the action taken
             when Subscriber Host Connectivity Verification (SHCV) failed.";
    }

    typedef host-connectivity-verify-interval {
        type types-sros:time-duration {
            range "1..6000";
        }
        units "minutes";
        description
            "The host-connectivity-verify-interval data type is a number that
             specifies the interval between connectivity checks.";
    }

    typedef host-connectivity-verify-retry-count {
        type uint32 {
            range "1..29";
        }
        description
            "The host-connectivity-verify-retry-count data type is a number
             that specifies the number of connectivity check retransmissions.

             Setting the value to n specifies that, for any given host,
             at most (n+1) probes are done each interval,
             and (n+1) missed replies are considered as a connectivity
             failure.";
    }

    typedef host-connectivity-verify-retry-timeout {
        type types-sros:time-duration {
            range "1..60";
        }
        units "seconds";
        description
            "The host-connectivity-verify-retry-timeout data type is a number
             that specifies the timeout before a connectivity check
             retransmission.";
    }

    typedef host-connectivity-verify-source-ip-origin {
        type enumeration {
            enum interface {
                value 1;
                description "IP address of the interface";
            }
            enum vrrp {
                value 2;
                description "Primary IP address of the VRRP";
            }
        }
        description
            "The host-connectivity-verify-source-ip-origin data type is an
             enumerated integer that describes the values used to identify the
             origin of the source IP address used for connectivity verification
             in a layer-3 service (IES or VPRN).

             The value 'interface' means that the IP address of the interface
             is used.

             The value 'vrrp' means that the primary IP address of the
             Virtual Router Redundancy Protocol (VRRP) is used.";
    }

    typedef router-advertisement-prefix-options-lifetime {
        type union {
            type types-sros:time-duration {
                range "0..4294967294";
            }
            type enumeration {
                enum infinite                       { value -1; }
            }
        }
        units "seconds";
        default "0";
    }

    typedef ludb-ipoe-match-type {
        type enumeration {
            enum circuit-id                     { value 1; }
            enum mac                            { value 2; }
            enum remote-id                      { value 3; }
            enum sap-id                         { value 4; }
            enum service-id                     { value 5; }
            enum string                         { value 6; }
            enum system-id                      { value 7; }
            enum option60                       { value 8; }
            enum encap-tag-range                { value 9; }
            enum dual-stack-remote-id           { value 10; }
            enum derived-id                     { value 11; }
            enum ip                             { value 12; }
        }
        description "The IPOE host match type.";
    }

    typedef ludb-ppp-match-type {
        type enumeration {
            enum circuit-id                     { value 1; }
            enum mac                            { value 2; }
            enum remote-id                      { value 3; }
            enum username                       { value 4; }
            enum service-name                   { value 5; }
            enum sap-id                         { value 6; }
            enum encap-tag-range                { value 7; }
            enum derived-id                     { value 8; }
        }
        description "The PPP host match criteria.";
    }

    typedef int-dest-id {
        type types-sros:string-not-all-spaces {
            length "1..32";
        }
        description
            "The string identifying an intermediate destination
             (for example a DSLAM).";
    }

    typedef ipoe-session-min-auth-interval {
        type union {
            type enumeration {
                enum infinite                       { value -1; }
                enum always-reauthenticate          { value 0; }
            }
            type types-sros:time-duration {
                range "1..32000000";
            }
        }
        units "seconds";
        description
            "Configure the minimum interval between two
             authentication attempts";
    }

    typedef ipoe-session-radius-session-timeout {
        type enumeration {
            enum absolute                       { value 1; }
            enum ignore                         { value 2; }
            enum backwards-compatible           { value 3; }
        }
        description "how to interpret the session timeout VSA";
    }

    typedef dhcp6-prefix-lifetime {
        type union {
            type types-sros:time-duration {
                range "300..4294967294";
            }
            type enumeration {
                enum infinite                       { value -1; }
            }
        }
        units "seconds";
    }

    typedef dhcp6-prefix-lifetime-new {
        type types-sros:time-duration {
            range "300..315446399";
        }
        units "seconds";
    }

    typedef dhcp6-renew-timer {
        type types-sros:time-duration {
            range "0..604800";
        }
        units "seconds";
        default "1800";
        description "The DHCP6 renew timer (T1).";
    }

    typedef dhcp6-rebind-timer {
        type types-sros:time-duration {
            range "0..1209600";
        }
        units "seconds";
        default "2880";
        description "The DHCP6 rebind timer (T2).";
    }

    typedef pppoe-anti-spoof {
        type enumeration {
            enum mac-sid                        { value 1; }
            enum mac-sid-ip                     { value 2; }
        }
        description "The type of anti-spoof filtering for PPPoE";
    }

    typedef session-anti-spoof {
        type union {
            type types-services:anti-spoof-option;
            type pppoe-anti-spoof;
        }
        description "The type of anti-spoof filtering for a subscriber session";
    }

    typedef bonding-context-id {
        type types-sros:named-item;
        description "The bonding context identifier.";
    }

    typedef bonding-connection-index {
        type uint32 {
            range "1..2";
        }
        description "The bonding connection index.";
    }

    typedef multicast-bonding-connection {
        type union {
            type bonding-connection-index;
            type enumeration {
                enum use-incoming                   { value 0; }
            }
        }
        description "The multicast bonding connection.";
    }

    typedef aa-sub-scope {
        type enumeration {
            enum subscriber                     { value 1; }
            enum mac                            { value 2; }
        }
        description "The scope of the AA subscriber";
    }

    typedef pppoe-session-id {
        type uint32 {
            range "0..65535";
        }
        description "PPPoE session identifier";
    }

    typedef subscriber-host-origin {
        type enumeration {
            enum static-host                    { value 1; }
            enum dhcp-lease                     { value 2; }
            enum non-subscriber-traffic         { value 3; }
            enum pppoe-session                  { value 4; }
            enum arp-host                       { value 5; }
            enum ipcp-session                   { value 6; }
            enum l2tp-session                   { value 7; }
            enum ppp-slaac                      { value 8; }
            enum ppp-dhcp6                      { value 9; }
            enum ipoe-dhcp6                     { value 10; }
            enum ipoe-slaac                     { value 11; }
            enum wpp                            { value 12; }
            enum static-host-v6                 { value 13; }
            enum managed-host-data-trigger      { value 14; }
            enum managed-host-aaa               { value 15; }
            enum managed-host-gtp               { value 16; }
            enum managed-host-bonding           { value 17; }
            enum pfcp                           { value 18; }
        }
        description "The origin of the subscriber host.";
    }

    typedef accounting-session-id {
        type string {
            length "1..22";
        }
        description "Identification of a sbuscriber for the purposes of accounting";
    }

    typedef routing-origin {
        type enumeration {
            enum aaa                            { value 1; }
            enum dynamic                        { value 2; }
            enum static                         { value 3; }
            enum bonding                        { value 4; }
            enum pfcp                           { value 5; }
        }
        description "The origin of the address of a subscriber host";
    }

    typedef any-qos-policy-name {
        type types-sros:named-item-64;
        description
            "The identification of any qos policy, including dynamic policies
             created by the system";
    }

    typedef overrule-qos-policy-name {
        type any-qos-policy-name;
        description "Qos policy to over-rule the policy specified in the sla-profile";
    }

    typedef any-filter-name {
        type types-filter:filter-name;
        description
            "The identification of any filter, including dynamic filters created
             by the system";
    }

    typedef overrule-filter-name {
        type union {
            type any-filter-name;
            type enumeration {
                enum disabled-filter                { value -1; }
            }
        }
        description "Filter to over-rule the filter specified in the sla-profile";
    }

    typedef subscriber-host-one-time-http-redirect-state {
        type enumeration {
            enum off                            { value 0; }
            enum active                         { value 1; }
            enum triggered                      { value 2; }
        }
        description "The state of the one-time HTTP redirection for a subscriber host";
    }

    typedef subscriber-host-one-time-http-redirect-filter-source {
        type enumeration {
            enum unknown                        { value 0; }
            enum sla-profile                    { value 1; }
            enum radius                         { value 2; }
            enum radius-coa                     { value 3; }
            enum diameter                       { value 4; }
            enum diameter-rar                   { value 5; }
        }
        description "The source of the one-time HTTP redirection for a subscriber host";
    }

    typedef sla-profile-instance-sharing-type {
        type enumeration {
            enum per-sap                        { value 1; }
            enum per-group                      { value 2; }
            enum per-ppp-session                { value 3; }
            enum per-ipoe-session               { value 4; }
            enum per-pfcp-session               { value 5; }
        }
        description
            "Indicates the way subscriber hosts of a given subscriber and SAP
             are grouped together to share an SLA profile instance";
    }

    typedef submgt-statistics-ipv4-type {
        type enumeration {
            enum ipcp {
                value 0;
                description "The number of PPP hosts (IPCP)";
            }
            enum dhcp {
                value 1;
                description "The number of IPOE hosts (DHCP)";
            }
            enum arp {
                value 2;
                description "The number of IPOE hosts (ARP)";
            }
            enum static {
                value 3;
                description "The number of IPOE hosts (Static)";
            }
            enum data-triggered {
                value 4;
                description "The number of IPOE managed hosts (data-triggered WAN)";
            }
            enum aaa {
                value 5;
                description "The number of IPOE managed hosts (AAA-triggered)";
            }
            enum gtp {
                value 6;
                description "The number of IPOE managed hosts (GTP-triggered)";
            }
            enum bonding {
                value 7;
                description "The number of IPOE managed hosts (bonding-triggered)";
            }
            enum dhcp-bsm {
                value 8;
                description "The number of IPOE BSM hosts (DHCP)";
            }
            enum static-bsm {
                value 9;
                description "The number of IPOE BSM hosts (Static)";
            }
            enum dhcp-bsm-antispoof {
                value 10;
                description "The number of IPOE BSM hosts with antispoof (DHCP)";
            }
            enum static-bsm-antispoof {
                value 11;
                description "The number of IPOE BSM hosts with antispoof (Static)";
            }
            enum pfcp-ppp {
                value 12;
                description "The number of PPP hosts (PFCP)";
            }
            enum pfcp-ipoe {
                value 13;
                description "The number of IPOE hosts (PFCP)";
            }
            enum pfcp-fwa {
                value 14;
                description "The number of FWA hosts (PFCP)";
            }
        }
        description "Submgt statistics about IPv4 hosts";
    }

    typedef submgt-statistics-ipv6-type {
        type enumeration {
            enum ppp-slaac {
                value 0;
                description "The number of PPP hosts (SLAAC)";
            }
            enum ppp-dhcp6-na {
                value 1;
                description "The number of PPP hosts (DHCP6 NA)";
            }
            enum ppp-dhcp6-pd {
                value 2;
                description "The number of PPP hosts (DHCP6 PD)";
            }
            enum ppp-dhcp6-pd-mngdrt {
                value 3;
                description "The number of PPP managed routes (DHCP6 PD)";
            }
            enum ipoe-slaac {
                value 4;
                description "The number of IPOE hosts (SLAAC)";
            }
            enum ipoe-dhcp6-na {
                value 5;
                description "The number of IPOE hosts (DHCP6 NA)";
            }
            enum ipoe-dhcp6-pd {
                value 6;
                description "The number of IPOE hosts (DHCP6 PD)";
            }
            enum ipoe-dhcp6-pd-mngdrt {
                value 7;
                description "The number of IPOE managed routes (DHCP6 PD)";
            }
            enum ipoe-static-wan {
                value 8;
                description "The number of IPOE hosts (Static WAN)";
            }
            enum ipoe-static-pfx {
                value 9;
                description "The number of IPOE hosts (Static Pfx)";
            }
            enum ipoe-mngd-data-wan {
                value 10;
                description "The number of IPOE hosts (data-triggered WAN)";
            }
            enum ipoe-mngd-data-pfx {
                value 11;
                description "The number of IPOE managed hosts (data-triggered Pfx)";
            }
            enum ipoe-mngd-data-pfx-mngdrt {
                value 12;
                description "The number of IPOE managed routes (data-triggered Pfx)";
            }
            enum ipoe-mngd-aaa {
                value 13;
                description "The number of IPOE managed hosts (AAA-triggered)";
            }
            enum ipoe-mngd-gtp {
                value 14;
                description "The number of IPOE managed hosts (GTP-triggered)";
            }
            enum ipoe-mngd-bonding {
                value 15;
                description "The number of IPOE managed hosts (bonding-triggered)";
            }
            enum ipoe-dhcp6-na-bsm {
                value 16;
                description "The number of IPOE BSM hosts (DHCP6 NA)";
            }
            enum ipoe-dhcp6-pd-bsm {
                value 17;
                description "The number of IPOE BSM hosts (DHCP6 PD)";
            }
            enum pfcp-ppp-slaac {
                value 18;
                description "The number of PPP hosts (PFCP SLAAC)";
            }
            enum pfcp-ppp-na {
                value 19;
                description "The number of PPP hosts (PFCP NA)";
            }
            enum pfcp-ppp-pd {
                value 20;
                description "The number of PPP hosts (PFCP PD)";
            }
            enum pfcp-ipoe-slaac {
                value 21;
                description "The number of IPOE hosts (PFCP SLAAC)";
            }
            enum pfcp-ipoe-na {
                value 22;
                description "The number of IPOE hosts (PFCP NA)";
            }
            enum pfcp-ipoe-pd {
                value 23;
                description "The number of IPOE hosts (PFCP PD)";
            }
            enum pfcp-fwa-slaac {
                value 24;
                description "The number of FWA hosts (PFCP SLAAC)";
            }
            enum pfcp-fwa-na {
                value 25;
                description "The number of FWA hosts (PFCP NA)";
            }
            enum pfcp-fwa-pd {
                value 26;
                description "The number of FWA hosts (PFCP PD)";
            }
        }
        description "Submgt statistics about IPv6 hosts and managed routes";
    }

    typedef submgt-statistics-total-type {
        type enumeration {
            enum subhosts {
                value 0;
                description "The total number of subscriber hosts";
            }
            enum ppp {
                value 1;
                description "The total number of PPP hosts";
            }
            enum ipoe {
                value 2;
                description "The total number of IPOE hosts";
            }
            enum ipv4 {
                value 3;
                description "The total number of IPv4 hosts";
            }
            enum ipv6 {
                value 4;
                description "The total number of IPv6 hosts";
            }
            enum ipv6-pd-mngdrt {
                value 5;
                description "The total number of PD Managed Routes";
            }
            enum l2tp-lac {
                value 6;
                description "The total number of L2TP hosts (LAC)";
            }
            enum l2tp-lns {
                value 7;
                description "The total number of L2TP hosts (LNS)";
            }
            enum internal {
                value 8;
                description "The total number of internal hosts";
            }
            enum nonsub-traffic {
                value 9;
                description "The total number of Non Subscriber Traffic hosts";
            }
            enum dhcp-leases {
                value 10;
                description "The total number of DHCP leases";
            }
            enum dhcp6-leases {
                value 11;
                description "The total number of DHCPv6 leases";
            }
            enum scale {
                value 12;
                description "The total number of hosts, including internal hosts";
            }
            enum pfcp {
                value 13;
                description "The total number of PFCP hosts";
            }
        }
        description "Submgt statistics about total hosts and leases (V4, V6 and other)";
    }

    typedef submgt-statistics-l2tp-type {
        type enumeration {
            enum l2tp-tunnels-originator {
                value 0;
                description "The total number of L2TP tunnels (originator)";
            }
            enum l2tp-tunnels-receiver {
                value 1;
                description "The total number of L2TP tunnels (receiver)";
            }
            enum l2tp-tunnels-total {
                value 2;
                description "The total number of L2TP tunnels";
            }
        }
        description "Submgt statistics about L2TP tunnels";
    }

    typedef submgt-statistics-session-type {
        type enumeration {
            enum ppp-sessions-total-established {
                value 0;
                description "The total number of PPP sessions established";
            }
            enum ppp-sessions-total-in-setup {
                value 1;
                description "The total number of PPP sessions in setup";
            }
            enum ppp-sessions-local-pppoe {
                value 2;
                description "The total number of locally terminated PPP sessions (PPPoE)";
            }
            enum ppp-sessions-local-pppoeoa {
                value 3;
                description "The total number of locally terminated PPP sessions (PPPoEoA)";
            }
            enum ppp-sessions-local-pppoa {
                value 4;
                description "The total number of locally terminated PPP sessions (PPPoA)";
            }
            enum ppp-sessions-local-l2tp-lns {
                value 5;
                description "The total number of locally terminated PPP sessions (L2TP LNS)";
            }
            enum ppp-sessions-local-total {
                value 6;
                description "The total number of locally terminated PPP sessions";
            }
            enum ppp-sessions-lac-pppoe {
                value 7;
                description "The total number of PPP sessions tunneled over L2TP (PPPoE)";
            }
            enum ppp-sessions-lac-pppoeoa {
                value 8;
                description "The total number of PPP sessions tunneled over L2TP (PPPoEoA)";
            }
            enum ppp-sessions-lac-pppoa {
                value 9;
                description "The total number of PPP sessions tunneled over L2TP (PPPoA)";
            }
            enum ppp-sessions-lac-l2tp-lts {
                value 10;
                description "The total number of PPP sessions tunneled over L2TP (L2TP LTS)";
            }
            enum ppp-sessions-lac-total {
                value 11;
                description "The total number of PPP sessions tunneled over L2TP";
            }
            enum ipoe-sessions-total-established {
                value 12;
                description "The total number of IPOE sessions established";
            }
            enum ipoe-sessions-total-in-setup {
                value 13;
                description "The total number of IPOE sessions in setup";
            }
            enum subscribers-total {
                value 14;
                description "The total number of Subscribers";
            }
            enum pfcp-sessions-ppp {
                value 15;
                description "The total number of PFCP sessions (PPP)";
            }
            enum pfcp-sessions-ipoe {
                value 16;
                description "The total number of PFCP sessions (IPOE)";
            }
            enum pfcp-sessions-default-tunnel {
                value 17;
                description "The total number of PFCP default tunnels";
            }
            enum pfcp-sessions-in-setup {
                value 18;
                description "The total number of PFCP sessions in setup";
            }
            enum pfcp-sessions-total {
                value 19;
                description "The total number of PFCP sessions";
            }
            enum pfcp-sessions-lac {
                value 20;
                description "The total number of PFCP sessions (LAC)";
            }
            enum pfcp-sessions-fwa {
                value 21;
                description "The total number of PFCP sessions (FWA)";
            }
            enum pfcp-sessions-l2-access-id-tunnel {
                value 22;
                description "The total number of PFCP l2 access id tunnels";
            }
        }
        description "Submgt statistics about PPP sessions, IPOE sessions and Subscribers";
    }

    typedef subscriber-egress-policer-stat-mode-type {
        type enumeration {
            enum no-stats                       { value 0; }
            enum minimal                        { value 1; }
            enum offered-profile-no-cir         { value 2; }
            enum offered-total-cir              { value 3; }
            enum offered-profile-cir            { value 4; }
            enum offered-limited-capped-cir     { value 5; }
            enum offered-profile-capped-cir     { value 6; }
            enum v4-v6                          { value 7; }
            enum offered-total-cir-exceed       { value 8; }
            enum offered-four-profile-no-cir    { value 9; }
            enum offered-total-cir-four-profile { value 10; }
        }
        description "the mode of statistics collected by this egress policer.";
    }

    typedef subscriber-egress-policer-stat-mode-2-type {
        type enumeration {
            enum no-stats                       { value 0; }
            enum minimal                        { value 1; }
            enum offered-profile-no-cir         { value 2; }
            enum offered-total-cir              { value 3; }
            enum offered-profile-cir            { value 4; }
            enum offered-limited-capped-cir     { value 5; }
            enum offered-profile-capped-cir     { value 6; }
            enum v4-v6                          { value 7; }
            enum offered-total-cir-exceed       { value 8; }
            enum offered-four-profile-no-cir    { value 9; }
            enum offered-total-cir-four-profile { value 10; }
            enum bonding                        { value 11; }
        }
        description "the mode of statistics collected by this egress policer.";
    }

    typedef subscriber-ingress-policer-stat-mode-type {
        type enumeration {
            enum no-stats                       { value 0; }
            enum minimal                        { value 1; }
            enum offered-profile-no-cir         { value 2; }
            enum offered-total-cir              { value 3; }
            enum offered-priority-no-cir        { value 4; }
            enum offered-profile-cir            { value 5; }
            enum offered-priority-cir           { value 6; }
            enum offered-limited-profile-cir    { value 7; }
            enum offered-profile-capped-cir     { value 8; }
            enum offered-limited-capped-cir     { value 9; }
            enum v4-v6                          { value 10; }
        }
        description "the mode of statistics collected by this ingress policer.";
    }

    typedef shcv-oper-state {
        type enumeration {
            enum disabled                       { value 1; }
            enum undefined                      { value 2; }
            enum down                           { value 3; }
            enum up                             { value 4; }
        }
        description "The operational state of the subscriber host connectivity check.";
    }

    typedef iaid-type {
        type enumeration {
            enum temporary                      { value 1; }
            enum non-temporary                  { value 2; }
            enum prefix                         { value 3; }
        }
        description "The type of the addresses that are associated with the Identity Association ID (IAID)";
    }

    typedef ppp-user-name {
        type types-sros:display-string-or-empty {
            length "0..253";
        }
        description "The PPP user name";
    }

    typedef sla-profile-instance-id {
        type uint32;
        description "Identifies a sla profile instance";
    }

    typedef rip-listener-state {
        type enumeration {
            enum active                         { value 1; }
            enum inactive                       { value 2; }
            enum no-esm-required                { value 3; }
            enum wrong-anti-spoof               { value 4; }
            enum local-interface-down           { value 5; }
            enum host-inactive                  { value 6; }
            enum l2-aware-not-supported         { value 7; }
            enum gtp-not-supported              { value 8; }
            enum multi-chassis-standby          { value 9; }
            enum rip-disabled                   { value 10; }
        }
        description "The state of the RIP listener";
    }

    typedef bgp-peering-state {
        type enumeration {
            enum installed                      { value 1; }
            enum not-installed                  { value 2; }
            enum no-enhanced-submgt             { value 3; }
            enum wrong-anti-spoof               { value 4; }
            enum parent-interface-down          { value 5; }
            enum host-inactive                  { value 6; }
            enum no-dual-homing-support         { value 7; }
            enum invalid-radius-attribute       { value 8; }
            enum no-dynamic-peer-group          { value 9; }
            enum duplicate-peer                 { value 10; }
            enum max-peers-reached              { value 11; }
            enum l2-aware-not-supported         { value 12; }
            enum gtp-not-supported              { value 13; }
            enum generic-error                  { value 14; }
        }
        description "The state of the BGP peering session.";
    }

    typedef dhcp-address-origin {
        type enumeration {
            enum none                           { value 0; }
            enum dhcp                           { value 1; }
            enum radius                         { value 2; }
            enum retailer-radius                { value 3; }
            enum retailer-dhcp                  { value 4; }
            enum default                        { value 5; }
            enum local-user-db                  { value 6; }
            enum gtp                            { value 7; }
            enum local-pool                     { value 8; }
            enum wpp                            { value 9; }
            enum diameter-gx                    { value 10; }
            enum dtc                            { value 11; }
            enum diameter-nasreq                { value 12; }
            enum data                           { value 13; }
            enum bonding                        { value 14; }
        }
        description "The address origin.";
    }

    typedef session-address-origin {
        type enumeration {
            enum none                           { value 0; }
            enum dhcp                           { value 1; }
            enum radius                         { value 2; }
            enum retailer-radius                { value 3; }
            enum retailer-dhcp                  { value 4; }
            enum default                        { value 5; }
            enum local-user-db                  { value 6; }
            enum gtp                            { value 7; }
            enum local-pool                     { value 8; }
            enum wpp                            { value 9; }
            enum diameter-gx                    { value 10; }
            enum dtc                            { value 11; }
            enum diameter-nasreq                { value 12; }
            enum data                           { value 13; }
            enum bonding                        { value 14; }
            enum mid-session-change             { value 50; }
            enum tags                           { value 51; }
            enum l2tp                           { value 52; }
            enum python                         { value 53; }
        }
        description "The address origin.";
    }

    typedef managed-route-state {
        type enumeration {
            enum installed                      { value 0; }
            enum not-yet-installed              { value 1; }
            enum wrong-anti-spoof-type          { value 2; }
            enum out-of-memory                  { value 3; }
            enum shadowed                       { value 4; }
            enum route-table-full               { value 5; }
            enum parent-interface-down          { value 6; }
            enum host-inactive                  { value 7; }
            enum enhanced-subscriber-management-required { value 8; }
            enum l2-aware-not-supported         { value 10; }
            enum next-hop-limit-exceeded        { value 11; }
            enum no-next-hop                    { value 13; }
            enum gtp-not-supported              { value 14; }
            enum withdrawn                      { value 15; }
        }
        description "The state of the managed route";
    }

    typedef access-loop-encap-1 {
        type union {
            type uint32 {
                range "3..255";
            }
            type enumeration {
                enum untagged-ethernet              { value 1; }
                enum single-tagged-ethernet         { value 2; }
            }
        }
        description "The encapsulation used on the DSL access loop";
    }

    typedef access-loop-encap-2 {
        type union {
            type uint32 {
                range "9..255";
            }
            type enumeration {
                enum pppoa-llc                      { value 1; }
                enum pppoa-null                     { value 2; }
                enum ipoa-llc                       { value 3; }
                enum ipoa-null                      { value 4; }
                enum ethernet-over-aal5-llc-fcs     { value 5; }
                enum ethernet-over-aal5-llc-no-fcs  { value 6; }
                enum ethernet-over-aal5-null-fcs    { value 7; }
                enum ethernet-over-aal5-null-no-fcs { value 8; }
            }
        }
        description "The encapsulation used on the DSL access loop";
    }

    typedef data-link {
        type union {
            type enumeration {
                enum aal5                           { value 0; }
                enum ethernet                       { value 1; }
            }
            type uint32 {
                range "2..255";
            }
        }
        description "The data link on the DSL access loop";
    }

    typedef match-protocol-next-header {
        type types-sros:match-ip-protocol-legacy;
        description "IPv4 protocol or IPv6 next-header";
    }

    typedef match-icmp-type {
        type uint32 {
            range "0..255";
        }
        description "IPv6 or IPv6 icmp type";
    }

    typedef authentication-origin {
        type enumeration {
            enum python                         { value 1; }
            enum diameter-gx                    { value 2; }
            enum ludb                           { value 3; }
            enum radius                         { value 4; }
            enum diameter-nasreq                { value 5; }
            enum gtp                            { value 6; }
            enum dhcp                           { value 7; }
            enum local-address-assignment       { value 8; }
            enum pfcp                           { value 9; }
            enum config                         { value 10; }
        }
        description
            "The authentication-origin data type is an enumerated
             integer that describes the possible authentication source / origin.";
    }

}
