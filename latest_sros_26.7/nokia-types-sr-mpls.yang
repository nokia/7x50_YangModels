module nokia-types-sr-mpls {

    yang-version "1.1";

    namespace "urn:nokia.com:sros:ns:yang:sr:types-sr-mpls";

    prefix "types-sr-mpls";

    import nokia-sros-yang-extensions     { prefix "sros-ext"; }

    sros-ext:sros-major-release "rel26";
    organization "Nokia";
    contact
        "Nokia SR OS Support
         Web: <http://www.nokia.com>";
    description
        "Common sr-mpls data types used in the SR OS management system.

         Copyright 2016 Nokia. All rights reserved. Reproduction of this document
         is authorized on the condition that the foregoing copyright notice is included.

         This nokia-types-sr-mpls YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";
    revision "2026-03-11";

    typedef sid-oper-state {
        type enumeration {
            enum enabled                        { value 1; }
            enum admin-down                     { value 2; }
            enum failed                         { value 3; }
            enum not-preferred                  { value 4; }
            enum if-down                        { value 5; }
            enum if-failed                      { value 6; }
        }
        description
            "Indicates the operational state of a prefix SID for
             an interface.";
    }

    typedef srh-mode {
        type enumeration {
            enum psp                            { value 1; }
            enum usp                            { value 2; }
            enum psp-usd                        { value 3; }
            enum usp-usd                        { value 4; }
            enum psp-usp-usd                    { value 5; }
        }
        description
            "Segment Routing Header (SRH) mode.

             psp - Penultimate Segment Pop of the SRH.
             usp - Ultimate Segment Pop of the SRH.
             pspUsd - PSP Ultimate Segment Decapsulation.
             uspUsd - USP Ultimate Segment Decapsulation.
             pspUspUsd - PSP USP Ultimate Segment Decapsulation.";
    }

}
