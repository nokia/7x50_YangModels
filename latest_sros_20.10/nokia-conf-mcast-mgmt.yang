submodule nokia-conf-mcast-mgmt {

    yang-version "1.1";

    belongs-to nokia-conf { prefix "conf"; }

    import ietf-yang-types                { prefix "yang"; }
    import nokia-sros-yang-extensions     { prefix "sros-ext"; }
    import nokia-types-mcast-mgmt         { prefix "types-mcast-mgmt"; }
    import nokia-types-sros               { prefix "types-sros"; }

    include nokia-conf-groups;
    include nokia-conf-qos;

    sros-ext:sros-major-release "rel20";

    organization "Nokia";

    contact
        "Nokia SR OS Support
         Web: <http://www.nokia.com>";

    description
        "Nokia YANG Data model to configure mcast mgmt on SR OS based routers.

         Copyright 2016 Nokia. All rights reserved. Reproduction of this document
         is authorized on the condition that the foregoing copyright notice is included.

         This nokia-conf-mcast-mgmt YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-18";

    grouping conf-mcast-mgmt-multicast-management {
        container multicast-management {
            description "Enter the multicast-management context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list multicast-info-policy {
                key "policy-name";
                max-elements 32;
                description "Enter the multicast-info-policy list instance";

                leaf policy-name {
                    type types-sros:named-item;
                    description "Multicast information policy name";
                }

                leaf description {
                    type types-sros:description;
                    description "Text description";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                list bundle {
                    key "bundle-name";
                    max-elements 32;
                    description "Enter the bundle list instance";

                    leaf bundle-name {
                        type types-sros:named-item;
                        description "Bundle name";
                    }

                    leaf admin-bw {
                        type uint32 {
                            range "1..40000000";
                        }
                        units "kilobps";
                        description "Administrative bandwidth";
                    }

                    leaf cong-priority-threshold {
                        type uint32 {
                            range "0..7";
                        }
                        default "4";
                        description "Preference level threshold from low to high priority";
                    }

                    leaf description {
                        type types-sros:description;
                        description "Text description";
                    }

                    leaf ecmp-opt-threshold {
                        type uint32 {
                            range "0..7";
                        }
                        default "7";
                        description "ECMP threshold";
                    }

                    leaf explicit-sf-path {
                        type enumeration {
                            enum "primary"                      { value 1; }
                            enum "secondary"                    { value 2; }
                        }
                        description "Explicit ingress switch fabric multicast path";
                    }

                    leaf keepalive-override {
                        type uint32 {
                            range "10..86000";
                        }
                        units "seconds";
                        description "Keepalive timer override";
                    }

                    leaf preference {
                        type uint32 {
                            range "1..7";
                        }
                        description "Relative preference level for multicast channels";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    container bw-activity {
                        description "Enter the bw-activity context";

                        leaf bw-activity-type {
                            type enumeration {
                                enum "use-admin-bw"                 { value 1; }
                                enum "dynamic"                      { value 2; }
                            }
                            default "dynamic";
                            description "Bandwidth required by a multicast channel";
                        }

                        leaf black-hole-rate {
                            type uint32 {
                                range "1..40000000";
                            }
                            units "kilobps";
                            description "Rate that a channel is placed in the blackhole state";
                        }

                        leaf falling-delay {
                            type uint32 {
                                range "10..3600";
                            }
                            units "seconds";
                            default "30";
                            description "Falling delay threshold value until delay time expires";
                        }

                    } // container bw-activity

                    container primary-tunnel-interface {
                        description "Enter the primary-tunnel-interface context";

                        leaf sender {
                            type types-sros:ipv4-address;
                            description "Bundle set to receive from the primary tunnel interface";
                        }

                        choice p2mp {
                            case rsvp-p2mp {

                                leaf rsvp-p2mp {
                                    type types-sros:named-item;
                                    description "P2MP name for the LDP P2MP";
                                }

                            }
                            case ldp-p2mp {

                                leaf ldp-p2mp {
                                    type uint32 {
                                        range "1..4294967295";
                                    }
                                    description "ID for signaling MLDP P2MP LSP";
                                }

                            }
                        }
                    } // container primary-tunnel-interface

                    container video {
                        description "Enter the video context";

                        leaf fcc-channel-type {
                            type types-mcast-mgmt:channel-type;
                            description "Channel type for the bundle or channel";
                        }

                        leaf fcc-min-duration {
                            type uint32 {
                                range "300..8000";
                            }
                            units "milliseconds";
                            default "300";
                            description "Minimum duration of the FCC burst";
                        }

                        leaf fcc-server {
                            type boolean;
                            default "false";
                            description "Enable the FCC server for a multicast bundle";
                        }

                        leaf local-fcc-port {
                            type uint32 {
                                range "1024..5999|6251..65535";
                            }
                            default "4098";
                            description "Local port for FCC requests";
                        }

                        leaf local-rt-port {
                            type uint32 {
                                range "1024..5999|6251..65535";
                            }
                            default "4096";
                            description "Local port for RET requests";
                        }

                        leaf local-rt-server {
                            type boolean;
                            default "false";
                            description "Enable local retransmission server capability";
                        }

                        leaf reorder-audio {
                            type uint32 {
                                range "100..1000";
                            }
                            units "milliseconds";
                            description "Time the audio packets are reordered in the ad stream";
                        }

                        leaf rt-buffer-size {
                            type uint32 {
                                range "300..8000";
                            }
                            units "milliseconds";
                            default "300";
                            description "Buffer size to store channel packets";
                        }

                        leaf video-group {
                            type uint32 {
                                range "1..4";
                            }
                            description "Video group for the bundle";
                        }

                        container rt-server {
                            presence "Enter the 'rt-server' context";
                            description "Enable the rt-server context";

                            leaf ip-address {
                                type types-sros:ipv4-unicast-address;
                                mandatory true;
                                description "IP address of the upstream retransmission server";
                            }

                            leaf port {
                                type uint32 {
                                    range "1024..5999|6251..65535";
                                }
                                mandatory true;
                                description "RET server port number";
                            }

                        } // container rt-server

                        container stream-selection {
                            description "Enter the stream-selection context";

                            leaf source1 {
                                type types-sros:ipv4-address;
                                description "Primary source IP address";
                            }

                            leaf intf1 {
                                type types-sros:named-item;
                                description "Primary interface";
                            }

                            leaf source2 {
                                type types-sros:ipv4-address;
                                description "Secondary source IP address";
                            }

                            leaf intf2 {
                                type types-sros:named-item;
                                description "Secondary interface";
                            }

                        } // container stream-selection

                        container analyzer {
                            presence "Enter the 'analyzer' context";
                            description "Enable the analyzer context";

                            leaf description {
                                type types-sros:description;
                                description "Text description";
                            }

                            container alarms {
                                description "Enter the alarms context";

                                leaf cc-error {
                                    type boolean;
                                    default "false";
                                    description "Check the continuity counter";
                                }

                                leaf non-vid-pid-absent {
                                    type uint32 {
                                        range "100..5000";
                                    }
                                    units "milliseconds";
                                    description "PID checked within the specified interval";
                                }

                                leaf pat-syntax {
                                    type boolean;
                                    default "false";
                                    description "Check for PAT syntax errors";
                                }

                                leaf pid-pmt-unref {
                                    type boolean;
                                    default "false";
                                    description "Check for unreferenced PIDs in the PMT";
                                }

                                leaf pmt-syntax {
                                    type boolean;
                                    default "false";
                                    description "Check for PMT syntax errors";
                                }

                                leaf tei-set {
                                    type boolean;
                                    default "false";
                                    description "Check for TEI set errors";
                                }

                                leaf ts-sync-loss {
                                    type boolean;
                                    default "false";
                                    description "Check for synchronization loss errors";
                                }

                                leaf vid-pid-absent {
                                    type uint32 {
                                        range "100..5000";
                                    }
                                    units "milliseconds";
                                    description "VID PID checked within the specified time interval";
                                }

                                container pat-repetition {
                                    presence "Enter the 'pat-repetition' context";
                                    description "Enable the pat-repetition context";

                                    leaf tnc {
                                        type uint32 {
                                            range "100..800";
                                        }
                                        units "milliseconds";
                                        default "100";
                                        description "Time between two PATs for which a TNC alarm is raised";
                                    }

                                    leaf qos {
                                        type uint32 {
                                            range "200..900";
                                        }
                                        units "milliseconds";
                                        default "200";
                                        description "Time between two PATs for which a QoS alarm is raised";
                                    }

                                    leaf poa {
                                        type uint32 {
                                            range "300..1000";
                                        }
                                        units "milliseconds";
                                        default "500";
                                        description "Time between two PATs for which a POA alarm is raised";
                                    }

                                } // container pat-repetition

                                container pcr-repetition {
                                    presence "Enter the 'pcr-repetition' context";
                                    description "Enable the pcr-repetition context";

                                    leaf tnc {
                                        type uint32 {
                                            range "100..800";
                                        }
                                        units "milliseconds";
                                        default "100";
                                        description "Time between two PCRs for which a TNC alarm is raised";
                                    }

                                    leaf qos {
                                        type uint32 {
                                            range "200..900";
                                        }
                                        units "milliseconds";
                                        default "200";
                                        description "Time between two PCRs for which a QoS alarm is raised";
                                    }

                                    leaf poa {
                                        type uint32 {
                                            range "300..1000";
                                        }
                                        units "milliseconds";
                                        default "500";
                                        description "Time between two PCRs for which a POA alarm is raised";
                                    }

                                } // container pcr-repetition

                                container pmt-repetition {
                                    presence "Enter the 'pmt-repetition' context";
                                    description "Enable the pmt-repetition context";

                                    leaf tnc {
                                        type uint32 {
                                            range "100..4800";
                                        }
                                        units "milliseconds";
                                        default "400";
                                        description "Time between two PMTs for which a TNC alarm is raised";
                                    }

                                    leaf qos {
                                        type uint32 {
                                            range "200..4900";
                                        }
                                        units "milliseconds";
                                        default "800";
                                        description "Time between two PMTs for which a QoS alarm is raised";
                                    }

                                    leaf poa {
                                        type uint32 {
                                            range "300..5000";
                                        }
                                        units "milliseconds";
                                        default "2000";
                                        description "Time between two PMTs for which a POA alarm is raised";
                                    }

                                } // container pmt-repetition

                                container report-alarm {
                                    description "Enter the report-alarm context";

                                    leaf severity {
                                        type enumeration {
                                            enum "tnc"                          { value 1; }
                                            enum "qos"                          { value 2; }
                                            enum "poa"                          { value 3; }
                                        }
                                        description "Keyword for the type of alarm";
                                    }

                                } // container report-alarm

                            } // container alarms

                        } // container analyzer

                    } // container video

                    list channel {
                        key "start end";
                        description "Enter the channel list instance";

                        leaf start {
                            type types-sros:ip-multicast-address;
                            description "Starting IP address for the channel range";
                        }

                        leaf end {
                            type types-sros:ip-multicast-address;
                            description "Ending IP address for the channel range";
                        }

                        leaf admin-bw {
                            type uint32 {
                                range "1..40000000";
                            }
                            units "kilobps";
                            description "Administrative bandwidth";
                        }

                        leaf explicit-sf-path {
                            type enumeration {
                                enum "primary"                      { value 1; }
                                enum "secondary"                    { value 2; }
                            }
                            description "Explicit switch fabric path shared to multicast channel";
                        }

                        leaf keepalive-override {
                            type uint32 {
                                range "10..86000";
                            }
                            units "seconds";
                            description "Keepalive timer override";
                        }

                        leaf preference {
                            type uint32 {
                                range "1..7";
                            }
                            description "Relative preference level for multicast channels";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container bw-activity {
                            description "Enter the bw-activity context";

                            leaf bw-activity-type {
                                type enumeration {
                                    enum "use-admin-bw"                 { value 1; }
                                    enum "dynamic"                      { value 2; }
                                }
                                description "Bandwidth required by a multicast channel";
                            }

                            leaf black-hole-rate {
                                type uint32 {
                                    range "0..40000000";
                                }
                                units "kilobps";
                                default "0";
                                description "Rate that a channel is placed in the blackhole state";
                            }

                            leaf falling-delay {
                                type uint32 {
                                    range "10..3600";
                                }
                                units "seconds";
                                description "Falling delay threshold value until delay time expires";
                            }

                        } // container bw-activity

                        container primary-tunnel-interface {
                            description "Enter the primary-tunnel-interface context";

                            leaf sender {
                                type types-sros:ipv4-address;
                                description "Bundle set to receive from the primary tunnel interface";
                            }

                            choice p2mp {
                                case rsvp-p2mp {

                                    leaf rsvp-p2mp {
                                        type types-sros:named-item;
                                        description "P2MP name for the LDP P2MP";
                                    }

                                }
                                case ldp-p2mp {

                                    leaf ldp-p2mp {
                                        type uint32 {
                                            range "1..4294967295";
                                        }
                                        description "ID for signaling MLDP P2MP LSP";
                                    }

                                }
                            }
                        } // container primary-tunnel-interface

                        container video {
                            description "Enter the video context";

                            leaf fcc-channel-type {
                                type types-mcast-mgmt:channel-type-with-inherit;
                                description "Channel type for the bundle or channel";
                            }

                            leaf fcc-min-duration {
                                type uint32 {
                                    range "300..8000";
                                }
                                units "milliseconds";
                                description "Minimum duration of the FCC burst";
                            }

                            leaf fcc-server {
                                type types-sros:bool-with-inherit;
                                description "Value to override the parent value of the FCC server";
                            }

                            leaf local-rt-server {
                                type types-sros:bool-with-inherit;
                                description "Value to override the parent value of local RT server";
                            }

                            leaf reorder-audio {
                                type uint32 {
                                    range "100..1000";
                                }
                                units "milliseconds";
                                description "Time the audio packets are reordered in the ad stream";
                            }

                            leaf rt-buffer-size {
                                type uint32 {
                                    range "300..8000";
                                }
                                units "milliseconds";
                                default "300";
                                description "Buffer size to store channel packets";
                            }

                            leaf video-group {
                                type union {
                                    type uint32 {
                                        range "1..4";
                                    }
                                    type enumeration {
                                        enum "none"                         { value 0; }
                                    }
                                }
                                description "Video group ID";
                            }

                            container rt-server {
                                description "Enter the rt-server context";

                                leaf rt-state {
                                    type types-sros:bool-with-inherit;
                                    description "Retransmission server state";
                                }

                                leaf ip-address {
                                    type types-sros:ipv4-unicast-address;
                                    description "IP address of the upstream retransmission server";
                                }

                                leaf port {
                                    type uint32 {
                                        range "1024..5999|6251..65535";
                                    }
                                    description "UDP port to send RET requests to the upstream RET sever";
                                }

                            } // container rt-server

                            container stream-selection {
                                description "Enter the stream-selection context";

                                leaf source1 {
                                    type types-sros:ipv4-address;
                                    description "Primary source IP address";
                                }

                                leaf intf1 {
                                    type types-sros:named-item;
                                    description "Primary interface";
                                }

                                leaf source2 {
                                    type types-sros:ipv4-address;
                                    description "Secondary source IP address";
                                }

                                leaf intf2 {
                                    type types-sros:named-item;
                                    description "Secondary interface";
                                }

                            } // container stream-selection

                            container analyzer {
                                presence "Enter the 'analyzer' context";
                                description "Enable the analyzer context";

                                leaf description {
                                    type types-sros:description;
                                    description "Text description";
                                }

                                container alarms {
                                    description "Enter the alarms context";

                                    leaf cc-error {
                                        type boolean;
                                        default "false";
                                        description "Check the continuity counter";
                                    }

                                    leaf non-vid-pid-absent {
                                        type uint32 {
                                            range "100..5000";
                                        }
                                        units "milliseconds";
                                        description "PID checked within the specified interval";
                                    }

                                    leaf pat-syntax {
                                        type boolean;
                                        default "false";
                                        description "Check for PAT syntax errors";
                                    }

                                    leaf pid-pmt-unref {
                                        type boolean;
                                        default "false";
                                        description "Check for unreferenced PIDs in the PMT";
                                    }

                                    leaf pmt-syntax {
                                        type boolean;
                                        default "false";
                                        description "Check for PMT syntax errors";
                                    }

                                    leaf tei-set {
                                        type boolean;
                                        default "false";
                                        description "Check for TEI set errors";
                                    }

                                    leaf ts-sync-loss {
                                        type boolean;
                                        default "false";
                                        description "Check for synchronization loss errors";
                                    }

                                    leaf vid-pid-absent {
                                        type uint32 {
                                            range "100..5000";
                                        }
                                        units "milliseconds";
                                        description "VID PID checked within the specified time interval";
                                    }

                                    container pat-repetition {
                                        presence "Enter the 'pat-repetition' context";
                                        description "Enable the pat-repetition context";

                                        leaf tnc {
                                            type uint32 {
                                                range "100..800";
                                            }
                                            units "milliseconds";
                                            default "100";
                                            description "Time between two PATs for which a TNC alarm is raised";
                                        }

                                        leaf qos {
                                            type uint32 {
                                                range "200..900";
                                            }
                                            units "milliseconds";
                                            default "200";
                                            description "Time between two PATs for which a QoS alarm is raised";
                                        }

                                        leaf poa {
                                            type uint32 {
                                                range "300..1000";
                                            }
                                            units "milliseconds";
                                            default "500";
                                            description "Time between two PATs for which a POA alarm is raised";
                                        }

                                    } // container pat-repetition

                                    container pcr-repetition {
                                        presence "Enter the 'pcr-repetition' context";
                                        description "Enable the pcr-repetition context";

                                        leaf tnc {
                                            type uint32 {
                                                range "100..800";
                                            }
                                            units "milliseconds";
                                            default "100";
                                            description "Time between two PCRs for which a TNC alarm is raised";
                                        }

                                        leaf qos {
                                            type uint32 {
                                                range "200..900";
                                            }
                                            units "milliseconds";
                                            default "200";
                                            description "Time between two PCRs for which a QoS alarm is raised";
                                        }

                                        leaf poa {
                                            type uint32 {
                                                range "300..1000";
                                            }
                                            units "milliseconds";
                                            default "500";
                                            description "Time between two PCRs for which a POA alarm is raised";
                                        }

                                    } // container pcr-repetition

                                    container pmt-repetition {
                                        presence "Enter the 'pmt-repetition' context";
                                        description "Enable the pmt-repetition context";

                                        leaf tnc {
                                            type uint32 {
                                                range "100..4800";
                                            }
                                            units "milliseconds";
                                            default "400";
                                            description "Time between two PMTs for which a TNC alarm is raised";
                                        }

                                        leaf qos {
                                            type uint32 {
                                                range "200..4900";
                                            }
                                            units "milliseconds";
                                            default "800";
                                            description "Time between two PMTs for which a QoS alarm is raised";
                                        }

                                        leaf poa {
                                            type uint32 {
                                                range "300..5000";
                                            }
                                            units "milliseconds";
                                            default "2000";
                                            description "Time between two PMTs for which a POA alarm is raised";
                                        }

                                    } // container pmt-repetition

                                    container report-alarm {
                                        description "Enter the report-alarm context";

                                        leaf severity {
                                            type enumeration {
                                                enum "tnc"                          { value 1; }
                                                enum "qos"                          { value 2; }
                                                enum "poa"                          { value 3; }
                                            }
                                            description "Keyword for the type of alarm";
                                        }

                                    } // container report-alarm

                                } // container alarms

                            } // container analyzer

                        } // container video

                        list source-override {
                            key "ip-address";
                            description "Enter the source-override list instance";

                            leaf ip-address {
                                type types-sros:ip-unicast-address;
                                description "IP address for the source override";
                            }

                            leaf admin-bw {
                                type uint32 {
                                    range "1..40000000";
                                }
                                units "kilobps";
                                description "Administrative bandwidth";
                            }

                            leaf explicit-sf-path {
                                type enumeration {
                                    enum "primary"                      { value 1; }
                                    enum "secondary"                    { value 2; }
                                }
                                description "Explicit switch fabric path shared to multicast channel";
                            }

                            leaf keepalive-override {
                                type uint32 {
                                    range "10..86000";
                                }
                                units "seconds";
                                description "Keepalive timer override";
                            }

                            leaf preference {
                                type uint32 {
                                    range "1..7";
                                }
                                description "Relative preference level for multicast channels";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container bw-activity {
                                description "Enter the bw-activity context";

                                leaf bw-activity-type {
                                    type enumeration {
                                        enum "use-admin-bw"                 { value 1; }
                                        enum "dynamic"                      { value 2; }
                                    }
                                    description "Bandwidth required by a multicast channel";
                                }

                                leaf black-hole-rate {
                                    type uint32 {
                                        range "0..40000000";
                                    }
                                    units "kilobps";
                                    default "0";
                                    description "Rate that a channel is placed in the blackhole state";
                                }

                                leaf falling-delay {
                                    type uint32 {
                                        range "10..3600";
                                    }
                                    units "seconds";
                                    description "Falling delay threshold value until delay time expires";
                                }

                            } // container bw-activity

                            container primary-tunnel-interface {
                                description "Enter the primary-tunnel-interface context";

                                leaf sender {
                                    type types-sros:ipv4-address;
                                    description "Bundle set to receive from the primary tunnel interface";
                                }

                                choice p2mp {
                                    case rsvp-p2mp {

                                        leaf rsvp-p2mp {
                                            type types-sros:named-item;
                                            description "P2MP name for the LDP P2MP";
                                        }

                                    }
                                    case ldp-p2mp {

                                        leaf ldp-p2mp {
                                            type uint32 {
                                                range "1..4294967295";
                                            }
                                            description "ID for signaling MLDP P2MP LSP";
                                        }

                                    }
                                }
                            } // container primary-tunnel-interface

                            container video {
                                description "Enter the video context";

                                leaf fcc-channel-type {
                                    type types-mcast-mgmt:channel-type-with-inherit;
                                    description "Channel type for the bundle or channel";
                                }

                                leaf fcc-min-duration {
                                    type uint32 {
                                        range "300..8000";
                                    }
                                    units "milliseconds";
                                    description "Minimum duration of the FCC burst";
                                }

                                leaf fcc-server {
                                    type types-sros:bool-with-inherit;
                                    description "Value to override the parent value of the FCC server";
                                }

                                leaf local-rt-server {
                                    type types-sros:bool-with-inherit;
                                    description "Value to override the parent value of local RT server";
                                }

                                leaf reorder-audio {
                                    type uint32 {
                                        range "100..1000";
                                    }
                                    units "milliseconds";
                                    description "Time the audio packets are reordered in the ad stream";
                                }

                                leaf rt-buffer-size {
                                    type uint32 {
                                        range "300..8000";
                                    }
                                    units "milliseconds";
                                    default "300";
                                    description "Buffer size to store channel packets";
                                }

                                leaf video-group {
                                    type union {
                                        type uint32 {
                                            range "1..4";
                                        }
                                        type enumeration {
                                            enum "none"                         { value 0; }
                                        }
                                    }
                                    description "Video group ID";
                                }

                                container rt-server {
                                    description "Enter the rt-server context";

                                    leaf rt-state {
                                        type types-sros:bool-with-inherit;
                                        description "Retransmission server state";
                                    }

                                    leaf ip-address {
                                        type types-sros:ipv4-unicast-address;
                                        description "IP address of the upstream retransmission server";
                                    }

                                    leaf port {
                                        type uint32 {
                                            range "1024..5999|6251..65535";
                                        }
                                        description "UDP port to send RET requests to the upstream RET sever";
                                    }

                                } // container rt-server

                                container stream-selection {
                                    description "Enter the stream-selection context";

                                    leaf source1 {
                                        type types-sros:ipv4-address;
                                        description "Primary source IP address";
                                    }

                                    leaf intf1 {
                                        type types-sros:named-item;
                                        description "Primary interface";
                                    }

                                    leaf source2 {
                                        type types-sros:ipv4-address;
                                        description "Secondary source IP address";
                                    }

                                    leaf intf2 {
                                        type types-sros:named-item;
                                        description "Secondary interface";
                                    }

                                } // container stream-selection

                                container analyzer {
                                    presence "Enter the 'analyzer' context";
                                    description "Enable the analyzer context";

                                    leaf description {
                                        type types-sros:description;
                                        description "Text description";
                                    }

                                    container alarms {
                                        description "Enter the alarms context";

                                        leaf cc-error {
                                            type boolean;
                                            default "false";
                                            description "Check the continuity counter";
                                        }

                                        leaf non-vid-pid-absent {
                                            type uint32 {
                                                range "100..5000";
                                            }
                                            units "milliseconds";
                                            description "PID checked within the specified interval";
                                        }

                                        leaf pat-syntax {
                                            type boolean;
                                            default "false";
                                            description "Check for PAT syntax errors";
                                        }

                                        leaf pid-pmt-unref {
                                            type boolean;
                                            default "false";
                                            description "Check for unreferenced PIDs in the PMT";
                                        }

                                        leaf pmt-syntax {
                                            type boolean;
                                            default "false";
                                            description "Check for PMT syntax errors";
                                        }

                                        leaf tei-set {
                                            type boolean;
                                            default "false";
                                            description "Check for TEI set errors";
                                        }

                                        leaf ts-sync-loss {
                                            type boolean;
                                            default "false";
                                            description "Check for synchronization loss errors";
                                        }

                                        leaf vid-pid-absent {
                                            type uint32 {
                                                range "100..5000";
                                            }
                                            units "milliseconds";
                                            description "VID PID checked within the specified time interval";
                                        }

                                        container pat-repetition {
                                            presence "Enter the 'pat-repetition' context";
                                            description "Enable the pat-repetition context";

                                            leaf tnc {
                                                type uint32 {
                                                    range "100..800";
                                                }
                                                units "milliseconds";
                                                default "100";
                                                description "Time between two PATs for which a TNC alarm is raised";
                                            }

                                            leaf qos {
                                                type uint32 {
                                                    range "200..900";
                                                }
                                                units "milliseconds";
                                                default "200";
                                                description "Time between two PATs for which a QoS alarm is raised";
                                            }

                                            leaf poa {
                                                type uint32 {
                                                    range "300..1000";
                                                }
                                                units "milliseconds";
                                                default "500";
                                                description "Time between two PATs for which a POA alarm is raised";
                                            }

                                        } // container pat-repetition

                                        container pcr-repetition {
                                            presence "Enter the 'pcr-repetition' context";
                                            description "Enable the pcr-repetition context";

                                            leaf tnc {
                                                type uint32 {
                                                    range "100..800";
                                                }
                                                units "milliseconds";
                                                default "100";
                                                description "Time between two PCRs for which a TNC alarm is raised";
                                            }

                                            leaf qos {
                                                type uint32 {
                                                    range "200..900";
                                                }
                                                units "milliseconds";
                                                default "200";
                                                description "Time between two PCRs for which a QoS alarm is raised";
                                            }

                                            leaf poa {
                                                type uint32 {
                                                    range "300..1000";
                                                }
                                                units "milliseconds";
                                                default "500";
                                                description "Time between two PCRs for which a POA alarm is raised";
                                            }

                                        } // container pcr-repetition

                                        container pmt-repetition {
                                            presence "Enter the 'pmt-repetition' context";
                                            description "Enable the pmt-repetition context";

                                            leaf tnc {
                                                type uint32 {
                                                    range "100..4800";
                                                }
                                                units "milliseconds";
                                                default "400";
                                                description "Time between two PMTs for which a TNC alarm is raised";
                                            }

                                            leaf qos {
                                                type uint32 {
                                                    range "200..4900";
                                                }
                                                units "milliseconds";
                                                default "800";
                                                description "Time between two PMTs for which a QoS alarm is raised";
                                            }

                                            leaf poa {
                                                type uint32 {
                                                    range "300..5000";
                                                }
                                                units "milliseconds";
                                                default "2000";
                                                description "Time between two PMTs for which a POA alarm is raised";
                                            }

                                        } // container pmt-repetition

                                        container report-alarm {
                                            description "Enter the report-alarm context";

                                            leaf severity {
                                                type enumeration {
                                                    enum "tnc"                          { value 1; }
                                                    enum "qos"                          { value 2; }
                                                    enum "poa"                          { value 3; }
                                                }
                                                description "Keyword for the type of alarm";
                                            }

                                        } // container report-alarm

                                    } // container alarms

                                } // container analyzer

                            } // container video

                        } // list source-override

                    } // list channel

                } // list bundle

                container video-policy {
                    description "Enter the video-policy context";

                    list video-interface {
                        key "ip-address";
                        description "Enter the video-interface list instance";

                        leaf ip-address {
                            type types-sros:ipv4-unicast-address;
                            description "IP address of the video interface";
                        }

                        leaf subscriber-bw-limit {
                            type uint32 {
                                range "1..4294967295";
                            }
                            units "kilobps";
                            default "4294967295";
                            description "Egress bandwidth limit per subscriber";
                        }

                        leaf rt-payload-type {
                            type uint32 {
                                range "33|96..127";
                            }
                            default "99";
                            description "Format for the received retransmission packets";
                        }

                        leaf max-sessions {
                            type uint32 {
                                range "1..65536";
                            }
                            default "256";
                            description "Maximum number of sessions per client";
                        }

                        leaf max-igmp-latency {
                            type uint32 {
                                range "10..1000";
                            }
                            units "milliseconds";
                            default "100";
                            description "Maximum IGMP latency per client";
                        }

                        leaf fcc-session-timeout {
                            type uint32 {
                                range "5..300";
                            }
                            units "seconds";
                            default "300";
                            description "FCC session timeout";
                        }

                        leaf ret-session-timeout {
                            type uint32 {
                                range "5..300";
                            }
                            units "seconds";
                            default "300";
                            description "RET session timeout";
                        }

                        leaf rt-rate {
                            type types-mcast-mgmt:percent-without-zero;
                            default "5";
                            description "Rate the RET packets are sent to client";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container hd {
                            description "Enter the hd context";

                            leaf dent-threshold {
                                type uint32 {
                                    range "1..31";
                                }
                                default "16";
                                description "Threshold below which the FCC server dents unicast data";
                            }

                            leaf fcc-burst {
                                type uint32 {
                                    range "0..600";
                                }
                                units "percent";
                                default "25";
                                description "Burst rate FCC server sends unicast data to FCC client";
                            }

                            leaf local-rt-server {
                                type boolean;
                                default "false";
                                description "Enable local retransmission server capability";
                            }

                            leaf rt-rate {
                                type types-mcast-mgmt:percent-without-zero;
                                default "5";
                                description "Rate the RET packets are sent to client";
                            }

                            leaf mc-handover {
                                type types-sros:percent;
                                default "25";
                                description "Rate the FCC server sends data during the handover";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container fcc-server {
                                description "Enter the fcc-server context";

                                leaf mode {
                                    type types-mcast-mgmt:mode;
                                    description "Mode the FCC server sends information to the client";
                                }

                            } // container fcc-server

                        } // container hd

                        container pip {
                            description "Enter the pip context";

                            leaf dent-threshold {
                                type uint32 {
                                    range "1..31";
                                }
                                default "16";
                                description "Threshold below which the FCC server dents unicast data";
                            }

                            leaf fcc-burst {
                                type uint32 {
                                    range "0..600";
                                }
                                units "percent";
                                default "25";
                                description "Burst rate FCC server sends unicast data to FCC client";
                            }

                            leaf local-rt-server {
                                type boolean;
                                default "false";
                                description "Enable local retransmission server capability";
                            }

                            leaf rt-rate {
                                type types-mcast-mgmt:percent-without-zero;
                                default "5";
                                description "Rate the RET packets are sent to client";
                            }

                            leaf mc-handover {
                                type uint32 {
                                    range "0..600";
                                }
                                units "percent";
                                default "25";
                                description "Rate the FCC server sends data during the handover";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container fcc-server {
                                description "Enter the fcc-server context";

                                leaf mode {
                                    type types-mcast-mgmt:mode;
                                    description "Mode the FCC server sends information to the client";
                                }

                            } // container fcc-server

                        } // container pip

                        container sd {
                            description "Enter the sd context";

                            leaf dent-threshold {
                                type uint32 {
                                    range "1..31";
                                }
                                default "16";
                                description "Threshold below which the FCC server dents unicast data";
                            }

                            leaf fcc-burst {
                                type uint32 {
                                    range "0..600";
                                }
                                units "percent";
                                default "25";
                                description "Burst rate FCC server sends unicast data to FCC client";
                            }

                            leaf local-rt-server {
                                type boolean;
                                default "false";
                                description "Enable local retransmission server capability";
                            }

                            leaf rt-rate {
                                type types-mcast-mgmt:percent-without-zero;
                                default "5";
                                description "Rate the RET packets are sent to client";
                            }

                            leaf mc-handover {
                                type uint32 {
                                    range "0..600";
                                }
                                units "percent";
                                default "25";
                                description "Rate the FCC server sends data during the handover";
                            }

                            leaf-list apply-groups {
                                type leafref {
                                    path "../../../../../../groups/group/name";
                                }
                                max-elements 8;
                                ordered-by user;
                                description "Apply a configuration group at this level";
                            }

                            leaf-list apply-groups-exclude {
                                type leafref {
                                    path "../../../../../../groups/group/name";
                                }
                                max-elements 8;
                                ordered-by user;
                                description "Exclude a configuration group at this level";
                            }

                            container fcc-server {
                                description "Enter the fcc-server context";

                                leaf mode {
                                    type types-mcast-mgmt:mode;
                                    description "Mode the FCC server sends information to the client";
                                }

                            } // container fcc-server

                        } // container sd

                    } // list video-interface

                } // container video-policy

            } // list multicast-info-policy

            list multicast-reporting-destination {
                key "name";
                description "Enter the multicast-reporting-destination list instance";

                leaf name {
                    type types-sros:named-item;
                    description "Multicast reporting destination name";
                }

                leaf description {
                    type types-sros:description;
                    description "Text description";
                }

                leaf admin-state {
                    type types-sros:admin-state;
                    default "disable";
                    description "Administrative state of multicast reporting destination";
                }

                leaf address {
                    type types-sros:ipv4-address;
                    default "0.0.0.0";
                    description "IP address of the multicast reporting destination";
                }

                leaf udp-port {
                    type types-sros:tcp-udp-port {
                        range "1..65535";
                    }
                    default "1037";
                    description "UDP port where multicast reports are sent";
                }

                leaf maximum-transmission-delay {
                    type uint32 {
                        range "0..100";
                    }
                    units "deciseconds";
                    default "1";
                    description "Time delay before packet transmits to the destination";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

            } // list multicast-reporting-destination

            list bandwidth-policy {
                key "policy-name";
                max-elements 32;
                description "Enter the bandwidth-policy list instance";

                leaf policy-name {
                    type types-sros:named-item;
                    description "Bandwidth policy name";
                }

                leaf admin-bw-threshold {
                    type uint32 {
                        range "1..40000000";
                    }
                    units "kilobps";
                    default "10";
                    description "Administrative bandwidth threshold";
                }

                leaf description {
                    type types-sros:description;
                    description "Text description";
                }

                leaf falling-percent-reset {
                    type types-mcast-mgmt:percent-without-zero;
                    default "50";
                    description "Percent of bandwidth that decreases before resetting";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container mcast-pool {
                    description "Enter the mcast-pool context";

                    leaf percent-of-total {
                        type uint32 {
                            range "1..50";
                        }
                        units "percent";
                        default "10";
                        description "Percent of ingress buffers assigned to multicast pool";
                    }

                    leaf resv-cbs {
                        type types-mcast-mgmt:percent-without-zero;
                        default "50";
                        description "Percentage of pool reserved for multicast path queues";
                    }

                    leaf slope-policy {
                        type leafref {
                            path "../../../../qos/slope-policy/slope-policy-name";
                        }
                        description "Slope policy name";
                    }

                } // container mcast-pool

                container impm-paths {
                    description "Enter the impm-paths context";

                    container primary-path {
                        description "Enter the primary-path context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container queue-parameters {
                            description "Enter the queue-parameters context";

                            leaf cbs {
                                type decimal64 {
                                    range "0.00..100.00";
                                    fraction-digits 2;
                                }
                                units "percent";
                                default "5.00";
                                description "Override for default CBS for single queue for each path";
                            }

                            leaf mbs {
                                type decimal64 {
                                    range "0.00..100.00";
                                    fraction-digits 2;
                                }
                                units "percent";
                                default "7.00";
                                description "Override for default MBS for single queue for each path";
                            }

                            container drop-tail {
                                description "Enter the drop-tail context";

                                container low {
                                    description "Enter the low context";

                                    leaf percent-reduction-from-mbs {
                                        type types-sros:percent;
                                        default "10";
                                        description "Low drop-tail percent from MBS that is reduced";
                                    }

                                } // container low

                            } // container drop-tail

                        } // container queue-parameters

                    } // container primary-path

                    container secondary-path {
                        description "Enter the secondary-path context";

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                        container number-paths {
                            description "Enter the number-paths context";

                            leaf number-of-paths {
                                type uint32 {
                                    range "1..15";
                                }
                                default "1";
                                description "Number of secondary paths";
                            }

                            leaf redundant-sfm {
                                type uint32 {
                                    range "1..15";
                                }
                                default "1";
                                description "Number of secondary paths in redundant SFM mode";
                            }

                        } // container number-paths

                        container queue-parameters {
                            description "Enter the queue-parameters context";

                            leaf cbs {
                                type decimal64 {
                                    range "0.00..100.00";
                                    fraction-digits 2;
                                }
                                units "percent";
                                default "30.00";
                                description "Override for default CBS for single queue for each path";
                            }

                            leaf mbs {
                                type decimal64 {
                                    range "0.00..100.00";
                                    fraction-digits 2;
                                }
                                units "percent";
                                default "40.00";
                                description "Override for default MBS for single queue for each path";
                            }

                            container drop-tail {
                                description "Enter the drop-tail context";

                                container low {
                                    description "Enter the low context";

                                    leaf percent-reduction-from-mbs {
                                        type types-sros:percent;
                                        default "10";
                                        description "Low drop-tail percent from MBS that is reduced";
                                    }

                                } // container low

                            } // container drop-tail

                        } // container queue-parameters

                    } // container secondary-path

                } // container impm-paths

            } // list bandwidth-policy

            container chassis-level {
                description "Enter the chassis-level context";

                leaf mmrp-impm-override {
                    type boolean;
                    default "false";
                    description "Manage MMRP traffic by IMPM";
                }

                leaf round-robin-inactive-records {
                    type boolean;
                    default "false";
                    description "Redistribute newly populated inactive records";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container per-mcast-plane-capacity {
                    description "Enter the per-mcast-plane-capacity context";

                    leaf total-capacity {
                        type enumeration {
                            enum "dynamic"                      { value 0; }
                            enum "2000"                         { value 2000; }
                            enum "4000"                         { value 4000; }
                            enum "5250"                         { value 5250; }
                            enum "8250"                         { value 8250; }
                            enum "15000"                        { value 15000; }
                            enum "17000"                        { value 17000; }
                            enum "19000"                        { value 19000; }
                            enum "16500"                        { status obsolete; }
                        }
                        units "megabps";
                        description "Total multicast plane bandwidth";
                    }

                    container mcast-capacity {
                        description "Enter the mcast-capacity context";

                        leaf primary-percentage {
                            type decimal64 {
                                range "0.01..100.00";
                                fraction-digits 2;
                            }
                            units "percent";
                            description "Percent of plane capacity for primary multicast planes";
                        }

                        leaf secondary-percentage {
                            type decimal64 {
                                range "0.01..100.00";
                                fraction-digits 2;
                            }
                            units "percent";
                            description "Percent of plane capacity for secondary multicast plane";
                        }

                    } // container mcast-capacity

                    container redundant-mcast-capacity {
                        description "Enter the redundant-mcast-capacity context";

                        leaf primary-percentage {
                            type decimal64 {
                                range "0.01..100.00";
                                fraction-digits 2;
                            }
                            units "percent";
                            description "Percent of plane capacity for primary multicast planes";
                        }

                        leaf secondary-percentage {
                            type decimal64 {
                                range "0.01..100.00";
                                fraction-digits 2;
                            }
                            units "percent";
                            description "Percent of plane capacity for secondary multicast plane";
                        }

                    } // container redundant-mcast-capacity

                } // container per-mcast-plane-capacity

            } // container chassis-level

        } // container multicast-management

    } // grouping conf-mcast-mgmt-multicast-management

}
