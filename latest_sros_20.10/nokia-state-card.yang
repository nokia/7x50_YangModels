submodule nokia-state-card {

    yang-version "1.1";

    belongs-to nokia-state { prefix "state"; }

    import ietf-yang-types                { prefix "yang"; }
    import nokia-sros-yang-extensions     { prefix "sros-ext"; }
    import nokia-types-card               { prefix "types-card"; }
    import nokia-types-services           { prefix "types-services"; }
    import nokia-types-sros               { prefix "types-sros"; }
    import nokia-types-subscriber-mgmt    { prefix "types-submgt"; }

    include nokia-state-card-fp;

    sros-ext:sros-major-release "rel20";

    organization "Nokia";

    contact
        "Nokia SR OS Support
         Web: <http://www.nokia.com>";

    description
        "Nokia YANG Data model with operational state for cards on SR OS based routers.

         Copyright 2016 Nokia. All rights reserved. Reproduction of this document
         is authorized on the condition that the foregoing copyright notice is included.

         This nokia-state-card YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-02-19";

    grouping state-card {
        list card {
            key "slot-number";
            description "Enter the card list instance";

            leaf slot-number {
                type types-card:iom-card-slot;
                description "IOM slot number within the chassis";
            }

            leaf equipped-type {
                type types-card:sros-iom-type-state;
                description "Indicates the card type that is physically inserted into the slot.";
            }

            leaf clock-source {
                type string {
                    length "0..80";
                }
                description "Indicates the clock source of the card.";
            }

            leaf available-mda-slots {
                type uint32;
                description "Indicates the number of MDA slots available on the card.";
            }

            leaf installed-mda-slots {
                type uint32;
                description "Indicates the number of MDA slots installed on the card.";
            }

            leaf installed-xiom-slots {
                type uint32;
                description "Indicates the number of XIOM slots installed on the card.";
            }

            leaf memory-size {
                type uint32;
                description "Indicates the amount of memory populated on the card.";
            }

            leaf last-bootup-reason {
                type enumeration {
                    enum "hard-reboot"                  { value 0; }
                    enum "soft-reset"                   { value 1; }
                    enum "power-cycle"                  { value 2; }
                    enum "clear-card"                   { value 3; }
                    enum "activity-switch"              { value 4; }
                    enum "config-change"                { value 5; }
                    enum "runtime-failure"              { value 6; }
                    enum "boot-failure"                 { value 7; }
                    enum "unexpected"                   { value 8; }
                    enum "issu-timeout"                 { value 9; }
                    enum "reinserted"                   { value 10; }
                    enum "issu-hard-reboot"             { value 11; }
                    enum "ccm-failure"                  { value 12; }
                    enum "power-change"                 { value 13; }
                    enum "level-change"                 { value 14; }
                    enum "sfm-fail-recovery"            { value 15; }
                }
                description "Indicates the reason for the last reboot/reset of the card.";
            }

            leaf equipped-level {
                type types-card:sros-iom-level-state;
                description "Indicates the functional level of the card that is physically inserted into the slot.";
            }

            leaf licensed-level {
                type types-card:sros-iom-level-state;
                description "Indicates the card level that is licensed in this slot.";
            }

            leaf licensed-bandwidth {
                type uint32;
                description "Indicates the amount of bandwidth licensed in this slot.";
            }

            list event {
                key "type";
                description "Enter the event list instance";

                leaf type {
                    type enumeration {
                        enum "soft-error"                   { value 1; }
                    }
                    description "Unique identifier for the card event type to monitor";
                }

                leaf occurrences {
                    type yang:counter64;
                    description "Indicates the number of times this event has been detected.";
                }

                leaf last-occurrence {
                    type yang:date-and-time;
                    description "Indicates the timestamp of the last time the event was detected.";
                }

            } // list event

            container hardware-data {
                description "Enter the hardware-data context";

                leaf part-number {
                    type string {
                        length "0..32";
                    }
                    description "Indicates the part number information.";
                }

                leaf serial-number {
                    type string {
                        length "0..32";
                    }
                    description "Indicates the serial number of the hardware component.";
                }

                leaf manufacturing-date {
                    type string {
                        length "0..8";
                    }
                    description "Indicates the manufacturing date of the hardware component.";
                }

                leaf common-language-equipment-identifier {
                    type string {
                        length "0..10";
                    }
                    description "Indicates the CLEI, a unique 10-character identifier fixed by the manufacturer.";
                }

                leaf field-replaceable-unit {
                    type boolean;
                    description "Indicates whether the hardware component is a field replaceable unit or not.";
                }

                leaf contained-in {
                    type types-sros:named-item-or-empty;
                    description "Indicates the hardware component that contains this component. An empty string indicates that this component is not contained in any other component.";
                }

                leaf oper-state {
                    type enumeration {
                        enum "unknown"                      { value 1; }
                        enum "in-service"                   { value 2; }
                        enum "out-of-service"               { value 3; }
                        enum "diagnosing"                   { value 4; }
                        enum "failed"                       { value 5; }
                        enum "booting"                      { value 6; }
                        enum "empty"                        { value 7; }
                        enum "provisioned"                  { value 8; }
                        enum "unprovisioned"                { value 9; }
                        enum "upgrade"                      { value 10; }
                        enum "downgrade"                    { value 11; }
                        enum "in-service-upgrade"           { value 12; }
                        enum "in-service-downgrade"         { value 13; }
                        enum "reset-pending"                { value 14; }
                        enum "soft-reset"                   { value 15; }
                        enum "pre-extension"                { value 16; }
                        enum "downloading"                  { value 17; }
                    }
                    description "Indicates the operational status of the hardware component.";
                }

                leaf failure-reason {
                    type string {
                        length "0..255";
                    }
                    description "Indicates the reason why a hardware component 'failed' as indicated in oper-state.";
                }

                leaf contains-temperature-sensor {
                    type boolean;
                    description "Indicates whether or not this hardware component contains a temperature sensor.";
                }

                leaf temperature {
                    type int32;
                    description "Indicates the current temperature in degrees celsius from the temperature sensor.";
                }

                leaf temperature-threshold {
                    type int32;
                    description "Indicates the temperature threshold for this hardware component in degrees celsius.";
                }

                leaf alarm-state {
                    type enumeration {
                        enum "unknown"                      { value 0; }
                        enum "alarm-active"                 { value 1; }
                        enum "alarm-cleared"                { value 2; }
                    }
                    description "Indicates the current alarm state for this hardware component.";
                }

                leaf manufacturing-deviations {
                    type string {
                        length "0..255";
                    }
                    description "Indicates the record of changes done by the manfacturing to the hardware or software which is outside the normal revision control process.";
                }

                leaf equipped-platform-type {
                    type enumeration {
                        enum "platform-unknown"             { value 0; }
                        enum "platform-7750"                { value 1; }
                        enum "platform-7450"                { value 2; }
                        enum "platform-7710"                { value 3; }
                        enum "platform-7950"                { value 4; }
                        enum "platform-7705"                { value 5; }
                        enum "platform-7250"                { value 6; }
                    }
                    description "Indicates the platform type of the installed hardware component, as read from the EEPROM.";
                }

                leaf manufacturing-assembly-number {
                    type string {
                        length "0..32";
                    }
                    description "Indicates an assembly number indicating manufacturing differences for a given part number.";
                }

                leaf power-zone-location {
                    type uint32 {
                        range "0..32";
                    }
                    description "Indicates the managed power zone that this hardware component resides.";
                }

                leaf base-mac-address {
                    type yang:mac-address;
                    description "Indicates the base MAC address of the hardware component.";
                }

                leaf boot-code-version {
                    type string {
                        length "0..255";
                    }
                    description "Indicates the version number of boot eprom.";
                }

                leaf software-code-version {
                    type string {
                        length "0..255";
                    }
                    description "Indicates the software product release version number for the software image currently running.";
                }

                leaf software-last-boot-time {
                    type yang:date-and-time;
                    description "This indicates the date and time the software running on this hardware component was last rebooted.";
                }

                leaf software-image-source {
                    type enumeration {
                        enum "unknown"                      { value 0; }
                        enum "primary"                      { value 1; }
                        enum "secondary"                    { value 2; }
                        enum "tertiary"                     { value 3; }
                    }
                    description "Indicates the location in the Boot Options File (BOF) where the software image file was found when the system last rebooted.";
                }

                leaf firmware-code-version {
                    type string {
                        length "0..255";
                    }
                    description "Indicates the software product release version number associated with the firmware version currently programmed.";
                }

                leaf firmware-revision-status {
                    type enumeration {
                        enum "not-applicable"               { value 0; }
                        enum "acceptable"                   { value 1; }
                        enum "not-acceptable"               { value 2; }
                        enum "upgrade-pending"              { value 3; }
                        enum "upgrading"                    { value 4; }
                        enum "upgrade-next-hard-reset"      { value 5; }
                    }
                    description "Indicates the firmware/FPGA revision status for the hardware component.";
                }

            } // container hardware-data

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

            } // container subscriber-management

            list mda {
                key "mda-slot";
                description "Enter the mda list instance";

                leaf mda-slot {
                    type uint32 {
                        range "1..6";
                    }
                    description "MDA slot";
                }

                leaf equipped-type {
                    type types-card:sros-mda-type-state;
                    description "Indicates the MDA type that is physically inserted into the slot.";
                }

                leaf maximum-ports {
                    type int32;
                    description "Indicates the maximum number of ports or connectors that can be equipped on the MDA.";
                }

                leaf equipped-ports {
                    type uint32;
                    description "Indicates the number of ports or connectors equipped on the MDA.";
                }

                leaf transmit-timing-selected {
                    type enumeration {
                        enum "cpm-a"                        { value 1; }
                        enum "cpm-b"                        { value 2; }
                        enum "local"                        { value 3; }
                        enum "holdover"                     { value 4; }
                        enum "not-applicable"               { value 5; }
                        enum "cpm-c"                        { value 6; }
                        enum "cpm-d"                        { value 7; }
                    }
                    description "Indicates the trasnmit timing method that is selected and being used by the MDA.";
                }

                leaf sync-if-timing-status {
                    type enumeration {
                        enum "qualified"                    { value 1; }
                        enum "not-qualified"                { value 2; }
                        enum "not-applicable"               { value 3; }
                    }
                    description "State of synchronous timing subsystem used by the MDA";
                }

                leaf capabilities {
                    type bits {
                        bit ethernet                       { position 0; }
                        bit sonet                          { position 1; }
                        bit tdm                            { position 2; }
                        bit ppp                            { position 3; }
                        bit fr                             { position 4; }
                        bit atm                            { position 5; }
                        bit chdlc                          { position 6; }
                        bit cma                            { position 7; }
                        bit cem                            { position 8; }
                        bit serial                         { position 9; }
                        bit wireless                       { position 10; }
                        bit cellular                       { position 11; }
                    }
                    description "Indicates the capabilities of the MDA.";
                }

                leaf minimum-channelization {
                    type types-card:mda-channel-type;
                    description "Indicates the minimum size of the channel that can exist on the MDA.";
                }

                leaf maximum-channelization {
                    type types-card:mda-channel-type;
                    description "Indicates the maximum size of the channel that can exist on the MDA.";
                }

                leaf maximum-channels {
                    type uint32;
                    description "Indicates the total number of leaf SONET paths, TDM channels, and bundles on the MDA that may be configured to pass traffic.";
                }

                leaf channels-in-use {
                    type uint32;
                    description "Indicates the number of leaf SONET paths, TDM channels, and bundles on the MDA which are in use.";
                }

                leaf high-bandwidth-multicast-taps {
                    type uint32;
                    description "Indicates the number of high bandwidth multicast traffic taps on the MDA.";
                }

                leaf equipped-level {
                    type types-card:sros-mda-level-state;
                    description "Indicates the functional level of the MDA that is physically inserted into the slot.";
                }

                leaf licensed-level {
                    type types-card:sros-mda-level-state;
                    description "Indicates the MDA level that is licensed for the slot.";
                }

                leaf licensed-bandwidth {
                    type uint32;
                    description "Indicates the bandwidth that has been licensed (used) for the slot.";
                }

                container access {
                    description "Enter the access context";

                    container ingress {
                        description "Enter the ingress context";

                        container mc-path-mgmt-pool {
                            description "Enter the mc-path-mgmt-pool context";

                            leaf amber-alarm-threshold {
                                type uint32;
                                units "percent";
                                description "Indicates the amber alarm threshold allowed on over-subscription.";
                            }

                            leaf red-alarm-threshold {
                                type uint32;
                                units "percent";
                                description "Indicates red alarm threshold allowed on over-subscription.";
                            }

                            leaf slope-policy {
                                type types-sros:named-item;
                                description "Indicates the slope policy.";
                            }

                            container resv-cbs {
                                description "Enter the resv-cbs context";

                                leaf cbs {
                                    type int32;
                                    description "Indicates the percentage of pool size reserved for CBS. The value '-1' means 30%.";
                                }

                                container amber-alarm-action {
                                    description "Enter the amber-alarm-action context";

                                    leaf step {
                                        type uint32;
                                        units "percent";
                                        description "Indicates the step-size percentage for the reserved CBS size of the pool. When set to a value of zero (0), the adaptive CBS sizing is disabled. To enable adaptive CBS sizing, both this leaf and amber-alarm-action/max must be set to non-default values. When resv-cbs is set to 'default', adaptive CBS sizing cannot be enabled.";
                                    }

                                    leaf max {
                                        type uint32;
                                        units "percent";
                                        description "Indicates the maximum percentage for the reserved CBS size of the pool. When set to a value of zero (0), the adaptive CBS sizing is disabled. To enable adaptive CBS sizing, both this leaf and amber-alarm-action/step must be set to non-default values. When resv-cbs is set to 'default', adaptive CBS sizing cannot be enabled. This value must not be more than resv-cbs.";
                                    }

                                } // container amber-alarm-action

                            } // container resv-cbs

                        } // container mc-path-mgmt-pool

                    } // container ingress

                } // container access

                list event {
                    key "type";
                    description "Enter the event list instance";

                    leaf type {
                        type enumeration {
                            enum "soft-error"                   { value 1; }
                            enum "internal-frame-loss"          { value 2; }
                            enum "memory-error"                 { value 3; }
                        }
                        description "MDA event type to be monitored";
                    }

                    leaf occurrences {
                        type yang:counter64;
                        description "Indicates the number of times this event has been detected.";
                    }

                    leaf last-occurrence {
                        type yang:date-and-time;
                        description "Indicates the timestamp of the last time the event was detected.";
                    }

                } // list event

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf contained-in {
                        type types-sros:named-item-or-empty;
                        description "Indicates the hardware component that contains this component. An empty string indicates that this component is not contained in any other component.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf contains-temperature-sensor {
                        type boolean;
                        description "Indicates whether or not this hardware component contains a temperature sensor.";
                    }

                    leaf temperature {
                        type int32;
                        description "Indicates the current temperature in degrees celsius from the temperature sensor.";
                    }

                    leaf temperature-threshold {
                        type int32;
                        description "Indicates the temperature threshold for this hardware component in degrees celsius.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf power-zone-location {
                        type uint32 {
                            range "0..32";
                        }
                        description "Indicates the managed power zone that this hardware component resides.";
                    }

                    leaf base-mac-address {
                        type yang:mac-address;
                        description "Indicates the base MAC address of the hardware component.";
                    }

                    leaf boot-code-version {
                        type string {
                            length "0..255";
                        }
                        description "Indicates the version number of boot eprom.";
                    }

                    leaf software-code-version {
                        type string {
                            length "0..255";
                        }
                        description "Indicates the software product release version number for the software image currently running.";
                    }

                    leaf software-last-boot-time {
                        type yang:date-and-time;
                        description "This indicates the date and time the software running on this hardware component was last rebooted.";
                    }

                    leaf software-image-source {
                        type enumeration {
                            enum "unknown"                      { value 0; }
                            enum "primary"                      { value 1; }
                            enum "secondary"                    { value 2; }
                            enum "tertiary"                     { value 3; }
                        }
                        description "Indicates the location in the Boot Options File (BOF) where the software image file was found when the system last rebooted.";
                    }

                    leaf firmware-code-version {
                        type string {
                            length "0..255";
                        }
                        description "Indicates the software product release version number associated with the firmware version currently programmed.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

                container subscriber-management {
                    description "Enter the subscriber-management context";

                    container statistics {
                        description "Enter the statistics context";

                        leaf last-reset-peak-values {
                            type yang:date-and-time;
                            description "Timestamp of the last reset of the peak values";
                        }

                        list ipv4-hosts {
                            key "counter";
                            description "Enter the ipv4-hosts list instance";

                            leaf counter {
                                type types-submgt:submgt-statistics-ipv4-type;
                                description "Type of submgt ipv4 hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list ipv4-hosts

                        list ipv6-hosts {
                            key "counter";
                            description "Enter the ipv6-hosts list instance";

                            leaf counter {
                                type types-submgt:submgt-statistics-ipv6-type;
                                description "Type of submgt ipv6 hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list ipv6-hosts

                        list total-hosts {
                            key "counter";
                            description "Enter the total-hosts list instance";

                            leaf counter {
                                type types-submgt:submgt-statistics-total-type;
                                description "Type of submgt total hosts counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list total-hosts

                        list sessions {
                            key "counter";
                            description "Enter the sessions list instance";

                            leaf counter {
                                type types-submgt:submgt-statistics-session-type;
                                description "Type of submgt sessions counter";
                            }

                            leaf current-value {
                                type uint32;
                                description "Current value of submgt counter";
                            }

                            leaf peak-value {
                                type uint32;
                                description "Peak value of submgt counter";
                            }

                            leaf peak-timestamp {
                                type yang:date-and-time;
                                description "Peak timestamp of submgt counter";
                            }

                        } // list sessions

                    } // container statistics

                } // container subscriber-management

                container isa-tunnel {
                    description "Enter the isa-tunnel context";

                    leaf cryptographic-accelerator {
                        type string {
                            length "1..64";
                        }
                        description "The cryptographic accelerator information.";
                    }

                    container ipsec {
                        description "Enter the ipsec context";

                        list lockout-client {
                            key "public-service local-gateway-address address port";
                            description "Enter the lockout-client list instance";

                            leaf public-service {
                                type types-services:service-name;
                                description "The value of router-service-name is 'Base' for IES services. The value of router-service-name is the name of the service for VPRN services.";
                            }

                            leaf local-gateway-address {
                                type types-sros:ip-address;
                                description "The IP address of the local SAP IPsec gateway.";
                            }

                            leaf address {
                                type types-sros:ip-address;
                                description "The IP address of the lockout client.";
                            }

                            leaf port {
                                type union {
                                    type enumeration {
                                        enum "all"                          { value 0; description "all ports under the lockout client address are locked out"; }
                                    }
                                    type types-sros:tcp-udp-port-non-zero;
                                }
                                description "The port number of the lockout client. The value 'all' means that all ports under the lockout client address are locked out.";
                            }

                            leaf lockout {
                                type boolean;
                                description "Indicates whether a client is locked out by the system. The value of 'true' indicates that the client is locked out and all IKE traffics from this client are rejected by the system. The value of 'false' indicates that the system still accepts IKE traffic from this client but the client has failed on certain IKE authentications.";
                            }

                            leaf remaining-block-time {
                                type union {
                                    type enumeration {
                                        enum "infinite"                     { value 0; description "the client will never be unblocked"; }
                                    }
                                    type types-sros:time-duration {
                                        range "1..max";
                                    }
                                }
                                description "The time remaining until this client is unblocked. A value of 'infinite' indicates that this client will never be unblocked.";
                            }

                            container statistics {
                                description "Enter the statistics context";

                                leaf failed-attempts {
                                    type yang:counter32;
                                    description "The number of failed authentication attempts from the lockout client within the lockout duration.";
                                }

                                leaf dropped-packets {
                                    type yang:counter32;
                                    description "The number of dropped packets for the lockout client.";
                                }

                            } // container statistics

                        } // list lockout-client

                    } // container ipsec

                    container statistics {
                        description "Enter the statistics context";

                        container datapath {
                            description "Enter the datapath context";

                            leaf encrypted-packets {
                                type yang:counter64;
                                description "The number of packets encrypted by the IPsec data path";
                            }

                            leaf encrypted-bytes {
                                type yang:counter64;
                                description "The number of bytes encrypted by the IPsec data path";
                            }

                            leaf decrypted-packets {
                                type yang:counter64;
                                description "The number of packets decrypted by the IPsec data path";
                            }

                            leaf decrypted-bytes {
                                type yang:counter64;
                                description "The number of bytes decrypted by the IPsec data path";
                            }

                            leaf outbound-dropped-packets {
                                type yang:counter64;
                                description "The number of packets dropped before and during outbound (encryption) processing by the IPsec data path.";
                            }

                            leaf outbound-sa-misses {
                                type yang:counter64;
                                description "The number of packets dropped before outbound (encryption) processing by the IPsec data path due to no SA (security association) present.";
                            }

                            leaf outbound-policy-entry-misses {
                                type yang:counter32;
                                description "The number of packets dropped before outbound (encryption) processing by the IPsec data path due to no matching Policy Entry.";
                            }

                            leaf inbound-dropped-packets {
                                type yang:counter64;
                                description "The number of packets dropped before and during inbound (decryption) processing by the IPsec data path.";
                            }

                            leaf inbound-sa-misses {
                                type yang:counter64;
                                description "The number of packets dropped before inbound (decryption) processing by the IPsec data path due to no SA (security association) present.";
                            }

                            leaf inbound-ip-dst-src-mismatches {
                                type yang:counter32;
                                description "The the number of packets dropped before inbound (decryption) processing by the IPsec data path due to the received packet's outer IP destination or source address does not match the Tunnel's local or peer gateway address.";
                            }

                            leaf transmit-packet-errors {
                                type yang:counter32;
                                description "The number of packets transmit failures by the IPsec data path.";
                            }

                            leaf fragments-received {
                                type yang:counter64;
                                description "The number of fragments received by the IPsec data path.";
                            }

                            leaf reassembled-packets {
                                type yang:counter64;
                                description "The number of packets reassembled by the IPsec data path.";
                            }

                            leaf fragment-timeout-drops {
                                type yang:counter64;
                                description "The number of fragments dropped due to timeout by the IPsec data path.";
                            }

                            leaf fragments-total-drops {
                                type yang:counter64;
                                description "The number of total fragments dropped by the IPsec data path.";
                            }

                            leaf drop-too-big-df-set-packets {
                                type yang:counter64;
                                description "The number of packets with DF bit set dropped in this Tunnel exceeding MTU size and with clear tunnel DF bit not set.";
                            }

                            container gre-ip-tnl {
                                description "Enter the gre-ip-tnl context";

                                leaf received-packets {
                                    type yang:counter64;
                                    description "The number of packets received by the GRE tunnel data path.";
                                }

                                leaf received-bytes {
                                    type yang:counter64;
                                    description "The number of bytes received by the GRE tunnel data path.";
                                }

                                leaf received-errors {
                                    type yang:counter64;
                                    description "The number of packets dropped while receiving by the GRE tunnel data path";
                                }

                                leaf sent-packets {
                                    type yang:counter64;
                                    description "The number of packets transmitted by the GRE tunnel data path.";
                                }

                                leaf sent-bytes {
                                    type yang:counter64;
                                    description "The number of bytes transmitted by the GRE tunnel data path.";
                                }

                                leaf sent-errors {
                                    type yang:counter64;
                                    description "The number of packets dropped while transmitting by the GRE tunnel data path";
                                }

                            } // container gre-ip-tnl

                            container l2tpv3-tnl {
                                description "Enter the l2tpv3-tnl context";

                                leaf received-packets {
                                    type yang:counter64;
                                    description "The number of packets received by the L2TPv3 tunnel data path.";
                                }

                                leaf received-bytes {
                                    type yang:counter64;
                                    description "The number of bytes received by the L2TPv3 tunnel data path.";
                                }

                                leaf received-errors {
                                    type yang:counter64;
                                    description "The number of packets dropped while receiving by the L2TPv3 tunnel data path";
                                }

                                leaf sent-packets {
                                    type yang:counter64;
                                    description "The number of packets transmitted by the L2TPv3 tunnel data path.";
                                }

                                leaf sent-bytes {
                                    type yang:counter64;
                                    description "The number of bytes transmitted by the L2TPv3 tunnel data path.";
                                }

                                leaf sent-errors {
                                    type yang:counter64;
                                    description "The number of packets dropped while transmitting by the L2TPv3 tunnel data path.";
                                }

                            } // container l2tpv3-tnl

                        } // container datapath

                        container control {
                            description "Enter the control context";

                            leaf static-ipsec-tunnels {
                                type yang:counter32;
                                description "The number of configured static IPsec tunnels on the MDA.";
                            }

                            leaf dynamic-ipsec-tunnels {
                                type yang:counter32;
                                description "The number of dynamic IPsec tunnels in use on the MDA.";
                            }

                            leaf ip-gre-tunnels {
                                type yang:counter32;
                                description "The number of configured IP tunnels (with GRE headers) on the MDA.";
                            }

                            leaf ip-tunnels {
                                type yang:counter32;
                                description "The number of configured IPv4 tunnels on the MDA.";
                            }

                            leaf l2tpv3-tunnels {
                                type yang:counter32;
                                description "The number of configured L2TPv3 tunnels on the MDA.";
                            }

                        } // container control

                        container cpu-usage {
                            description "Enter the cpu-usage context";

                            container control-plane {
                                description "Enter the control-plane context";

                                container current {
                                    description "Enter the current context";

                                    leaf count {
                                        type decimal64 {
                                            range "0..100";
                                            fraction-digits 2;
                                        }
                                        units "percent";
                                        description "ISA Control Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf count {
                                        type decimal64 {
                                            range "0..100";
                                            fraction-digits 2;
                                        }
                                        units "percent";
                                        description "ISA Control Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container control-plane

                            container data-plane {
                                description "Enter the data-plane context";

                                container current {
                                    description "Enter the current context";

                                    leaf cpu-usage {
                                        type decimal64 {
                                            range "0..100";
                                            fraction-digits 2;
                                        }
                                        units "percent";
                                        description "ISA Data Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf cpu-usage {
                                        type decimal64 {
                                            range "0..100";
                                            fraction-digits 2;
                                        }
                                        units "percent";
                                        description "ISA Data Plane CPU Usage.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container data-plane

                        } // container cpu-usage

                        container memory-allocation-failure-rate {
                            description "Enter the memory-allocation-failure-rate context";

                            container current {
                                description "Enter the current context";

                                leaf count {
                                    type yang:counter64;
                                    units "failures per hour";
                                    description "ISA Memory Allocation Failure Rate.";
                                }

                                leaf start-time {
                                    type yang:date-and-time;
                                    description "The time when the sampling interval started.";
                                }

                                leaf sampling-duration {
                                    type types-sros:time-duration;
                                    description "The duration of the corresponding sampling interval.";
                                }

                            } // container current

                            list historical {
                                key "index";
                                description "Enter the historical list instance";

                                leaf index {
                                    type uint32 {
                                        range "2..max";
                                    }
                                    description "The index of the finished sampling interval period for this statistic. It starts with '2' and is ordered by start time of intervals so that smaller index indicate more recent intervals.";
                                }

                                leaf count {
                                    type yang:counter64;
                                    units "failures per hour";
                                    description "ISA Memory Allocation Failure Rate.";
                                }

                                leaf start-time {
                                    type yang:date-and-time;
                                    description "The time when the sampling interval started.";
                                }

                                leaf sampling-duration {
                                    type types-sros:time-duration;
                                    description "The duration of the corresponding sampling interval.";
                                }

                            } // list historical

                        } // container memory-allocation-failure-rate

                        container ip-tunnel {
                            description "Enter the ip-tunnel context";

                            container number-of-tunnels {
                                description "Enter the number-of-tunnels context";

                                container current {
                                    description "Enter the current context";

                                    leaf gre {
                                        type yang:counter64;
                                        description "Number of GRE tunnels.";
                                    }

                                    leaf ip {
                                        type yang:counter64;
                                        description "Number of IP tunnels.";
                                    }

                                    leaf start-time {
                                        type yang:date-and-time;
                                        description "The time when the sampling interval started.";
                                    }

                                } // container current

                            } // container number-of-tunnels

                            container throughput {
                                description "Enter the throughput context";

                                container gre {
                                    description "Enter the gre context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated GRE tunnel throughput.";
                                            }

                                            leaf decapsulated {
                                                type yang:counter64;
                                                units "packets per second";
                                                description "Decapsulated GRE tunnel throughput.";
                                            }

                                            leaf total {
                                                type yang:counter64;
                                                units "packets per second";
                                                description "Encapsulated and decapsulated GRE tunnel throughput.";
                                            }

                                        } // container packets

                                        container bytes {
                                            description "Enter the bytes context";

                                            leaf encapsulated {
                                                type yang:counter64;
                                                units "megabps";
                                                description "Encapsulated GRE tunnel throughput.";
                                            }

                                            leaf decapsulated {
                                                type yang:counter64;
                                                units "megabps";
                                                description "Decapsulated GRE tunnel throughput.";
                                            }

                                            leaf total {
                                                type yang:counter64;
                                                units "megabps";
                                                description "Encapsulated and decapsulated GRE tunnel throughput.";
                                            }

                                        } // container bytes

                                    } // container current

                                    list historical {
                                        key "index";
                                        description "Enter the historical list instance";

                                        leaf index {
                                            type uint32 {
                                                range "2..max";
                                            }
                                            description "The index of the finished sampling interval period for this statistic. It starts with '2' and is ordered by start time of intervals so that smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated GRE tunnel throughput.";
                                            }

                                            leaf decapsulated {
                                                type yang:counter64;
                                                units "packets per second";
                                                description "Decapsulated GRE tunnel throughput.";
                                            }

                                            leaf total {
                                                type yang:counter64;
                                                units "packets per second";
                                                description "Encapsulated and decapsulated GRE tunnel throughput.";
                                            }

                                        } // container packets

                                        container bytes {
                                            description "Enter the bytes context";

                                            leaf encapsulated {
                                                type yang:counter64;
                                                units "megabps";
                                                description "Encapsulated GRE tunnel throughput.";
                                            }

                                            leaf decapsulated {
                                                type yang:counter64;
                                                units "megabps";
                                                description "Decapsulated GRE tunnel throughput.";
                                            }

                                            leaf total {
                                                type yang:counter64;
                                                units "megabps";
                                                description "Encapsulated and decapsulated GRE tunnel throughput.";
                                            }

                                        } // container bytes

                                    } // list historical

                                } // container gre

                                container ip {
                                    description "Enter the ip context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated IP tunnel throughput.";
                                            }

                                            leaf decapsulated {
                                                type yang:counter64;
                                                units "packets per second";
                                                description "Decapsulated IP tunnel throughput.";
                                            }

                                            leaf total {
                                                type yang:counter64;
                                                units "packets per second";
                                                description "Encapsulated and decapsulated IP tunnel throughput.";
                                            }

                                        } // container packets

                                        container bytes {
                                            description "Enter the bytes context";

                                            leaf encapsulated {
                                                type yang:counter64;
                                                units "megabps";
                                                description "Encapsulated IP tunnel throughput.";
                                            }

                                            leaf decapsulated {
                                                type yang:counter64;
                                                units "megabps";
                                                description "Decapsulated IP tunnel throughput.";
                                            }

                                            leaf total {
                                                type yang:counter64;
                                                units "megabps";
                                                description "Encapsulated and decapsulated IP tunnel throughput.";
                                            }

                                        } // container bytes

                                    } // container current

                                    list historical {
                                        key "index";
                                        description "Enter the historical list instance";

                                        leaf index {
                                            type uint32 {
                                                range "2..max";
                                            }
                                            description "The index of the finished sampling interval period for this statistic. It starts with '2' and is ordered by start time of intervals so that smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated IP tunnel throughput.";
                                            }

                                            leaf decapsulated {
                                                type yang:counter64;
                                                units "packets per second";
                                                description "Decapsulated IP tunnel throughput.";
                                            }

                                            leaf total {
                                                type yang:counter64;
                                                units "packets per second";
                                                description "Encapsulated and decapsulated IP tunnel throughput.";
                                            }

                                        } // container packets

                                        container bytes {
                                            description "Enter the bytes context";

                                            leaf encapsulated {
                                                type yang:counter64;
                                                units "megabps";
                                                description "Encapsulated IP tunnel throughput.";
                                            }

                                            leaf decapsulated {
                                                type yang:counter64;
                                                units "megabps";
                                                description "Decapsulated IP tunnel throughput.";
                                            }

                                            leaf total {
                                                type yang:counter64;
                                                units "megabps";
                                                description "Encapsulated and decapsulated IP tunnel throughput.";
                                            }

                                        } // container bytes

                                    } // list historical

                                } // container ip

                                container l2tpv3 {
                                    description "Enter the l2tpv3 context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated L2TPv3 tunnel throughput.";
                                            }

                                            leaf decapsulated {
                                                type yang:counter64;
                                                units "packets per second";
                                                description "Decapsulated L2TPv3 tunnel throughput.";
                                            }

                                            leaf total {
                                                type yang:counter64;
                                                units "packets per second";
                                                description "Encapsulated and decapsulated L2TPv3 tunnel throughput.";
                                            }

                                        } // container packets

                                        container bytes {
                                            description "Enter the bytes context";

                                            leaf encapsulated {
                                                type yang:counter64;
                                                units "megabps";
                                                description "Encapsulated L2TPv3 tunnel throughput.";
                                            }

                                            leaf decapsulated {
                                                type yang:counter64;
                                                units "megabps";
                                                description "Decapsulated L2TPv3 tunnel throughput.";
                                            }

                                            leaf total {
                                                type yang:counter64;
                                                units "megabps";
                                                description "Encapsulated and decapsulated L2TPv3 tunnel throughput.";
                                            }

                                        } // container bytes

                                    } // container current

                                    list historical {
                                        key "index";
                                        description "Enter the historical list instance";

                                        leaf index {
                                            type uint32 {
                                                range "2..max";
                                            }
                                            description "The index of the finished sampling interval period for this statistic. It starts with '2' and is ordered by start time of intervals so that smaller index indicate more recent intervals.";
                                        }

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets per second";
                                                description "Encapsulated L2TPv3 tunnel throughput.";
                                            }

                                            leaf decapsulated {
                                                type yang:counter64;
                                                units "packets per second";
                                                description "Decapsulated L2TPv3 tunnel throughput.";
                                            }

                                            leaf total {
                                                type yang:counter64;
                                                units "packets per second";
                                                description "Encapsulated and decapsulated L2TPv3 tunnel throughput.";
                                            }

                                        } // container packets

                                        container bytes {
                                            description "Enter the bytes context";

                                            leaf encapsulated {
                                                type yang:counter64;
                                                units "megabps";
                                                description "Encapsulated L2TPv3 tunnel throughput.";
                                            }

                                            leaf decapsulated {
                                                type yang:counter64;
                                                units "megabps";
                                                description "Decapsulated L2TPv3 tunnel throughput.";
                                            }

                                            leaf total {
                                                type yang:counter64;
                                                units "megabps";
                                                description "Encapsulated and decapsulated L2TPv3 tunnel throughput.";
                                            }

                                        } // container bytes

                                    } // list historical

                                } // container l2tpv3

                            } // container throughput

                            container traffic-forward {
                                description "Enter the traffic-forward context";

                                container gre {
                                    description "Enter the gre context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped GRE tunnel packets.";
                                            }

                                            leaf decapsulated {
                                                type yang:counter64;
                                                units "packets";
                                                description "Number of decaped GRE tunnel packets.";
                                            }

                                            leaf total {
                                                type yang:counter64;
                                                units "packets";
                                                description "Number of encaped and decaped GRE tunnel packets.";
                                            }

                                        } // container packets

                                        container bytes {
                                            description "Enter the bytes context";

                                            leaf encapsulated {
                                                type yang:counter64;
                                                units "kilobytes";
                                                description "Number of kilobytes in the encaped GRE tunnel packets.";
                                            }

                                            leaf decapsulated {
                                                type yang:counter64;
                                                units "kilobytes";
                                                description "Number of kilobytes in the decaped GRE tunnel packets.";
                                            }

                                            leaf total {
                                                type yang:counter64;
                                                units "kilobytes";
                                                description "Number of kilobytes in the encaped and decaped GRE tunnel packets.";
                                            }

                                        } // container bytes

                                    } // container current

                                } // container gre

                                container ip {
                                    description "Enter the ip context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped IP tunnel packets.";
                                            }

                                            leaf decapsulated {
                                                type yang:counter64;
                                                units "packets";
                                                description "Number of decaped IP tunnel packets.";
                                            }

                                            leaf total {
                                                type yang:counter64;
                                                units "packets";
                                                description "Number of encaped and decaped IP tunnel packets.";
                                            }

                                        } // container packets

                                        container bytes {
                                            description "Enter the bytes context";

                                            leaf encapsulated {
                                                type yang:counter64;
                                                units "kilobytes";
                                                description "Number of kilobytes in the encaped IP tunnel packets.";
                                            }

                                            leaf decapsulated {
                                                type yang:counter64;
                                                units "kilobytes";
                                                description "Number of kilobytes in the decaped IP tunnel packets.";
                                            }

                                            leaf total {
                                                type yang:counter64;
                                                units "kilobytes";
                                                description "Number of kilobytes in the encaped and decaped IP tunnel packets.";
                                            }

                                        } // container bytes

                                    } // container current

                                } // container ip

                                container l2tpv3 {
                                    description "Enter the l2tpv3 context";

                                    container current {
                                        description "Enter the current context";

                                        leaf start-time {
                                            type yang:date-and-time;
                                            description "The time when the sampling interval started.";
                                        }

                                        leaf sampling-duration {
                                            type types-sros:time-duration;
                                            description "The duration of the corresponding sampling interval.";
                                        }

                                        container packets {
                                            description "Enter the packets context";

                                            leaf encapsulated {
                                                type yang:counter64;
                                                units "packets";
                                                description "Number of encaped L2TPv3 tunnel packets.";
                                            }

                                            leaf decapsulated {
                                                type yang:counter64;
                                                units "packets";
                                                description "Number of decaped L2TPv3 tunnel packets.";
                                            }

                                            leaf total {
                                                type yang:counter64;
                                                units "packets";
                                                description "Number of encaped and decaped L2TPv3 tunnel packets.";
                                            }

                                        } // container packets

                                        container bytes {
                                            description "Enter the bytes context";

                                            leaf encapsulated {
                                                type yang:counter64;
                                                units "kilobytes";
                                                description "Number of kilobytes in the encaped L2TPv3 tunnel packets.";
                                            }

                                            leaf decapsulated {
                                                type yang:counter64;
                                                units "kilobytes";
                                                description "Number of kilobytes in the decaped L2TPv3 tunnel packets.";
                                            }

                                            leaf total {
                                                type yang:counter64;
                                                units "kilobytes";
                                                description "Number of kilobytes in the encaped and decaped L2TPv3 tunnel packets.";
                                            }

                                        } // container bytes

                                    } // container current

                                } // container l2tpv3

                            } // container traffic-forward

                        } // container ip-tunnel

                        container ipsec {
                            description "Enter the ipsec context";

                            container number-of-tunnels {
                                description "Enter the number-of-tunnels context";

                                container current {
                                    description "Enter the current context";

                                    leaf static-lan-to-lan {
                                        type yang:counter64;
                                        description "Number of IPsec static LAN-to-LAN (SL2L) tunnels.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf static-lan-to-lan {
                                        type yang:counter64;
                                        description "Number of IPsec static LAN-to-LAN (SL2L) tunnels.";
                                    }

                                    leaf dynamic-lan-to-lan {
                                        type yang:counter64;
                                        description "Number of IPsec dynamic LAN-to-LAN (DL2L) tunnels.";
                                    }

                                    leaf remote-access {
                                        type yang:counter64;
                                        description "Number of IPsec remote access (RA) tunnels.";
                                    }

                                    leaf total {
                                        type yang:counter64;
                                        description "Total number of IPsec tunnels.";
                                    }

                                    leaf start-time {
                                        type yang:date-and-time;
                                        description "The time when the sampling interval started.";
                                    }

                                } // list historical

                            } // container number-of-tunnels

                            container throughput {
                                description "Enter the throughput context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets per second";
                                            description "Encrypted IPsec traffic throughput.";
                                        }

                                        leaf decrypted {
                                            type yang:counter64;
                                            units "packets per second";
                                            description "Decrypted IPsec traffic throughput.";
                                        }

                                        leaf total {
                                            type yang:counter64;
                                            units "packets per second";
                                            description "Encrypted and decrypted IPsec traffic throughput.";
                                        }

                                    } // container packets

                                    container bytes {
                                        description "Enter the bytes context";

                                        leaf encrypted {
                                            type yang:counter64;
                                            units "megabps";
                                            description "Encrypted IPsec traffic throughput.";
                                        }

                                        leaf decrypted {
                                            type yang:counter64;
                                            units "megabps";
                                            description "Decrypted IPsec traffic throughput.";
                                        }

                                        leaf total {
                                            type yang:counter64;
                                            units "megabps";
                                            description "Encrypted and decrypted IPsec traffic throughput.";
                                        }

                                    } // container bytes

                                } // list historical

                            } // container throughput

                            container tunnel-setup-rate {
                                description "Enter the tunnel-setup-rate context";

                                container current {
                                    description "Enter the current context";

                                    leaf static-lan-to-lan {
                                        type decimal64 {
                                            fraction-digits 2;
                                        }
                                        units "tunnels per second";
                                        description "Static LAN-to-LAN (SL2L) tunnel setup rate.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf static-lan-to-lan {
                                        type decimal64 {
                                            fraction-digits 2;
                                        }
                                        units "tunnels per second";
                                        description "Static LAN-to-LAN (SL2L) tunnel setup rate.";
                                    }

                                    leaf total {
                                        type decimal64 {
                                            fraction-digits 2;
                                        }
                                        units "tunnels per second";
                                        description "Total IPsec tunnel setup rate.";
                                    }

                                    leaf dynamic-lan-to-lan {
                                        type decimal64 {
                                            fraction-digits 2;
                                        }
                                        units "tunnels per second";
                                        description "Dynamic LAN-to-LAN (DL2L) tunnel setup rate.";
                                    }

                                    leaf remote-access {
                                        type decimal64 {
                                            fraction-digits 2;
                                        }
                                        units "tunnels per second";
                                        description "Remote access (RA) tunnel setup rate.";
                                    }

                                    leaf start-time {
                                        type yang:date-and-time;
                                        description "The time when the sampling interval started.";
                                    }

                                    leaf sampling-duration {
                                        type types-sros:time-duration;
                                        description "The duration of the corresponding sampling interval.";
                                    }

                                } // list historical

                            } // container tunnel-setup-rate

                            container traffic-forward {
                                description "Enter the traffic-forward context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container packets {
                                        description "Enter the packets context";

                                        leaf encrypted {
                                            type yang:counter64;
                                            units "packets";
                                            description "Number of encrypted IPsec packets.";
                                        }

                                        leaf decrypted {
                                            type yang:counter64;
                                            units "packets";
                                            description "Number of decrypted IPsec packets.";
                                        }

                                        leaf total {
                                            type yang:counter64;
                                            units "packets";
                                            description "Number of encrypted and decrypted IPsec packets.";
                                        }

                                    } // container packets

                                    container bytes {
                                        description "Enter the bytes context";

                                        leaf encrypted {
                                            type yang:counter64;
                                            units "kilobytes";
                                            description "Number of kilobytes in the encrypted IPsec packets.";
                                        }

                                        leaf decrypted {
                                            type yang:counter64;
                                            units "kilobytes";
                                            description "Number of kilobytes in the decrypted IPsec packets.";
                                        }

                                        leaf total {
                                            type yang:counter64;
                                            units "kilobytes";
                                            description "Number of kilobytes in the encrypted and decrypted IPsec packets.";
                                        }

                                    } // container bytes

                                } // container current

                            } // container traffic-forward

                            container ike-exchange-failure-rate {
                                description "Enter the ike-exchange-failure-rate context";

                                container current {
                                    description "Enter the current context";

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container other

                                } // container current

                                list historical {
                                    key "index";
                                    description "Enter the historical list instance";

                                    leaf index {
                                        type uint32 {
                                            range "2..max";
                                        }
                                        description "The index of the finished sampling interval period for this statistic. It starts with '2' and is ordered by start time of intervals so that smaller index indicate more recent intervals.";
                                    }

                                    leaf start-time {
                                        type yang:date-and-time;
                                        description "The time when the sampling interval started.";
                                    }

                                    leaf sampling-duration {
                                        type types-sros:time-duration;
                                        description "The duration of the corresponding sampling interval.";
                                    }

                                    container auth-failure {
                                        description "Enter the auth-failure context";

                                        leaf count {
                                            type decimal64 {
                                                fraction-digits 2;
                                            }
                                            units "failures per second";
                                            description "IKE exchange failure rate - authentication.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container auth-failure

                                    container non-proposal-chosen {
                                        description "Enter the non-proposal-chosen context";

                                        leaf count {
                                            type decimal64 {
                                                fraction-digits 2;
                                            }
                                            units "failures per second";
                                            description "IKE exchange failure rate - non-proposal chosen.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container non-proposal-chosen

                                    container internal-address-assignment {
                                        description "Enter the internal-address-assignment context";

                                        leaf count {
                                            type decimal64 {
                                                fraction-digits 2;
                                            }
                                            units "failures per second";
                                            description "IKE exchange failure rate - address assignment.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container internal-address-assignment

                                    container invalid-ts {
                                        description "Enter the invalid-ts context";

                                        leaf count {
                                            type decimal64 {
                                                fraction-digits 2;
                                            }
                                            units "failures per second";
                                            description "IKE exchange failure rate - invalid traffic selector.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container invalid-ts

                                    container invalid-ke {
                                        description "Enter the invalid-ke context";

                                        leaf count {
                                            type decimal64 {
                                                fraction-digits 2;
                                            }
                                            units "failures per second";
                                            description "IKE exchange failure rate - invalid key exchange.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container invalid-ke

                                    container dpd-timeout {
                                        description "Enter the dpd-timeout context";

                                        leaf count {
                                            type decimal64 {
                                                fraction-digits 2;
                                            }
                                            units "failures per second";
                                            description "IKE exchange failure rate - DPD timeout.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container dpd-timeout

                                    container other {
                                        description "Enter the other context";

                                        leaf count {
                                            type decimal64 {
                                                fraction-digits 2;
                                            }
                                            units "failures per second";
                                            description "IKE exchange failure rate - other failure reasons.";
                                        }

                                        leaf first-failure {
                                            type yang:date-and-time;
                                            description "The time when the first IKE exchange failure happened in the corresponding sampling interval.";
                                        }

                                        leaf first-failure-description {
                                            type types-sros:long-description;
                                            description "The description of the place where the first IKE exchange failure happened.";
                                        }

                                        leaf last-failure {
                                            type yang:date-and-time;
                                            description "The time when the last IKE exchange failure happened in the corresponding sampling interval.";
                                        }

                                        leaf last-failure-description {
                                            type types-sros:long-description;
                                            description "The description of the place where the last IKE exchange failure happened.";
                                        }

                                    } // container other

                                } // list historical

                            } // container ike-exchange-failure-rate

                            container ikev2-msg-drop {
                                description "Enter the ikev2-msg-drop context";

                                container current {
                                    description "Enter the current context";

                                    leaf ike-sa-init {
                                        type yang:counter64;
                                        description "Number of IKE-SA-INIT exchange packet drops.";
                                    }

                                    leaf ike-auth {
                                        type yang:counter64;
                                        description "Number of IKE-AUTH exchange packet drops.";
                                    }

                                    leaf create-child-and-info {
                                        type yang:counter64;
                                        description "Number of Create-CHILD and informational exchange packet drops.";
                                    }

                                    leaf start-time {
                                        type yang:date-and-time;
                                        description "The time when the sampling interval started.";
                                    }

                                    leaf sampling-duration {
                                        type types-sros:time-duration;
                                        description "The duration of the corresponding sampling interval.";
                                    }

                                } // container current

                            } // container ikev2-msg-drop

                        } // container ipsec

                    } // container statistics

                } // container isa-tunnel

                container resource-usage {
                    description "Enter the resource-usage context";

                    container egress-hsmda-queue-groups {
                        description "Enter the egress-hsmda-queue-groups context";

                        leaf total {
                            type yang:counter32;
                            description "The total number of resources supported on this MDA.";
                        }

                        leaf allocated {
                            type yang:counter32;
                            description "The total number of resources that are currently allocated on this MDA.";
                        }

                        leaf free {
                            type yang:counter32;
                            description "The total number of resources that are remaining free on this MDA.";
                        }

                    } // container egress-hsmda-queue-groups

                    container egress-hsmda-secondary-shapers {
                        description "Enter the egress-hsmda-secondary-shapers context";

                        leaf total {
                            type yang:counter32;
                            description "The total number of resources supported on this MDA.";
                        }

                        leaf allocated {
                            type yang:counter32;
                            description "The total number of resources that are currently allocated on this MDA.";
                        }

                        leaf free {
                            type yang:counter32;
                            description "The total number of resources that are remaining free on this MDA.";
                        }

                    } // container egress-hsmda-secondary-shapers

                } // container resource-usage

            } // list mda

            list xiom {
                key "xiom-slot";
                description "Enter the xiom list instance";

                leaf xiom-slot {
                    type string {
                        length "2";
                    }
                    description "XIOM slot ID";
                }

                leaf equipped-type {
                    type types-card:sros-xiom-type-state;
                    description "Indicates the XIOM type that is physically inserted into the slot.";
                }

                leaf equipped-level {
                    type types-card:sros-xiom-level-state;
                    description "Indicates the functional level of the XIOM that is physically inserted into the slot.";
                }

                leaf licensed-level {
                    type types-card:sros-xiom-level-state;
                    description "Indicates the XIOM level that is licensed for the slot.";
                }

                leaf available-mda-slots {
                    type uint32;
                    description "Indicates the number of MDA slots available on this XIOM.";
                }

                leaf installed-mda-slots {
                    type uint32;
                    description "Indicates the number of MDA slots installed on this XIOM.";
                }

                container hardware-data {
                    description "Enter the hardware-data context";

                    leaf part-number {
                        type string {
                            length "0..32";
                        }
                        description "Indicates the part number information.";
                    }

                    leaf serial-number {
                        type string {
                            length "0..32";
                        }
                        description "Indicates the serial number of the hardware component.";
                    }

                    leaf manufacturing-date {
                        type string {
                            length "0..8";
                        }
                        description "Indicates the manufacturing date of the hardware component.";
                    }

                    leaf common-language-equipment-identifier {
                        type string {
                            length "0..10";
                        }
                        description "Indicates the CLEI, a unique 10-character identifier fixed by the manufacturer.";
                    }

                    leaf field-replaceable-unit {
                        type boolean;
                        description "Indicates whether the hardware component is a field replaceable unit or not.";
                    }

                    leaf contained-in {
                        type types-sros:named-item-or-empty;
                        description "Indicates the hardware component that contains this component. An empty string indicates that this component is not contained in any other component.";
                    }

                    leaf oper-state {
                        type enumeration {
                            enum "unknown"                      { value 1; }
                            enum "in-service"                   { value 2; }
                            enum "out-of-service"               { value 3; }
                            enum "diagnosing"                   { value 4; }
                            enum "failed"                       { value 5; }
                            enum "booting"                      { value 6; }
                            enum "empty"                        { value 7; }
                            enum "provisioned"                  { value 8; }
                            enum "unprovisioned"                { value 9; }
                            enum "upgrade"                      { value 10; }
                            enum "downgrade"                    { value 11; }
                            enum "in-service-upgrade"           { value 12; }
                            enum "in-service-downgrade"         { value 13; }
                            enum "reset-pending"                { value 14; }
                            enum "soft-reset"                   { value 15; }
                            enum "pre-extension"                { value 16; }
                            enum "downloading"                  { value 17; }
                        }
                        description "Indicates the operational status of the hardware component.";
                    }

                    leaf failure-reason {
                        type string {
                            length "0..255";
                        }
                        description "Indicates the reason why a hardware component 'failed' as indicated in oper-state.";
                    }

                    leaf contains-temperature-sensor {
                        type boolean;
                        description "Indicates whether or not this hardware component contains a temperature sensor.";
                    }

                    leaf temperature {
                        type int32;
                        description "Indicates the current temperature in degrees celsius from the temperature sensor.";
                    }

                    leaf temperature-threshold {
                        type int32;
                        description "Indicates the temperature threshold for this hardware component in degrees celsius.";
                    }

                    leaf alarm-state {
                        type enumeration {
                            enum "unknown"                      { value 0; }
                            enum "alarm-active"                 { value 1; }
                            enum "alarm-cleared"                { value 2; }
                        }
                        description "Indicates the current alarm state for this hardware component.";
                    }

                    leaf manufacturing-deviations {
                        type string {
                            length "0..255";
                        }
                        description "Indicates the record of changes done by the manfacturing to the hardware or software which is outside the normal revision control process.";
                    }

                    leaf equipped-platform-type {
                        type enumeration {
                            enum "platform-unknown"             { value 0; }
                            enum "platform-7750"                { value 1; }
                            enum "platform-7450"                { value 2; }
                            enum "platform-7710"                { value 3; }
                            enum "platform-7950"                { value 4; }
                            enum "platform-7705"                { value 5; }
                            enum "platform-7250"                { value 6; }
                        }
                        description "Indicates the platform type of the installed hardware component, as read from the EEPROM.";
                    }

                    leaf manufacturing-assembly-number {
                        type string {
                            length "0..32";
                        }
                        description "Indicates an assembly number indicating manufacturing differences for a given part number.";
                    }

                    leaf base-mac-address {
                        type yang:mac-address;
                        description "Indicates the base MAC address of the hardware component.";
                    }

                    leaf boot-code-version {
                        type string {
                            length "0..255";
                        }
                        description "Indicates the version number of boot eprom.";
                    }

                    leaf software-code-version {
                        type string {
                            length "0..255";
                        }
                        description "Indicates the software product release version number for the software image currently running.";
                    }

                    leaf software-last-boot-time {
                        type yang:date-and-time;
                        description "This indicates the date and time the software running on this hardware component was last rebooted.";
                    }

                    leaf software-image-source {
                        type enumeration {
                            enum "unknown"                      { value 0; }
                            enum "primary"                      { value 1; }
                            enum "secondary"                    { value 2; }
                            enum "tertiary"                     { value 3; }
                        }
                        description "Indicates the location in the Boot Options File (BOF) where the software image file was found when the system last rebooted.";
                    }

                    leaf firmware-code-version {
                        type string {
                            length "0..255";
                        }
                        description "Indicates the software product release version number associated with the firmware version currently programmed.";
                    }

                    leaf firmware-revision-status {
                        type enumeration {
                            enum "not-applicable"               { value 0; }
                            enum "acceptable"                   { value 1; }
                            enum "not-acceptable"               { value 2; }
                            enum "upgrade-pending"              { value 3; }
                            enum "upgrading"                    { value 4; }
                            enum "upgrade-next-hard-reset"      { value 5; }
                        }
                        description "Indicates the firmware/FPGA revision status for the hardware component.";
                    }

                } // container hardware-data

                list mda {
                    key "mda-slot";
                    description "Enter the mda list instance";

                    leaf mda-slot {
                        type uint32 {
                            range "1..2";
                        }
                        description "MDA-s slot number";
                    }

                    leaf equipped-type {
                        type types-card:sros-xiom-mda-type-state;
                        description "Indicates the MDA type that is physically inserted into the XIOM slot.";
                    }

                    leaf maximum-ports {
                        type uint32;
                        description "Indicates the maximum number of ports or connectors that can be equipped on the MDA.";
                    }

                    leaf equipped-ports {
                        type uint32;
                        description "Indicates the number of ports or connectors equipped on the MDA.";
                    }

                    container hardware-data {
                        description "Enter the hardware-data context";

                        leaf part-number {
                            type string {
                                length "0..32";
                            }
                            description "Indicates the part number information.";
                        }

                        leaf serial-number {
                            type string {
                                length "0..32";
                            }
                            description "Indicates the serial number of the hardware component.";
                        }

                        leaf manufacturing-date {
                            type string {
                                length "0..8";
                            }
                            description "Indicates the manufacturing date of the hardware component.";
                        }

                        leaf common-language-equipment-identifier {
                            type string {
                                length "0..10";
                            }
                            description "Indicates the CLEI, a unique 10-character identifier fixed by the manufacturer.";
                        }

                        leaf field-replaceable-unit {
                            type boolean;
                            description "Indicates whether the hardware component is a field replaceable unit or not.";
                        }

                        leaf contained-in {
                            type types-sros:named-item-or-empty;
                            description "Indicates the hardware component that contains this component. An empty string indicates that this component is not contained in any other component.";
                        }

                        leaf oper-state {
                            type enumeration {
                                enum "unknown"                      { value 1; }
                                enum "in-service"                   { value 2; }
                                enum "out-of-service"               { value 3; }
                                enum "diagnosing"                   { value 4; }
                                enum "failed"                       { value 5; }
                                enum "booting"                      { value 6; }
                                enum "empty"                        { value 7; }
                                enum "provisioned"                  { value 8; }
                                enum "unprovisioned"                { value 9; }
                                enum "upgrade"                      { value 10; }
                                enum "downgrade"                    { value 11; }
                                enum "in-service-upgrade"           { value 12; }
                                enum "in-service-downgrade"         { value 13; }
                                enum "reset-pending"                { value 14; }
                                enum "soft-reset"                   { value 15; }
                                enum "pre-extension"                { value 16; }
                                enum "downloading"                  { value 17; }
                            }
                            description "Indicates the operational status of the hardware component.";
                        }

                        leaf failure-reason {
                            type string {
                                length "0..255";
                            }
                            description "Indicates the reason why a hardware component 'failed' as indicated in oper-state.";
                        }

                        leaf contains-temperature-sensor {
                            type boolean;
                            description "Indicates whether or not this hardware component contains a temperature sensor.";
                        }

                        leaf temperature {
                            type int32;
                            description "Indicates the current temperature in degrees celsius from the temperature sensor.";
                        }

                        leaf temperature-threshold {
                            type int32;
                            description "Indicates the temperature threshold for this hardware component in degrees celsius.";
                        }

                        leaf alarm-state {
                            type enumeration {
                                enum "unknown"                      { value 0; }
                                enum "alarm-active"                 { value 1; }
                                enum "alarm-cleared"                { value 2; }
                            }
                            description "Indicates the current alarm state for this hardware component.";
                        }

                        leaf manufacturing-deviations {
                            type string {
                                length "0..255";
                            }
                            description "Indicates the record of changes done by the manfacturing to the hardware or software which is outside the normal revision control process.";
                        }

                        leaf equipped-platform-type {
                            type enumeration {
                                enum "platform-unknown"             { value 0; }
                                enum "platform-7750"                { value 1; }
                                enum "platform-7450"                { value 2; }
                                enum "platform-7710"                { value 3; }
                                enum "platform-7950"                { value 4; }
                                enum "platform-7705"                { value 5; }
                                enum "platform-7250"                { value 6; }
                            }
                            description "Indicates the platform type of the installed hardware component, as read from the EEPROM.";
                        }

                        leaf manufacturing-assembly-number {
                            type string {
                                length "0..32";
                            }
                            description "Indicates an assembly number indicating manufacturing differences for a given part number.";
                        }

                        leaf power-zone-location {
                            type uint32 {
                                range "0..32";
                            }
                            description "Indicates the managed power zone that this hardware component resides.";
                        }

                        leaf base-mac-address {
                            type yang:mac-address;
                            description "Indicates the base MAC address of the hardware component.";
                        }

                        leaf boot-code-version {
                            type string {
                                length "0..255";
                            }
                            description "Indicates the version number of boot eprom.";
                        }

                        leaf software-code-version {
                            type string {
                                length "0..255";
                            }
                            description "Indicates the software product release version number for the software image currently running.";
                        }

                        leaf software-last-boot-time {
                            type yang:date-and-time;
                            description "This indicates the date and time the software running on this hardware component was last rebooted.";
                        }

                        leaf software-image-source {
                            type enumeration {
                                enum "unknown"                      { value 0; }
                                enum "primary"                      { value 1; }
                                enum "secondary"                    { value 2; }
                                enum "tertiary"                     { value 3; }
                            }
                            description "Indicates the location in the Boot Options File (BOF) where the software image file was found when the system last rebooted.";
                        }

                        leaf firmware-code-version {
                            type string {
                                length "0..255";
                            }
                            description "Indicates the software product release version number associated with the firmware version currently programmed.";
                        }

                        leaf firmware-revision-status {
                            type enumeration {
                                enum "not-applicable"               { value 0; }
                                enum "acceptable"                   { value 1; }
                                enum "not-acceptable"               { value 2; }
                                enum "upgrade-pending"              { value 3; }
                                enum "upgrading"                    { value 4; }
                                enum "upgrade-next-hard-reset"      { value 5; }
                            }
                            description "Indicates the firmware/FPGA revision status for the hardware component.";
                        }

                    } // container hardware-data

                    container subscriber-management {
                        description "Enter the subscriber-management context";

                        container statistics {
                            description "Enter the statistics context";

                            leaf last-reset-peak-values {
                                type yang:date-and-time;
                                description "Timestamp of the last reset of the peak values";
                            }

                            list ipv4-hosts {
                                key "counter";
                                description "Enter the ipv4-hosts list instance";

                                leaf counter {
                                    type types-submgt:submgt-statistics-ipv4-type;
                                    description "Type of submgt ipv4 hosts counter";
                                }

                                leaf current-value {
                                    type uint32;
                                    description "Current value of submgt counter";
                                }

                                leaf peak-value {
                                    type uint32;
                                    description "Peak value of submgt counter";
                                }

                                leaf peak-timestamp {
                                    type yang:date-and-time;
                                    description "Peak timestamp of submgt counter";
                                }

                            } // list ipv4-hosts

                            list ipv6-hosts {
                                key "counter";
                                description "Enter the ipv6-hosts list instance";

                                leaf counter {
                                    type types-submgt:submgt-statistics-ipv6-type;
                                    description "Type of submgt ipv6 hosts counter";
                                }

                                leaf current-value {
                                    type uint32;
                                    description "Current value of submgt counter";
                                }

                                leaf peak-value {
                                    type uint32;
                                    description "Peak value of submgt counter";
                                }

                                leaf peak-timestamp {
                                    type yang:date-and-time;
                                    description "Peak timestamp of submgt counter";
                                }

                            } // list ipv6-hosts

                            list total-hosts {
                                key "counter";
                                description "Enter the total-hosts list instance";

                                leaf counter {
                                    type types-submgt:submgt-statistics-total-type;
                                    description "Type of submgt total hosts counter";
                                }

                                leaf current-value {
                                    type uint32;
                                    description "Current value of submgt counter";
                                }

                                leaf peak-value {
                                    type uint32;
                                    description "Peak value of submgt counter";
                                }

                                leaf peak-timestamp {
                                    type yang:date-and-time;
                                    description "Peak timestamp of submgt counter";
                                }

                            } // list total-hosts

                            list sessions {
                                key "counter";
                                description "Enter the sessions list instance";

                                leaf counter {
                                    type types-submgt:submgt-statistics-session-type;
                                    description "Type of submgt sessions counter";
                                }

                                leaf current-value {
                                    type uint32;
                                    description "Current value of submgt counter";
                                }

                                leaf peak-value {
                                    type uint32;
                                    description "Peak value of submgt counter";
                                }

                                leaf peak-timestamp {
                                    type yang:date-and-time;
                                    description "Peak timestamp of submgt counter";
                                }

                            } // list sessions

                        } // container statistics

                    } // container subscriber-management

                } // list mda

            } // list xiom

            container resource-usage {
                description "Enter the resource-usage context";

                container qos-user-schedulers {
                    description "Enter the qos-user-schedulers context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container qos-user-schedulers

                container qos-user-schedulers-overrides {
                    description "Enter the qos-user-schedulers-overrides context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container qos-user-schedulers-overrides

                container hsmda-queue-overrides {
                    description "Enter the hsmda-queue-overrides context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container hsmda-queue-overrides

                container egress-port-access-network-qgroup-instances {
                    description "Enter the egress-port-access-network-qgroup-instances context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                    container egress-access-port-queue-group-instances {
                        description "Enter the egress-access-port-queue-group-instances context";

                        leaf total {
                            type yang:counter32;
                            description "The total number of resources supported on this card.";
                        }

                        leaf allocated {
                            type yang:counter32;
                            description "The total number of resources that are currently allocated on this card.";
                        }

                        leaf free {
                            type yang:counter32;
                            description "The total number of resources that are remaining free on this card.";
                        }

                    } // container egress-access-port-queue-group-instances

                    container egress-network-port-queue-group-instances {
                        description "Enter the egress-network-port-queue-group-instances context";

                        leaf total {
                            type yang:counter32;
                            description "The total number of resources supported on this card.";
                        }

                        leaf allocated {
                            type yang:counter32;
                            description "The total number of resources that are currently allocated on this card.";
                        }

                        leaf free {
                            type yang:counter32;
                            description "The total number of resources that are remaining free on this card.";
                        }

                    } // container egress-network-port-queue-group-instances

                } // container egress-port-access-network-qgroup-instances

                container ingress-fp-queue-group-instances {
                    description "Enter the ingress-fp-queue-group-instances context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container ingress-fp-queue-group-instances

                container egress-port-vport {
                    description "Enter the egress-port-vport context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container egress-port-vport

                container qos-intermediate-arbiters {
                    description "Enter the qos-intermediate-arbiters context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container qos-intermediate-arbiters

                container qos-intermediate-arbiters-overrides {
                    description "Enter the qos-intermediate-arbiters-overrides context";

                    leaf total {
                        type yang:counter32;
                        description "The total number of resources supported on this card.";
                    }

                    leaf allocated {
                        type yang:counter32;
                        description "The total number of resources that are currently allocated on this card.";
                    }

                    leaf free {
                        type yang:counter32;
                        description "The total number of resources that are remaining free on this card.";
                    }

                } // container qos-intermediate-arbiters-overrides

                container sap {
                    description "Enter the sap context";

                    leaf total {
                        type uint32;
                        description "Total number of SAPS available in the card slot.";
                    }

                    leaf allocated {
                        type uint32;
                        description "Total number of SAPS allocated in the card slot.";
                    }

                    leaf free {
                        type uint32;
                        description "Total number of SAPS free in the card slot.";
                    }

                    container epipe {
                        description "Enter the epipe context";

                        leaf total {
                            type uint32;
                            description "Total number of SAPS available in the card slot.";
                        }

                        leaf allocated {
                            type uint32;
                            description "Total number of SAPS allocated in the card slot.";
                        }

                        leaf free {
                            type uint32;
                            description "Total number of SAPS free in the card slot.";
                        }

                    } // container epipe

                    container non-epipe {
                        description "Enter the non-epipe context";

                        leaf total {
                            type uint32;
                            description "Total number of SAPS available in the card slot.";
                        }

                        leaf allocated {
                            type uint32;
                            description "Total number of SAPS allocated in the card slot.";
                        }

                        leaf free {
                            type uint32;
                            description "Total number of SAPS free in the card slot.";
                        }

                    } // container non-epipe

                    container apipe {
                        description "Enter the apipe context";

                        leaf allocated {
                            type uint32;
                            description "Total number of SAPs per service allocated in the card slot.";
                        }

                    } // container apipe

                    container cpipe {
                        description "Enter the cpipe context";

                        leaf allocated {
                            type uint32;
                            description "Total number of SAPs per service allocated in the card slot.";
                        }

                    } // container cpipe

                    container fpipe {
                        description "Enter the fpipe context";

                        leaf allocated {
                            type uint32;
                            description "Total number of SAPs per service allocated in the card slot.";
                        }

                    } // container fpipe

                    container ipipe {
                        description "Enter the ipipe context";

                        leaf allocated {
                            type uint32;
                            description "Total number of SAPs per service allocated in the card slot.";
                        }

                    } // container ipipe

                    container ies {
                        description "Enter the ies context";

                        leaf allocated {
                            type uint32;
                            description "Total number of SAPs per service allocated in the card slot.";
                        }

                    } // container ies

                    container mirror {
                        description "Enter the mirror context";

                        leaf allocated {
                            type uint32;
                            description "Total number of SAPs per service allocated in the card slot.";
                        }

                    } // container mirror

                    container vpls {
                        description "Enter the vpls context";

                        leaf allocated {
                            type uint32;
                            description "Total number of SAPs per service allocated in the card slot.";
                        }

                    } // container vpls

                    container vprn {
                        description "Enter the vprn context";

                        leaf allocated {
                            type uint32;
                            description "Total number of SAPs per service allocated in the card slot.";
                        }

                    } // container vprn

                } // container sap

            } // container resource-usage

            uses state-card-fp;
        } // list card

    } // grouping state-card

}
