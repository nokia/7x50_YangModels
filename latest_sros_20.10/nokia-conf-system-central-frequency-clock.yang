submodule nokia-conf-system-central-frequency-clock {

    yang-version "1.1";

    belongs-to nokia-conf { prefix "conf"; }

    import nokia-sros-yang-extensions     { prefix "sros-ext"; }
    import nokia-types-sros               { prefix "types-sros"; }
    import nokia-types-system             { prefix "types-system"; }

    include nokia-conf-groups;

    sros-ext:sros-major-release "rel20";

    organization "Nokia";

    contact
        "Nokia SR OS Support
         Web: <http://www.nokia.com>";

    description
        "Nokia YANG Data model to configure system central-frequency-clock parameters on SR OS based routers.

         Copyright 2016 Nokia. All rights reserved. Reproduction of this document
         is authorized on the condition that the foregoing copyright notice is included.

         This nokia-conf-system-central-frequency-clock YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping conf-system-central-frequency-clock {
        container central-frequency-clock {
            description "Enter the central-frequency-clock context";

            leaf ql-minimum {
                type types-system:ref-ssm-quality-level-override;
                default "unused";
                description "Minimum signal quality level for system timing module";
            }

            leaf ql-selection {
                type boolean;
                default "false";
                description "Consider quality level in system and BITS output timing";
            }

            leaf revert {
                type boolean;
                default "false";
                description "Revert to higher-priority reference source";
            }

            leaf wait-to-restore {
                type uint32 {
                    range "1..12";
                }
                units "minutes";
                description "Time to re-validate a previously failed input reference";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container ref-order {
                description "Enter the ref-order context";

                leaf first {
                    type types-system:sets-ref-source;
                    description "First preferred timing reference source";
                }

                leaf second {
                    type types-system:sets-ref-source;
                    description "Second preferred timing reference source";
                }

                leaf third {
                    type types-system:sets-ref-source;
                    description "Third preferred timing reference source";
                }

                leaf fourth {
                    type types-system:sets-ref-source;
                    description "Fourth preferred timing reference source";
                }

                leaf fifth {
                    type types-system:sets-ref-source;
                    description "Fifth preferred timing reference source";
                }

            } // container ref-order

            container bits {
                description "Enter the bits context";

                leaf interface-type {
                    type types-system:bits-if-type;
                    default "ds1-esf";
                    description "Interface type of the BITS timing reference";
                }

                leaf ql-override {
                    type types-system:ssm-quality-level-override;
                    default "unused";
                    description "Override for the quality level of the timing reference";
                }

                leaf ssm-bit {
                    when "../interface-type = 'e1-pcm30crc' or ../interface-type = 'e1-pcm31crc'";
                    type uint32 {
                        range "4..8";
                    }
                    default "8";
                    description "Sa bit to convey SSM information";
                }

                container input {
                    description "Enter the input context";

                    leaf admin-state {
                        type types-sros:admin-state;
                        default "disable";
                        description "Administrative state of the BITS input timing reference";
                    }

                } // container input

                container output {
                    description "Enter the output context";

                    leaf line-length {
                        type enumeration {
                            enum "length-not-applicable"        { value 0; }
                            enum "110"                          { value 1; }
                            enum "220"                          { value 2; }
                            enum "330"                          { value 3; }
                            enum "440"                          { value 4; }
                            enum "550"                          { value 5; }
                            enum "660"                          { value 6; }
                        }
                        description "Line length for the BITS output timing reference";
                    }

                    leaf ql-minimum {
                        type types-system:ref-ssm-quality-level-override;
                        default "unused";
                        description "Minimum signal quality level for BITSout port";
                    }

                    leaf source {
                        type types-system:bits-out-source;
                        default "line-ref";
                        description "Source of the BITS output timing reference";
                    }

                    leaf squelch {
                        type boolean;
                        default "false";
                        description "Squelch the signal of the BITS output timing reference";
                    }

                    leaf admin-state {
                        type types-sros:admin-state;
                        description "Administrative state of BITS output timing reference";
                    }

                } // container output

            } // container bits

            container ptp {
                description "Enter the ptp context";

                leaf admin-state {
                    type types-sros:admin-state;
                    default "disable";
                    description "Administrative state of the PTP timing reference";
                }

            } // container ptp

            container ref1 {
                description "Enter the ref1 context";

                leaf ql-override {
                    type types-system:ref-ssm-quality-level-override;
                    default "unused";
                    description "Quality level override of a timing reference";
                }

                leaf admin-state {
                    type types-sros:admin-state;
                    default "disable";
                    description "Administrative state of the first timing reference";
                }

                leaf source-port {
                    type types-sros:port;
                    description "Source port for the first timing reference";
                }

            } // container ref1

            container ref2 {
                description "Enter the ref2 context";

                leaf ql-override {
                    type types-system:ref-ssm-quality-level-override;
                    default "unused";
                    description "Quality level override of a timing reference";
                }

                leaf admin-state {
                    type types-sros:admin-state;
                    default "disable";
                    description "Administrative state of the second timing reference";
                }

                leaf source-port {
                    type types-sros:port;
                    description "Source port for the second timing reference";
                }

            } // container ref2

            container synce {
                description "Enter the synce context";

                leaf admin-state {
                    type types-sros:admin-state;
                    default "disable";
                    description "Administrative state of the SyncE timing reference";
                }

                leaf ql-override {
                    type types-system:ref-ssm-quality-level-override;
                    default "unused";
                    description "Override the quality level of a timing reference";
                }

            } // container synce

            container gnss {
                description "Enter the gnss context";

                leaf admin-state {
                    type types-sros:admin-state;
                    default "disable";
                    description "Administrative state of the gnss timing reference";
                }

                leaf ql-override {
                    type types-system:ssm-quality-level-override;
                    default "unused";
                    description "Override the quality level of a timing reference";
                }

            } // container gnss

        } // container central-frequency-clock

    } // grouping conf-system-central-frequency-clock

}
