submodule nokia-state-svc-vprn-ripng {

    yang-version "1.1";

    belongs-to nokia-state { prefix "state"; }

    import ietf-yang-types                { prefix "yang"; }
    import nokia-sros-yang-extensions     { prefix "sros-ext"; }
    import nokia-types-ripng              { prefix "types-ripng"; }
    import nokia-types-sros               { prefix "types-sros"; }

    include nokia-state-service;
    include nokia-state-svc-vprn;

    sros-ext:sros-major-release "rel20";

    organization "Nokia";

    contact
        "Nokia SR OS Support
         Web: <http://www.nokia.com>";

    description
        "Nokia YANG Data model with operational state for vprn ripng protocol attributes on SR OS based routers.

         Copyright 2016 Nokia. All rights reserved. Reproduction of this document
         is authorized on the condition that the foregoing copyright notice is included.

         This nokia-state-svc-vprn-ripng YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping state-svc-vprn-ripng {
        container ripng {
            description "Enter the ripng context";

            leaf oper-state {
                type types-sros:oper-state;
                description "The operational state of this RIPng instance.";
            }

            list peer {
                key "interface-name address";
                description "Enter the peer list instance";

                leaf interface-name {
                    type types-sros:interface-name;
                    description "The interface on which this peer was discovered.";
                }

                leaf address {
                    type types-sros:ipv6-address;
                    description "IP Address the peer is using as its source address.";
                }

                leaf version {
                    type types-ripng:peer-version;
                    description "The RIPng version in the header of the last packet received from this peer.";
                }

                leaf last-update {
                    type yang:date-and-time;
                    description "The time the most recent RIPng update was received from this peer.";
                }

            } // list peer

            list advertised-routes {
                key "destination interface-name interface-address";
                description "Enter the advertised-routes list instance";

                leaf destination {
                    type types-sros:ipv6-prefix-with-host-bits;
                    description "Destination IP prefix of the advertised route. If length of prefix is zero, then this indicates a default route.";
                }

                leaf interface-name {
                    type types-sros:interface-name;
                    description "The interface on which the route is advertised.";
                }

                leaf interface-address {
                    type types-sros:ipv6-address;
                    description "The IP address of the subnet/prefix to which the route is advertised.";
                }

                leaf next-hop {
                    type types-sros:ipv6-address;
                    description "The IP address which is advertised in the Next Hop field of the RIPng updates.";
                }

                leaf metric {
                    type types-ripng:metric;
                    description "The metric with which the route is advertised.";
                }

                leaf tag {
                    type uint16;
                    description "The value which is advertised in the Route Tag field for the route.";
                }

                leaf ttl {
                    type uint32;
                    units "seconds";
                    description "The number of seconds till the flush timer expires. The flush timer is active for only those routes which are no longer valid. Such routes will be advertised with a metric of 16 till the flush timer expires after which they will be removed from the database.";
                }

            } // list advertised-routes

            list database {
                key "destination interface-name peer";
                description "Enter the database list instance";

                leaf destination {
                    type types-sros:ipv6-prefix-with-host-bits;
                    description "Destination IP prefix of the RIP route. If length of prefix is zero, then this indicates a default route.";
                }

                leaf interface-name {
                    type types-sros:interface-name;
                    description "The interface on which this route was received.";
                }

                leaf peer {
                    type types-sros:ipv6-address;
                    description "The IP address of the peer from whom this route was received.";
                }

                leaf next-hop {
                    type types-sros:ipv6-address;
                    description "The IP address in the Next Hop field of the RIPng updatevreceived for this route. The Next Hop field is the immediate next hop IP address to which packets sent to the destination specified by this route entry should be forwarded. A value of 0::0 in this field indicates that packets should be forwarded to the originator of the RIPng advertisement.";
                }

                leaf metric {
                    type types-ripng:metric;
                    description "The distance to the destination as advertised by the peer that sent this route.";
                }

                leaf tag {
                    type uint16;
                    description "The value in the Route Tag field of the update received for this route.";
                }

                leaf ttl {
                    type uint32;
                    units "seconds";
                    description "The number of seconds till the timeout timer expires.";
                }

                leaf fc {
                    type types-sros:fc-name;
                    description "The forwarding class associated with the RIPng route.";
                }

                leaf priority {
                    type types-sros:priority;
                    description "Specifies the priority to be assigned to the RIPng route.";
                }

                leaf active {
                    type boolean;
                    description "Indicates whether or not the route entry is active in the system. It will be true if the route entry has been added to the Route Table Manager(RTM).";
                }

            } // list database

            list group {
                key "group-name";
                description "Enter the group list instance";

                leaf group-name {
                    type types-sros:named-item;
                    description "RIP group name";
                }

                leaf oper-state {
                    type types-sros:oper-state;
                    description "The operational state of this RIPng group.";
                }

                list neighbor {
                    key "interface-name";
                    description "Enter the neighbor list instance";

                    leaf interface-name {
                        type leafref {
                            path "../../../../interface/interface-name";
                        }
                        description "IP interface name";
                    }

                    leaf oper-state {
                        type types-sros:oper-state;
                        description "The operational state of this RIPng neighbor.";
                    }

                    container statistics {
                        description "Enter the statistics context";

                        container updates-sent {
                            description "Enter the updates-sent context";

                            leaf total {
                                type yang:counter32;
                                description "The number of all RIPng updates actually sent on this interface. This explicitly does include full updates sent containing new information.";
                            }

                            leaf last-5min {
                                type yang:counter32;
                                description "The number of all RIPng updates actually sent on this interface in the last 5 minutes. This explicitly does include full updates sent containing new information.";
                            }

                            leaf last-1min {
                                type yang:counter32;
                                description "The number of all RIPng updates actually sent on this interface in the last minute. This explicitly does include full updates sent containing new information.";
                            }

                        } // container updates-sent

                        container triggered-updates {
                            description "Enter the triggered-updates context";

                            leaf total {
                                type yang:counter32;
                                description "The number of triggered RIPng updates actually sent on this interface. This explicitly does include full updates sent containing new information.";
                            }

                            leaf last-5min {
                                type yang:counter32;
                                description "The number of triggered RIPng updates actually sent on this interface in the last 5 minutes. This explicitly does include full updates sent containing new information.";
                            }

                            leaf last-1min {
                                type yang:counter32;
                                description "The number of triggered RIPng updates actually sent on this interface in the last minute. This explicitly does include full updates sent containing new information.";
                            }

                        } // container triggered-updates

                        container bad-packets-received {
                            description "Enter the bad-packets-received context";

                            leaf total {
                                type yang:counter32;
                                description "The number of RIPng updates received on this interface that were discarded as invalid.";
                            }

                            leaf last-5min {
                                type yang:counter32;
                                description "The number of RIPng response packets discarded (for any reason e.g. a version 0 packet, or an unknown command type) in the last 5 minutes.";
                            }

                            leaf last-1min {
                                type yang:counter32;
                                description "The number of RIPng response packets discarded (for any reason e.g. a version 0 packet, or an unknown command type) in the last minute.";
                            }

                        } // container bad-packets-received

                        container updates-received {
                            description "Enter the updates-received context";

                            leaf total {
                                type yang:counter32;
                                description "The number of RIPng response packets received.";
                            }

                            leaf last-5min {
                                type yang:counter32;
                                description "The number of RIPng response packets received in the last 5 minutes.";
                            }

                            leaf last-1min {
                                type yang:counter32;
                                description "The number of RIPng response packets received in the last minute.";
                            }

                        } // container updates-received

                        container updates-ignored {
                            description "Enter the updates-ignored context";

                            leaf total {
                                type yang:counter32;
                                description "The number of RIPng response packets received which were subsequently discarded for any reason.";
                            }

                            leaf last-5min {
                                type yang:counter32;
                                description "The number of RIPng response packets received in the last 5 minutes which were subsequently discarded for any reason.";
                            }

                            leaf last-1min {
                                type yang:counter32;
                                description "The number of RIPng response packets received in the last minute which were subsequently discarded for any reason.";
                            }

                        } // container updates-ignored

                        container bad-routes {
                            description "Enter the bad-routes context";

                            leaf total {
                                type yang:counter32;
                                description "The number of routes, in valid RIPng packets, which were ignored for any reason (e.g. unknown address family, or invalid metric).";
                            }

                            leaf last-5min {
                                type yang:counter32;
                                description "The number of routes, in valid RIPng packets, which were ignored for any reason (e.g. unknown address family, or invalid metric) in the last 5 minutes.";
                            }

                            leaf last-1min {
                                type yang:counter32;
                                description "The number of routes, in valid RIPng packets, which were ignored for any reason (e.g. unknown address family, or invalid metric) in the last minute.";
                            }

                        } // container bad-routes

                        container requests-received {
                            description "Enter the requests-received context";

                            leaf total {
                                type yang:counter32;
                                description "The number of RIPng request packets received.";
                            }

                            leaf last-5min {
                                type yang:counter32;
                                description "The number RIPng request packets received in the last 5 minutes.";
                            }

                            leaf last-1min {
                                type yang:counter32;
                                description "The number RIPng request packets received in the last minute.";
                            }

                        } // container requests-received

                        container requests-ignored {
                            description "Enter the requests-ignored context";

                            leaf total {
                                type yang:counter32;
                                description "The number of RIPng request packets received that were subsequently discarded for any reason.";
                            }

                            leaf last-5min {
                                type yang:counter32;
                                description "The number of RIPng request packets received in the last 5 minutes that were subsequently discarded for any reason.";
                            }

                            leaf last-1min {
                                type yang:counter32;
                                description "The number of RIPng request packets received in the last minute that were subsequently discarded for any reason.";
                            }

                        } // container requests-ignored

                    } // container statistics

                } // list neighbor

            } // list group

        } // container ripng

    } // grouping state-svc-vprn-ripng

}
