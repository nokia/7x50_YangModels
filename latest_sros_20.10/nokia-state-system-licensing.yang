submodule nokia-state-system-licensing {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Nokia YANG Data model with operational state for system license parameters on SR OS based routers.

         Copyright 2016 Nokia. All rights reserved. Reproduction of this document
         is authorized on the condition that the foregoing copyright notice is included.

         This nokia-state-system-licensing YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping state-system-licensing {
        container licensing {
            description "Enter the licensing context";

            leaf uuid {
                type types-sros:description;
                description
                    "Indicates the UUID of this system for
                     licensing.";
            }

            leaf product {
                type types-sros:description;
                description
                    "Indicates the type of license required
                     with this system.";
            }

            leaf state {
                type enumeration {
                    enum "unlicensed"                   { value 0; }
                    enum "licensed"                     { value 1; }
                    enum "invalid-license"              { value 2; }
                    enum "expired-license"              { value 3; }
                }
                description "Indicates the state of the system licensing.";
            }

            leaf reboot-pending {
                type boolean;
                description
                    "Indicates if a system reboot is pending due to
                     licensing violation.";
            }

            container active-license {
                description "Enter the active-license context";

                leaf uuid {
                    type types-sros:description;
                    description "Indicates the target UUID of this system license.";
                }

                leaf name {
                    type types-sros:description;
                    description "Indicates the name associated with this license.";
                }

                leaf description {
                    type types-sros:description;
                    description "Indicates the description of this license.";
                }

                leaf product {
                    type types-sros:description;
                    description "Indicates the product this license is for.";
                }

                leaf version {
                    type types-sros:description;
                    description "Indicates the software version this license is for.";
                }

                leaf issue-date-time {
                    type yang:date-and-time;
                    description "Indicates the date and time license was issued.";
                }

                leaf start-date-time {
                    type yang:date-and-time;
                    description "Indicates the date and time license becomes valid.";
                }

                leaf end-date-time {
                    type yang:date-and-time;
                    description "Indicates the date and time license expires.";
                }

            } // container active-license

            list available-license {
                key "index";
                description "Enter the available-license list instance";

                leaf index {
                    type uint32;
                    description "Indicates the index of the matched license.";
                }

                leaf uuid {
                    type types-sros:description;
                    description "Indicates the target UUID of this system license.";
                }

                leaf name {
                    type types-sros:description;
                    description "Indicates the name associated with this license.";
                }

                leaf description {
                    type types-sros:description;
                    description "Indicates the description of this license.";
                }

                leaf product {
                    type types-sros:description;
                    description "Indicates the product this license is for.";
                }

                leaf version {
                    type types-sros:description;
                    description "Indicates the software version this license is for.";
                }

                leaf issue-date-time {
                    type yang:date-and-time;
                    description "Indicates the date and time license was issued.";
                }

                leaf start-date-time {
                    type yang:date-and-time;
                    description "Indicates the date and time license becomes valid.";
                }

                leaf end-date-time {
                    type yang:date-and-time;
                    description "Indicates the date and time license expires.";
                }

            } // list available-license

            list licensed-feature {
                key "group name";
                description "Enter the licensed-feature list instance";

                leaf group {
                    type enumeration {
                        enum "system"                       { value 0; }
                        enum "services"                     { value 1; }
                        enum "nsp"                          { value 2; }
                        enum "isa"                          { value 3; }
                        enum "iom"                          { value 4; }
                        enum "mda"                          { value 5; }
                        enum "ports"                        { value 6; }
                    }
                    description "Indicates the licensing group.";
                }

                leaf name {
                    type types-sros:named-item-or-empty;
                    description "Indicates the name of the licensed feature.";
                }

                leaf description {
                    type types-sros:description;
                    description "Indicates the description of this licensed feature.";
                }

                leaf type {
                    type enumeration {
                        enum "unknown"                      { value 0; }
                        enum "pool"                         { value 1; }
                        enum "rtu"                          { value 2; }
                    }
                    description "Indicates the type of feature license.";
                }

                leaf pool-size {
                    type int32;
                    description "Indicates the size of the license pool.";
                }

                leaf allocated {
                    type uint32;
                    description
                        "Indicates the number of these licenses currently allocated
                         in the system.";
                }

                leaf present {
                    type boolean;
                    description
                        "Indicates if the current system license grants the right to use
                         the feature on this system.";
                }

                leaf state {
                    type enumeration {
                        enum "unknown"                      { value 0; }
                        enum "valid"                        { value 1; }
                        enum "error"                        { value 2; }
                        enum "violation"                    { value 3; }
                    }
                    description
                        "Indicates the state of the license for this feature.
                         valid     - No issue with application license
                         error     - Insufficient licensing has been detected.
                         violation - License violation has been detected.";
                }

            } // list licensed-feature

        } // container licensing

    } // grouping state-system-licensing

}
