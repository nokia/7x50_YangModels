submodule nokia-state-multilink-bundle {

    yang-version "1.1";

    belongs-to nokia-state { prefix "state"; }

    import ietf-yang-types                { prefix "yang"; }
    import nokia-sros-yang-extensions     { prefix "sros-ext"; }
    import nokia-types-port               { prefix "types-port"; }
    import nokia-types-sros               { prefix "types-sros"; }


    sros-ext:sros-major-release "rel20";

    organization "Nokia";

    contact
        "Nokia SR OS Support
         Web: <http://www.nokia.com>";

    description
        "Nokia YANG Data model with operational state for multilink-bundle ports on SR OS based routers.

         Copyright 2016 Nokia. All rights reserved. Reproduction of this document
         is authorized on the condition that the foregoing copyright notice is included.

         This nokia-state-multilink-bundle YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-04";

    grouping state-multilink-bundle {
        list multilink-bundle {
            key "bundle-id";
            description "Enter the multilink-bundle list instance";

            leaf bundle-id {
                type types-sros:port;
                description "Multilink bundle associated with the IP interface";
            }

            leaf port-state {
                type types-port:port-state;
                description
                    "Indicates the state level of this port. A value of 'none' indicates the
                     port is either in its initial creation state or is just about to
                     be deleted.  A value of 'ghost' represents a port that is not
                     physically present.  This state may represent a pre-provisioned
                     port.  A value of 'link-down' represents a port that is physically
                     present but does not have a link.  The 'link-up' state represents a
                     port that is physically present and has physical link present.
                     A port in 'up' state is ready to pass some kinds of traffic. The
                     'diagnose' state represents the port undergoing diagnostic test.";
            }

            leaf previous-state {
                type types-port:port-state;
                description
                    "Indicates the state that the port transitioned from, into  the current state
                     level of the port indicated by 'port-state'.";
            }

            leaf active-links {
                type uint32;
                description "Indicates the current number of active links belonging to this bundle.";
            }

            leaf input-discards {
                type yang:counter32;
                description "Indicates the number of LCP packets that were discarded.";
            }

            leaf oper-mtu {
                type uint32;
                units "bytes";
                description "Indicates the operational MTU of the bundle.";
            }

            leaf oper-mrru {
                type uint32;
                units "bytes";
                description "Indicates the operational value of Max Received Reconstructed Unit (MRRU).";
            }

            leaf oper-state {
                type types-sros:oper-state;
                description "Indicates the current operational status of this port.";
            }

            leaf peer-mrru {
                type uint32;
                units "bytes";
                description "Indicates the MRRU value sent by the peer during negotiation.";
            }

            leaf total-links {
                type uint32;
                description "Indicates the total number of links configured for this bundle.";
            }

            leaf primary-member-port {
                type types-sros:port;
                description "Indicates the TmnxPortID of the primary member of this bundle.";
            }

            leaf up-time {
                type uint32;
                units "seconds";
                description "Indicates the time since the bundle is operationally in service.";
            }

            list member {
                key "channel-id";
                description "Enter the member list instance";

                leaf channel-id {
                    type types-sros:port;
                    description "Uniquely identifies the multilink bundle member.";
                }

                leaf active {
                    type boolean;
                    description "Indicates if the member is active in the multilink bundle.";
                }

                leaf down-reason {
                    type enumeration {
                        enum "none"                         { value 0; }
                        enum "out-of-service"               { value 1; }
                        enum "red-diff-delay-exceeded"      { value 2; }
                        enum "mismatch-end-point-discriminator" { value 3; }
                        enum "peer-not-bundle-member"       { value 4; }
                        enum "under-negotiation"            { value 5; }
                        enum "peer-invalid-header-format"   { value 6; }
                        enum "other"                        { value 7; }
                    }
                    description "Indicates the reason the member of the multilink bundle is down.";
                }

                leaf up-time {
                    type uint32;
                    units "seconds";
                    description "Indicates the time since the bundle member has been active.";
                }

            } // list member

            container mlppp {
                description "Enter the mlppp context";

                list control-protocol {
                    key "protocol";
                    description "Enter the control-protocol list instance";

                    leaf protocol {
                        type enumeration {
                            enum "lcp"                          { value 1; }
                            enum "ipcp"                         { value 2; }
                            enum "mplscp"                       { value 3; }
                            enum "bcp"                          { value 4; }
                            enum "osicp"                        { value 5; }
                            enum "lqr"                          { value 6; }
                            enum "ipv6cp"                       { value 7; }
                        }
                        description "Indicates the control protocol type.";
                    }

                    leaf state {
                        type enumeration {
                            enum "initial"                      { value 1; }
                            enum "starting"                     { value 2; }
                            enum "closed"                       { value 3; }
                            enum "stopped"                      { value 4; }
                            enum "closing"                      { value 5; }
                            enum "stopping"                     { value 6; }
                            enum "request-sent"                 { value 7; }
                            enum "ack-received"                 { value 8; }
                            enum "ack-sent"                     { value 9; }
                            enum "opened"                       { value 10; }
                        }
                        description
                            "Indicates the current state of the PPP Control Protocol
                             on this interface.";
                    }

                    leaf state-last-changed {
                        type yang:date-and-time;
                        description "Indicates the last time the value of state changed.";
                    }

                    leaf restart-count {
                        type yang:counter32;
                        description
                            "Indicates the number of times the control protocol has reached
                             the 'opened' state.";
                    }

                    leaf restart-count-last-cleared {
                        type yang:date-and-time;
                        description "Indicates the last time restart-count has been reset to zero.";
                    }

                } // list control-protocol

            } // container mlppp

        } // list multilink-bundle

    } // grouping state-multilink-bundle

}
