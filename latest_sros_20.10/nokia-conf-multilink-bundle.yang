submodule nokia-conf-multilink-bundle {

    yang-version "1.1";

    belongs-to nokia-conf { prefix "conf"; }

    import nokia-sros-yang-extensions     { prefix "sros-ext"; }
    import nokia-types-sros               { prefix "types-sros"; }

    include nokia-conf-groups;
    include nokia-conf-qos;

    sros-ext:sros-major-release "rel20";

    organization "Nokia";

    contact
        "Nokia SR OS Support
         Web: <http://www.nokia.com>";

    description
        "Nokia YANG Data model to configure multilink-bundle ports on SR OS based routers.

         Copyright 2016 Nokia. All rights reserved. Reproduction of this document
         is authorized on the condition that the foregoing copyright notice is included.

         This nokia-conf-multilink-bundle YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-08-04";

    grouping conf-multilink-bundle {
        list multilink-bundle {
            key "bundle-id";
            description "Enter the multilink-bundle list instance";

            leaf bundle-id {
                type types-sros:port;
                description "The identifier which uniquely identifies the multilink bundle.";
            }

            leaf admin-state {
                type types-sros:admin-state;
                default "disable";
                description "Specifies the desired administrative state of this bundle.";
            }

            leaf description {
                type types-sros:long-description;
                description "Text description";
            }

            leaf fragment-threshold {
                type union {
                    type uint32 {
                        range "128..512";
                    }
                    type enumeration {
                        enum "unlimited"                    { value 0; }
                    }
                }
                units "bytes";
                sros-ext:auto-restart-to-modify;
                default "128";
                description "Configure the maximum bytes of a fragment transmitted across the multilink bundle.";
            }

            leaf interleave-fragment {
                type boolean;
                default "false";
                description "Enable/disable the LFI function on the given multilink bundle.";
            }

            leaf minimum-links {
                type uint32 {
                    range "1..8";
                }
                default "1";
                description "Configure the minimum links that must be active for the bundle to be active.";
            }

            leaf mrru {
                type uint32 {
                    range "1500..9206";
                }
                units "bytes";
                sros-ext:auto-restart-to-modify;
                description "Configure the Maximum Received Reconstructed Unit.";
            }

            leaf protect-bundle {
                type leafref {
                    path "../../multilink-bundle/bundle-id";
                }
                sros-ext:immutable;
                description "Configure the protection bundle that is part of this BPG.";
            }

            leaf short-sequence {
                type boolean;
                sros-ext:auto-restart-to-modify;
                default "false";
                description "Enable/disable the use of short sequence by MLPPP bundles.";
            }

            leaf working-bundle {
                type leafref {
                    path "../../multilink-bundle/bundle-id";
                }
                sros-ext:immutable;
                description "Configure the working bundle that is part of this BPG.";
            }

            leaf yellow-differential-delay {
                type uint32 {
                    range "1..25";
                }
                units "milliseconds";
                description "Configure the yellow warning threshold (in milliseconds) of differential delay for members.";
            }

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            container red-differential {
                description "Enter the red-differential context";

                leaf delay {
                    type uint32 {
                        range "1..50";
                    }
                    units "milliseconds";
                    description "Configure the maximum acceptable differential delay for members.";
                }

                leaf action {
                    type enumeration {
                        enum "down"                         { value 1; }
                    }
                    description "Configure the action to be taken when the differential delay exceeds the threshold configured in red-differential/delay.";
                }

            } // container red-differential

            list member {
                key "channel-id";
                description "Add a list entry for member";

                leaf channel-id {
                    type types-sros:port;
                    description "Uniquely identifies the multilink bundle member.";
                }

            } // list member

            container mlppp {
                description "Enter the mlppp context";

                leaf magic-number {
                    type boolean;
                    default "false";
                    description "Enable/disable magic-number loopback detection.";
                }

                leaf multiclass {
                    type uint32 {
                        range "2..4";
                    }
                    description "Configure MLPPP Multiclass attributes.";
                }

                leaf stateless-aps-switchover {
                    type boolean;
                    default "false";
                    description "Enable/disable stateless APS switchover.";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                container endpoint-discriminator {
                    description "Enter the endpoint-discriminator context";

                    leaf class {
                        type enumeration {
                            enum "null"                         { value 0; }
                            enum "ip-address"                   { value 2; }
                            enum "global-mac-address"           { value 3; }
                        }
                        description "Configure the endpoint discriminator class type.";
                    }

                    leaf discriminator-id {
                        type types-sros:ipv4-address;
                        description "Configure the endpoint descriminator identifier.";
                    }

                } // container endpoint-discriminator

                container egress {
                    description "Enter the egress context";

                    leaf qos-profile {
                        type leafref {
                            path "../../../../qos/mlppp-profile-egress/mc-mlppp-egress-prof-index";
                        }
                        description "Configure egress mlppp qos-profile.";
                    }

                } // container egress

                container ingress {
                    description "Enter the ingress context";

                    leaf qos-profile {
                        type leafref {
                            path "../../../../qos/mlppp-profile-ingress/mc-mlppp-ingress-prof-index";
                        }
                        description "Configure ingress mlppp qos-profile.";
                    }

                } // container ingress

            } // container mlppp

        } // list multilink-bundle

    } // grouping conf-multilink-bundle

}
