submodule nokia-conf-eth-cfm {

    yang-version "1.1";

    belongs-to nokia-conf { prefix "conf"; }

    import nokia-sros-yang-extensions     { prefix "sros-ext"; }
    import nokia-types-eth-cfm            { prefix "types-eth-cfm"; }
    import nokia-types-services           { prefix "types-services"; }
    import nokia-types-sros               { prefix "types-sros"; }

    include nokia-conf-groups;

    sros-ext:sros-major-release "rel20";

    organization "Nokia";

    contact
        "Nokia SR OS Support
         Web: <http://www.nokia.com>";

    description
        "Nokia YANG Data model to configure eth-cfm on SR OS based routers.

         Copyright 2016 Nokia. All rights reserved. Reproduction of this document
         is authorized on the condition that the foregoing copyright notice is included.

         This nokia-conf-eth-cfm YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-03";

    grouping conf-eth-cfm {
        container eth-cfm {
            description "Enter the eth-cfm context";

            leaf-list apply-groups {
                type leafref {
                    path "../../groups/group/name";
                }
                max-elements 8;
                ordered-by user;
                description "Apply a configuration group at this level";
            }

            leaf-list apply-groups-exclude {
                type leafref {
                    path "../../groups/group/name";
                }
                max-elements 8;
                ordered-by user;
                description "Exclude a configuration group at this level";
            }

            list domain {
                key "md-admin-name";
                description "Enter the domain list instance";

                leaf md-admin-name {
                    type types-eth-cfm:admin-name;
                    description "Unique domain name";
                }

                leaf level {
                    type types-eth-cfm:mp-level;
                    sros-ext:immutable;
                    mandatory true;
                    description "Maintenance Domain Level (MD Level)";
                }

                leaf md-index {
                    type uint32 {
                        range "1..max";
                    }
                    sros-ext:immutable;
                    description "The index of the Maintenance Domain (MD)";
                }

                leaf-list apply-groups {
                    type leafref {
                        path "../../../groups/group/name";
                    }
                    max-elements 8;
                    ordered-by user;
                    description "Apply a configuration group at this level";
                }

                leaf-list apply-groups-exclude {
                    type leafref {
                        path "../../../groups/group/name";
                    }
                    max-elements 8;
                    ordered-by user;
                    description "Exclude a configuration group at this level";
                }

                choice md-name {
                    mandatory true;
                    case dns {

                        leaf dns {
                            type string {
                                length "1..43";
                            }
                            sros-ext:immutable;
                            description "Domain name like text string derived from a DNS name";
                        }

                    }
                    case mac {

                        leaf mac {
                            type string {
                                length "13..23";
                                pattern "[0-9a-fA-F]{1,2}(:[0-9a-fA-F]{1,2}){5}-[0-9]{1,5}";
                            }
                            sros-ext:immutable;
                            description "Maintenance domain MAC name";
                        }

                    }
                    case name {

                        leaf name {
                            type string {
                                length "1..43";
                            }
                            sros-ext:immutable;
                            description "Maintenance Domain name";
                        }

                    }
                    case format {

                        leaf format {
                            type enumeration {
                                enum "none"                         { value 0; }
                            }
                            sros-ext:immutable;
                            description "Maintenance domain name not to be provided";
                        }

                    }
                }
                list association {
                    key "ma-admin-name";
                    description "Enter the association list instance";

                    leaf ma-admin-name {
                        type types-eth-cfm:admin-name;
                        description "Domain association name";
                    }

                    leaf ma-index {
                        type uint32 {
                            range "1..max";
                        }
                        sros-ext:immutable;
                        description "Maintenance Association (MA) table index";
                    }

                    leaf ccm-interval {
                        type types-eth-cfm:ccm-interval-type;
                        description "CCM transmission interval for all MEPs in association";
                    }

                    leaf auto-mep-discovery {
                        type boolean;
                        default "false";
                        description "Enable the ability to auto-discover remote MEPs in the network";
                    }

                    leaf facility-id-permission {
                        type types-eth-cfm:facility-id-permission-type;
                        default "none";
                        description "Sender ID TLV information for facility base MEPs";
                    }

                    leaf-list apply-groups {
                        type leafref {
                            path "../../../../groups/group/name";
                        }
                        max-elements 8;
                        ordered-by user;
                        description "Apply a configuration group at this level";
                    }

                    leaf-list apply-groups-exclude {
                        type leafref {
                            path "../../../../groups/group/name";
                        }
                        max-elements 8;
                        ordered-by user;
                        description "Exclude a configuration group at this level";
                    }

                    choice ma-name {
                        mandatory true;
                        description
                            "The Maintenance Domain Association name

                             It is the part of the Maintenance Association Identifier
                             which is unique within the Maintenance Domain Name and is
                             appended to the Maintenance Domain Name to form the
                             Maintenance Association Identifier (MAID).";
                        case icc-based {

                            leaf icc-based {
                                type string {
                                    length "8..13";
                                }
                                sros-ext:immutable;
                                description "Maintenance Association name in ICC-based format";
                            }

                        }
                        case integer {

                            leaf integer {
                                type uint32 {
                                    range "0..65535";
                                }
                                sros-ext:immutable;
                                description "Maintenance Association name in integer format";
                            }

                        }
                        case string {

                            leaf string {
                                type string {
                                    length "1..45";
                                }
                                sros-ext:immutable;
                                description "Maintenance Association name in raw ASCII string format";
                            }

                        }
                        case vid {

                            leaf vid {
                                type uint32 {
                                    range "0..4094";
                                }
                                sros-ext:immutable;
                                description "Primary VLAN ID for the Maintenance Association name";
                            }

                        }
                        case vpn-id {

                            leaf vpn-id {
                                type string {
                                    length "0..15";
                                    pattern "[0-9A-F]{6}(:[0-9A-F]{8})";
                                }
                                sros-ext:immutable;
                                description "VPN ID for the Maintenance Association name";
                            }

                        }
                    }
                    container ccm-hold-time {
                        description "Enter the ccm-hold-time context";

                        leaf down {
                            when "../../ccm-interval = '10ms' or ../../ccm-interval = '100ms'";
                            type uint32 {
                                range "1..1000";
                            }
                            units "centiseconds";
                            description "Additional time before a MEP declares a fault, in CCM timeout conditions";
                        }

                    } // container ccm-hold-time

                    list bridge-identifier {
                        key "bridge-name";
                        max-elements 1;
                        description "Enter the bridge-identifier list instance";

                        leaf bridge-name {
                            type types-services:service-name;
                            description "Bridge name that links to the service";
                        }

                        leaf vlan {
                            type int32 {
                                range "1..4094";
                            }
                            description "VLAN ID for the default domain index";
                        }

                        leaf mhf-creation {
                            type types-eth-cfm:tmnx-mhf-creation-type;
                            default "none";
                            description "MIP method of creation";
                        }

                        leaf id-permission {
                            type types-eth-cfm:facility-id-permission-type;
                            default "none";
                            description "Strategy for the inclusion of Sender ID TLV information";
                        }

                        leaf mip-ltr-priority {
                            type types-eth-cfm:frame-priority;
                            default "7";
                            description "Priority of the Linktrace Response Message (ETH-LTR) from a MIP";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list bridge-identifier

                    list remote-mep {
                        key "mep-id";
                        description "Enter the remote-mep list instance";

                        leaf mep-id {
                            type types-eth-cfm:mep-id-type;
                            description "Remote MEP ID";
                        }

                        leaf remote-mac {
                            type types-sros:mac-unicast-address-no-zero;
                            description "Remote MAC Address for transmitting CFM packets to remote MEPs";
                        }

                        leaf-list apply-groups {
                            type leafref {
                                path "../../../../../groups/group/name";
                            }
                            max-elements 8;
                            ordered-by user;
                            description "Apply a configuration group at this level";
                        }

                        leaf-list apply-groups-exclude {
                            type leafref {
                                path "../../../../../groups/group/name";
                            }
                            max-elements 8;
                            ordered-by user;
                            description "Exclude a configuration group at this level";
                        }

                    } // list remote-mep

                } // list association

            } // list domain

        } // container eth-cfm

    } // grouping conf-eth-cfm

}
