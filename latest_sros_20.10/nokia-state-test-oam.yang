submodule nokia-state-test-oam {

    yang-version "1.1";

    belongs-to nokia-state { prefix "state"; }

    import ietf-yang-types                { prefix "yang"; }
    import nokia-sros-yang-extensions     { prefix "sros-ext"; }
    import nokia-types-sros               { prefix "types-sros"; }


    sros-ext:sros-major-release "rel20";

    organization "Nokia";

    contact
        "Nokia SR OS Support
         Web: <http://www.nokia.com>";

    description
        "Nokia YANG Data model with operational state for OAM test parameters configuration on SR OS based routers.

         Copyright 2016 Nokia. All rights reserved. Reproduction of this document
         is authorized on the condition that the foregoing copyright notice is included.

         This nokia-state-test-oam YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-23";

    grouping state-test-oam {
        container test-oam {
            description "Enter the test-oam context";

            container twamp {
                description "Enter the twamp context";

                container server {
                    description "Enter the server context";

                    container statistics {
                        description "Enter the statistics context";

                        leaf session-count {
                            type uint32 {
                                range "0..128";
                            }
                            description "The number of currently in-progress sessions";
                        }

                        leaf session-completed {
                            type yang:counter32;
                            description "The number of test sessions completed";
                        }

                        leaf session-rejected {
                            type yang:counter32;
                            description "The number of test sessions rejected";
                        }

                        leaf test-packet-received {
                            type yang:counter32;
                            description "The number of TWAMP test packets received";
                        }

                        leaf test-packet-transmitted {
                            type yang:counter32;
                            description "The number of TWAMP test packets sent";
                        }

                        leaf oper-state {
                            type enumeration {
                                enum "unknown"                      { value 1; }
                                enum "in-service"                   { value 2; }
                                enum "out-of-service"               { value 3; }
                                enum "transition"                   { value 4; }
                            }
                            description "State of TWAMP server";
                        }

                        leaf up-time {
                            type uint32;
                            units "seconds";
                            description "Time elapsed since the most recent transition";
                        }

                        leaf connection-count {
                            type uint32 {
                                range "0..64";
                            }
                            description "Control connections currently managed by the TWAMP server";
                        }

                        leaf connections-rejected {
                            type yang:counter32;
                            description "Control connection requests which have been rejected by the TWAMP server";
                        }

                        leaf capabilities {
                            type bits {
                                bit unauthenticated                { position 0; }
                                bit authenticated                  { position 1; }
                                bit encrypted                      { position 2; }
                                bit unauthTestEncryptControl       { position 3; }
                                bit individualSessionControl       { position 4; }
                                bit reflectOctets                  { position 5; }
                                bit symmetricalSizeSenderTestPkt   { position 6; }
                                bit ikeV2DerivedMode               { position 7; }
                                bit dscpAndEcnMonitoring           { position 8; }
                            }
                            description "The set of standard TWAMP protocol options supported by the TWAMP server";
                        }

                        leaf sessions-aborted {
                            type yang:counter32;
                            description "Test sessions aborted by the TWAMP server";
                        }

                    } // container statistics

                    list prefix {
                        key "ip-prefix";
                        description "Enter the prefix list instance";

                        leaf ip-prefix {
                            type types-sros:ip-unicast-prefix;
                            description "Prefix to match against TWAMP client address";
                        }

                        container statistics {
                            description "Enter the statistics context";

                            leaf session-count {
                                type uint32 {
                                    range "0..128";
                                }
                                description "The number of currently in-progress sessions";
                            }

                            leaf session-completed {
                                type yang:counter32;
                                description "The number of test sessions completed";
                            }

                            leaf session-rejected {
                                type yang:counter32;
                                description "The number of test sessions rejected";
                            }

                            leaf test-packet-received {
                                type yang:counter32;
                                description "The number of TWAMP test packets received";
                            }

                            leaf test-packet-transmitted {
                                type yang:counter32;
                                description "The number of TWAMP test packets sent";
                            }

                            leaf sessions-aborted {
                                type yang:counter32;
                                description "Test sessions aborted by the TWAMP server for the prefix";
                            }

                            leaf connection-count {
                                type uint32 {
                                    range "0..64";
                                }
                                description "The number of control connections currently managed by the TWAMP server for the prefix";
                            }

                            leaf connections-rejected {
                                type yang:counter32;
                                description "Control connection requests which have been rejected by the TWAMP server for the prefix";
                            }

                        } // container statistics

                        list connection-statistics {
                            key "client-address sequence-number";
                            description "Enter the connection-statistics list instance";

                            leaf client-address {
                                type types-sros:ip-address;
                                description "The address of the specified session's TWAMP Session-Sender";
                            }

                            leaf sequence-number {
                                type uint32 {
                                    range "1..4294967295";
                                }
                                description "Control connection's sequence number";
                            }

                            leaf session-count {
                                type uint32 {
                                    range "0..128";
                                }
                                description "The number of currently in-progress sessions";
                            }

                            leaf session-completed {
                                type yang:counter32;
                                description "The number of test sessions completed";
                            }

                            leaf session-rejected {
                                type yang:counter32;
                                description "The number of test sessions rejected";
                            }

                            leaf test-packet-received {
                                type yang:counter32;
                                description "The number of TWAMP test packets received";
                            }

                            leaf test-packet-transmitted {
                                type yang:counter32;
                                description "The number of TWAMP test packets sent";
                            }

                            leaf oper-state {
                                type enumeration {
                                    enum "setting-up"                   { value 1; }
                                    enum "ready"                        { value 2; }
                                    enum "running"                      { value 3; }
                                }
                                description "State of a control connection managed by the TWAMP server";
                            }

                            leaf idle-time {
                                type uint32;
                                units "seconds";
                                description "Elapsed time since a TWAMP message was received on this control connection";
                            }

                        } // list connection-statistics

                    } // list prefix

                    list client {
                        key "client-address connection-sequence-number session-sequence-number";
                        description "Enter the client list instance";

                        leaf client-address {
                            type types-sros:ip-address;
                            description "The address of the specified session's TWAMP Session-Sender.";
                        }

                        leaf connection-sequence-number {
                            type uint32 {
                                range "1..4294967295";
                            }
                            description "Control connection's sequence number";
                        }

                        leaf session-sequence-number {
                            type uint32 {
                                range "1..4294967295";
                            }
                            description "TWAMP test session's sequence number";
                        }

                        leaf session-id {
                            type binary {
                                length "16";
                            }
                            description "The session identifier (SID) for the specified session";
                        }

                        leaf oper-state {
                            type enumeration {
                                enum "create"                       { value 1; }
                                enum "active"                       { value 2; }
                                enum "stop"                         { value 3; }
                            }
                            description "State of the specified session";
                        }

                        leaf sender-address {
                            type types-sros:ip-unicast-address;
                            description "The address of the specified session's TWAMP Session-Sender";
                        }

                        leaf sender-udp-port {
                            type types-sros:tcp-udp-port;
                            description "The Source UDP port field of test packets sent by the specified session's TWAMP Session-Sender";
                        }

                        leaf reflector-address {
                            type types-sros:ip-unicast-address;
                            description "The address of the specified session's TWAMP Session-Reflector";
                        }

                        leaf reflector-udp-port {
                            type types-sros:tcp-udp-port;
                            description "The UDP listen port of the specified session's TWAMP Session-Reflector";
                        }

                    } // list client

                } // container server

            } // container twamp

        } // container test-oam

    } // grouping state-test-oam

}
