submodule nokia-conf-router-bgp {

    yang-version "1.1";

    belongs-to nokia-conf { prefix "conf"; }

    import nokia-sros-yang-extensions     { prefix "sros-ext"; }
    import nokia-types-bgp                { prefix "types-bgp"; }
    import nokia-types-router             { prefix "types-router"; }
    import nokia-types-sros               { prefix "types-sros"; }

    include nokia-conf-bmp;
    include nokia-conf-groups;
    include nokia-conf-system;
    include nokia-conf-system-security;

    sros-ext:sros-major-release "rel20";

    organization "Nokia";

    contact
        "Nokia SR OS Support
         Web: <http://www.nokia.com>";

    description
        "Nokia YANG Data model to configure bgp protocol on SR OS based routers.

         Copyright 2016 Nokia. All rights reserved. Reproduction of this document
         is authorized on the condition that the foregoing copyright notice is included.

         This nokia-conf-router-bgp YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-09-16";

    grouping conf-router-bgp {
        container bgp {
            presence "Enter the 'bgp' context";
            description "Enable the bgp context";

            leaf description {
                type types-sros:description;
                description "Text description";
            }

            leaf connect-retry {
                type int32 {
                    range "1..65535";
                }
                default "120";
                description "BGP connect retry timer value";
            }

            leaf admin-state {
                type types-sros:admin-state;
                default "enable";
                description "Administrative state of the BGP instance";
            }

            leaf keepalive {
                type int32 {
                    range "0..21845";
                }
                default "30";
                description "Time after which the BGP KEEPALIVE message is sent";
            }

            leaf damping {
                type boolean;
                default "false";
                description "Use BGP route damping to reduce route flap";
            }

            leaf local-preference {
                type uint32;
                default "100";
                description "Default local preference if not in incoming routes";
            }

            leaf loop-detect {
                type types-bgp:loop-detect;
                default "ignore-loop";
                description "Strategy for loop detection in the AS path";
            }

            leaf loop-detect-threshold {
                type uint32 {
                    range "0..15";
                }
                default "0";
                description "Threshold for the global ASN in a received AS path";
            }

            leaf selective-label-ipv4-install {
                type boolean;
                default "false";
                description "Enable/Disable selective download for bgp label-ipv4 routes.";
            }

            leaf min-route-advertisement {
                type int16 {
                    range "1..255";
                }
                default "30";
                description "Minimum time before a prefix can be advertised to peer";
            }

            leaf aggregator-id-zero {
                type boolean;
                default "false";
                description "Set router ID in the BGP AGGREGATOR attribute to 0";
            }

            leaf preference {
                type uint32 {
                    range "1..255";
                }
                default "170";
                description "Route preference for routes learned from all peers";
            }

            leaf block-prefix-sid {
                type boolean;
                default "false";
                description "Block the prefix SID attribute";
            }

            leaf multihop {
                type int32 {
                    range "1..255";
                }
                description "TTL in IP packet headers for EBGP peers multi-hops away";
            }

            leaf med-out {
                type union {
                    type uint32;
                    type enumeration {
                        enum "igp-cost"                     { value -1; }
                    }
                }
                description "Default MED attribute value to advertise to peers";
            }

            leaf authentication-key {
                type types-sros:encrypted-leaf {
                    length "1..370";
                }
                description "BGP authentication key for all peers";
            }

            leaf client-reflect {
                type boolean;
                default "true";
                description "Allow client reflection of routes by route reflector";
            }

            leaf vpn-apply-export {
                type boolean;
                default "false";
                description "Apply base-instance BGP export policies to VPN routes";
            }

            leaf vpn-apply-import {
                type boolean;
                default "false";
                description "Apply base-instance import route policies to VPN routes";
            }

            leaf asn-4-byte {
                type boolean;
                default "true";
                description "Advertise support for 4-byte ASNs";
            }

            leaf path-mtu-discovery {
                type boolean;
                default "false";
                description "Enable Path MTU Discovery";
            }

            leaf enforce-first-as {
                type boolean;
                default "false";
                description "Enforce the configured peer AS value in received routes";
            }

            leaf initial-send-delay-zero {
                type boolean;
                default "false";
                description "Send BGP updates as soon as session comes up";
            }

            leaf router-id {
                type types-sros:ipv4-address;
                description "Router ID for the BGP instance in the AS";
            }

            leaf inter-as-vpn {
                type boolean;
                default "false";
                description "Allow advertisement of VPN routes across AS boundaries";
            }

            leaf purge-timer {
                type uint32 {
                    range "1..60";
                }
                default "10";
                description "Maximum time before stale routes are purged";
            }

            leaf route-table-install {
                type boolean;
                default "true";
                description "Install all IPv4 and IPv6 BGP routes in FIB and RTM";
            }

            leaf ibgp-multipath {
                type boolean;
                default "false";
                description "Enable IBGP multipath load balancing";
            }

            leaf rr-vpn-forwarding {
                type boolean;
                default "false";
                description "Allow route reflector to forward VPN-IP routes";
            }

            leaf bfd-liveness {
                type boolean;
                default "false";
                description "Enable BFD";
            }

            leaf fast-external-failover {
                type boolean;
                default "true";
                description "Drop external BGP session immediately when link fails";
            }

            leaf advertise-inactive {
                type boolean;
                default "false";
                description "Advertise inactive BGP routes to peers";
            }

            leaf authentication-keychain {
                type leafref {
                    path "../../../system/security/keychains/keychain/keychain-name";
                }
                description "TCP authentication keychain for the session";
            }

            leaf mvpn-vrf-import-subtype-new {
                type boolean;
                default "false";
                description "Encode the IANA value of 0x010b in advertised routes";
            }

            leaf rapid-withdrawal {
                type boolean;
                default "false";
                description "Send BGP withdrawal UPDATE messages immediately";
            }

            leaf mp-bgp-keep {
                type boolean;
                default "false";
                description "Keep rejected VPN-IP routes in RIB-IN";
            }

            leaf peer-ip-tracking {
                type boolean;
                default "false";
                description "Enable BGP peer tracking";
            }

            leaf split-horizon {
                type boolean;
                default "false";
                description "Prevent routes being reflected back to best-route peer";
            }

            leaf override-tunnel-elc {
                type boolean;
                default "false";
                description "Enable entropy label capability on BGP tunnels";
            }

            leaf link-state-route-export {
                type boolean;
                default "false";
                description "Allow the export of the TED NLRI database";
            }

            leaf link-state-route-import {
                type boolean;
                default "false";
                description "Allow the import of the TED NLRI database";
            }

            leaf third-party-nexthop {
                type boolean;
                default "false";
                description "Apply third-party next-hop processing to EBGP peers";
            }

            leaf dynamic-neighbor-limit {
                type uint32 {
                    range "1..8192";
                }
                description "Max dynamic BGP sessions to accept from remote peers";
            }

            leaf label-preference {
                type uint32 {
                    range "1..255";
                }
                default "170";
                description "Route preference for routes from labeled-unicast peers";
            }

            leaf peer-tracking-policy {
                type types-sros:named-item-64;
                description "Policy for BGP peer tracking on router instance";
            }

            leaf def-recv-evpn-encap {
                type types-bgp:encap;
                default "mpls";
                description "Default EVPN encapsulation type";
            }

            leaf sr-policy-import {
                type boolean;
                default "false";
                description "Import all segment routing policies into the BGP RIB";
            }

            leaf-list apply-groups {
                type leafref {
                    path "../../../groups/group/name";
                }
                max-elements 8;
                ordered-by user;
                description "Apply a configuration group at this level";
            }

            leaf-list apply-groups-exclude {
                type leafref {
                    path "../../../groups/group/name";
                }
                max-elements 8;
                ordered-by user;
                description "Exclude a configuration group at this level";
            }

            container hold-time {
                description "Enter the hold-time context";

                leaf seconds {
                    type int32 {
                        range "0|3..65535";
                    }
                    default "90";
                    description "Maximum time BGP waits between successive messages";
                }

                leaf minimum-hold-time {
                    type int32 {
                        range "0|3..65535";
                    }
                    default "0";
                    description "Minimum hold time between successive messages";
                }

            } // container hold-time

            container family {
                description "Enter the family context";

                leaf ipv4 {
                    type boolean;
                    default "true";
                    description "Advertise MP-BGP support for the IPv4 address family";
                }

                leaf vpn-ipv4 {
                    type boolean;
                    default "false";
                    description "Advertise MP-BGP support for IPv4 VPN address family";
                }

                leaf ipv6 {
                    type boolean;
                    default "false";
                    description "Advertise MP-BGP support for the IPv6 address family";
                }

                leaf mcast-ipv4 {
                    type boolean;
                    default "false";
                    description "Advertise support for the MCAST-IPv4 address family";
                }

                leaf vpn-ipv6 {
                    type boolean;
                    default "false";
                    description "Advertise MP-BGP support for IPv6 VPN address family";
                }

                leaf l2-vpn {
                    type boolean;
                    default "false";
                    description "Advertise MP-BGP support for the L2-VPN address family";
                }

                leaf mvpn-ipv4 {
                    type boolean;
                    default "false";
                    description "Advertise support for the IPv4 MCAST VPN address family";
                }

                leaf mdt-safi {
                    type boolean;
                    default "false";
                    description "Advertise MP-BGP support for MDT-SAFI address family";
                }

                leaf ms-pw {
                    type boolean;
                    default "false";
                    description "Advertise support for multi-segment PW address family";
                }

                leaf flow-ipv4 {
                    type boolean;
                    default "false";
                    description "Advertise support for the flowspec-IPv4 address family";
                }

                leaf route-target {
                    type boolean;
                    default "false";
                    description "Advertise MP-BGP support for RT constraint routes";
                }

                leaf mcast-vpn-ipv4 {
                    type boolean;
                    default "false";
                    description "Advertise support for the IPv4 VPN MCAST address family";
                }

                leaf mvpn-ipv6 {
                    type boolean;
                    default "false";
                    description "Advertise support for the IPv6 MCAST VPN address family";
                }

                leaf flow-ipv6 {
                    type boolean;
                    default "false";
                    description "Advertise support for the flowspec-IPv6 address family";
                }

                leaf evpn {
                    type boolean;
                    default "false";
                    description "Advertise MP-BGP support for the EVPN address family";
                }

                leaf mcast-ipv6 {
                    type boolean;
                    default "false";
                    description "Advertise support for the MCAST-IPv6 address family";
                }

                leaf label-ipv4 {
                    type boolean;
                    default "false";
                    description "Advertise support for the label-IPv4 address family";
                }

                leaf label-ipv6 {
                    type boolean;
                    default "false";
                    description "Advertise support for the label-IPv6 address family";
                }

                leaf bgp-ls {
                    type boolean;
                    default "false";
                    description "Advertise MP-BGP support for the BGP-LS address family";
                }

                leaf mcast-vpn-ipv6 {
                    type boolean;
                    default "false";
                    description "Advertise support for the IPv6 VPN MCAST address family";
                }

                leaf sr-policy-ipv4 {
                    type boolean;
                    default "false";
                    description "Advertise MP-BGP support for the SR-policy-IPv4 family";
                }

                leaf sr-policy-ipv6 {
                    type boolean;
                    default "false";
                    description "Advertise MP-BGP support for the SR-policy-IPv6 family";
                }

            } // container family

            container label-allocation {
                description "Enter the label-allocation context";

                container label-ipv6 {
                    description "Enter the label-ipv6 context";

                    leaf explicit-null {
                        type boolean;
                        default "true";
                        description "Apply advertised label and associated programming rules";
                    }

                } // container label-ipv6

            } // container label-allocation

            container send-default {
                description "Enter the send-default context";

                leaf ipv4 {
                    type boolean;
                    default "false";
                    description "Enable IPv4 family type";
                }

                leaf ipv6 {
                    type boolean;
                    default "false";
                    description "Enable IPv6 family type";
                }

                leaf export-policy {
                    type types-sros:named-item-64;
                    description "Export policy name";
                }

            } // container send-default

            container default-preference {
                description "Enter the default-preference context";

                leaf ebgp {
                    type uint32 {
                        range "0..255";
                    }
                    default "0";
                    description "Default preference for EBGP";
                }

                leaf ibgp {
                    type uint32 {
                        range "0..255";
                    }
                    default "0";
                    description "Default preference for IBGP";
                }

            } // container default-preference

            container default-label-preference {
                description "Enter the default-label-preference context";

                leaf ebgp {
                    type uint32 {
                        range "0..255";
                    }
                    default "0";
                    description "Default preference for EBGP";
                }

                leaf ibgp {
                    type uint32 {
                        range "0..255";
                    }
                    default "0";
                    description "Default preference for IBGP";
                }

            } // container default-label-preference

            container remove-private {
                presence "Enter the 'remove-private' context";
                description "Enable the remove-private context";

                leaf limited {
                    type boolean;
                    default "false";
                    description "Remove private ASNs up to first public ASN encountered";
                }

                leaf skip-peer-as {
                    type boolean;
                    default "false";
                    description "Keep private ASN if AS-PATH contains eBGP peer's ASN";
                }

                leaf replace {
                    type boolean;
                    default "false";
                    description "Replace private ASN with global ASN before advertising";
                }

            } // container remove-private

            container cluster {
                description "Enter the cluster context";

                leaf cluster-id {
                    type types-sros:ipv4-address;
                    description "Route reflector cluster ID";
                }

                leaf orr-location {
                    type uint32 {
                        range "1..255";
                    }
                    description "Optimal route reflection location for the cluster";
                }

                leaf allow-local-fallback {
                    type boolean;
                    default "false";
                    description "Allow fallback to RR topology location for ORR";
                }

            } // container cluster

            container ebgp-default-reject-policy {
                description "Enter the ebgp-default-reject-policy context";

                leaf import {
                    type boolean;
                    default "true";
                    description "Enable default reject import policy for external peers";
                }

                leaf export {
                    type boolean;
                    default "true";
                    description "Enable default reject export policy for external peers";
                }

            } // container ebgp-default-reject-policy

            container local-as {
                description "Enter the local-as context";

                leaf as-number {
                    type uint32 {
                        range "1..4294967295";
                    }
                    description "Local (or virtual) BGP AS number";
                }

                leaf private {
                    type boolean;
                    default "false";
                    description "Hide the local ASN in sent paths learned from peering";
                }

                leaf prepend-global-as {
                    type boolean;
                    default "true";
                    description "Prepend global AS when advertising routes to BGP peer";
                }

            } // container local-as

            container best-path-selection {
                description "Enter the best-path-selection context";

                leaf compare-origin-validation-state {
                    type boolean;
                    default "false";
                    description "Compare RPKI origin validation state of usable routes";
                }

                leaf deterministic-med {
                    type boolean;
                    default "false";
                    description "Group paths based on AS before MED attribute comparison";
                }

                leaf origin-invalid-unusable {
                    type boolean;
                    default "false";
                    description "Deem invalid routes unusable for best-path selection";
                }

                leaf ignore-nh-metric {
                    type boolean;
                    default "false";
                    description "Ignore next-hop distance in best path selection";
                }

                container always-compare-med {
                    description "Enter the always-compare-med context";

                    leaf med-value {
                        type types-bgp:med-value;
                        default "off";
                        description "Action for a missing MED attribute";
                    }

                    leaf strict-as {
                        type boolean;
                        default "true";
                        description "Compare MED only for routes from same neighbor AS";
                    }

                } // container always-compare-med

                container as-path-ignore {
                    description "Enter the as-path-ignore context";

                    leaf ipv4 {
                        type boolean;
                        default "false";
                        description "Ignore AS path length for unlabeled unicast IPv4 routes";
                    }

                    leaf vpn-ipv4 {
                        type boolean;
                        default "false";
                        description "Ignore AS path length for VPN IPv4 (SAFI 128) routes";
                    }

                    leaf ipv6 {
                        type boolean;
                        default "false";
                        description "Ignore AS path length for unlabeled unicast IPv6 routes";
                    }

                    leaf mcast-ipv4 {
                        type boolean;
                        default "false";
                        description "Ignore AS path length for IPv4 multicast routes";
                    }

                    leaf vpn-ipv6 {
                        type boolean;
                        default "false";
                        description "Ignore AS path length for VPN IPv6 (SAFI 128) routes";
                    }

                    leaf l2-vpn {
                        type boolean;
                        default "false";
                        description "Ignore AS path length for L2-VPN routes";
                    }

                    leaf mvpn-ipv4 {
                        type boolean;
                        default "false";
                        description "Ignore AS path length for IPv4 MVPN routes";
                    }

                    leaf mvpn-ipv6 {
                        type boolean;
                        default "false";
                        description "Ignore AS path length for IPv6 MVPN routes";
                    }

                    leaf mcast-ipv6 {
                        type boolean;
                        default "false";
                        description "Ignore AS path length for IPv6 multicast routes";
                    }

                    leaf label-ipv4 {
                        type boolean;
                        default "false";
                        description "Ignore AS path length for labeled-unicast IPv4 routes";
                    }

                    leaf label-ipv6 {
                        type boolean;
                        default "false";
                        description "Ignore AS path length for labeled-unicast IPv6 routes";
                    }

                } // container as-path-ignore

                container ignore-router-id {
                    presence "Enter the 'ignore-router-id' context";
                    description "Enable the ignore-router-id context";

                    container include-internal {
                        description "Enter the include-internal context";

                        leaf mvpn-ipv4 {
                            type boolean;
                            default "false";
                            description "Ignore the router IDs of MVPN-IPv4 routes";
                        }

                        leaf mvpn-ipv6 {
                            type boolean;
                            default "false";
                            description "Ignore the router IDs of MVPN-IPv6 routes";
                        }

                    } // container include-internal

                } // container ignore-router-id

                container ebgp-ibgp-equal {
                    description "Enter the ebgp-ibgp-equal context";

                    leaf ipv4 {
                        type boolean;
                        default "false";
                        description "Consider EBGP and IBGP IPv4 routes equal";
                    }

                    leaf ipv6 {
                        type boolean;
                        default "false";
                        description "Consider EBGP and IBGP IPv6 routes equal";
                    }

                    leaf vpn-ipv4 {
                        type boolean;
                        default "false";
                        description "Consider EBGP and IBGP VPN-IPv4 routes equal";
                    }

                    leaf vpn-ipv6 {
                        type boolean;
                        default "false";
                        description "Consider EBGP and IBGP VPN-IPv6 routes equal";
                    }

                    leaf label-ipv4 {
                        type boolean;
                        default "false";
                        description "Consider EBGP and IBGP label-IPv4 routes equal";
                    }

                    leaf label-ipv6 {
                        type boolean;
                        default "false";
                        description "Consider EBGP and IBGP label-IPv6 routes equal";
                    }

                } // container ebgp-ibgp-equal

            } // container best-path-selection

            container send-communities {
                description "Enter the send-communities context";

                leaf standard {
                    type boolean;
                    default "true";
                    description "Advertise the Communities attribute to peers";
                }

                leaf extended {
                    type boolean;
                    default "true";
                    description "Advertise the Extended Communities attribute to peers";
                }

                leaf large {
                    type boolean;
                    default "true";
                    description "Advertise the Large Communities attribute to peers";
                }

            } // container send-communities

            container error-handling {
                description "Enter the error-handling context";

                leaf update-fault-tolerance {
                    type boolean;
                    default "false";
                    description "Tolerate non-critical errors in UPDATE messages";
                }

            } // container error-handling

            container damp-peer-oscillations {
                presence "Enter the 'damp-peer-oscillations' context";
                description "Enable the damp-peer-oscillations context";

                leaf error-interval {
                    type uint32 {
                        range "0..2048";
                    }
                    default "30";
                    description "Time after a reset that the session must be error-free";
                }

                container idle-hold-time {
                    description "Enter the idle-hold-time context";

                    leaf initial-wait {
                        type uint32 {
                            range "0..2048";
                        }
                        default "0";
                        description "Time session remains in idle state after stabilization";
                    }

                    leaf second-wait {
                        type uint32 {
                            range "1..2048";
                        }
                        default "5";
                        description "Time that doubles after each session failure";
                    }

                    leaf max-wait {
                        type uint32 {
                            range "1..2048";
                        }
                        default "60";
                        description "Maximum session idle time after repeated instability";
                    }

                } // container idle-hold-time

            } // container damp-peer-oscillations

            container rapid-update {
                description "Enter the rapid-update context";

                leaf vpn-ipv4 {
                    type boolean;
                    default "false";
                    description "Include VPN IPv4 address family routes";
                }

                leaf vpn-ipv6 {
                    type boolean;
                    default "false";
                    description "Include VPN IPv6 address family routes";
                }

                leaf l2-vpn {
                    type boolean;
                    default "false";
                    description "Include L2 VPN address family routes";
                }

                leaf mvpn-ipv4 {
                    type boolean;
                    default "false";
                    description "Include MVPN IPv4 address family routes";
                }

                leaf mdt-safi {
                    type boolean;
                    default "false";
                    description "Include MDT SAFI address family routes";
                }

                leaf mcast-vpn-ipv4 {
                    type boolean;
                    default "false";
                    description "Include multicast VPN IPv4 address family routes";
                }

                leaf mvpn-ipv6 {
                    type boolean;
                    default "false";
                    description "Include MVPN IPv6 address family routes";
                }

                leaf evpn {
                    type boolean;
                    default "false";
                    description "Include EVPN address family routes";
                }

                leaf label-ipv4 {
                    type boolean;
                    default "false";
                    description "Include labeled IPv4 address family routes";
                }

                leaf label-ipv6 {
                    type boolean;
                    default "false";
                    description "Include labeled IPv6 address family routes";
                }

                leaf mcast-vpn-ipv6 {
                    type boolean;
                    default "false";
                    description "Include multicast VPN IPv6 address family routes";
                }

            } // container rapid-update

            container advertise-external {
                description "Enter the advertise-external context";

                leaf ipv4 {
                    type boolean;
                    default "false";
                    description "Enable support for unlabeled unicast IPv4 routes";
                }

                leaf ipv6 {
                    type boolean;
                    default "false";
                    description "Enable support for unlabeled unicast IPv6 routes";
                }

                leaf label-ipv4 {
                    type boolean;
                    default "false";
                    description "Enable support for labeled-unicast IPv4 routes";
                }

                leaf label-ipv6 {
                    type boolean;
                    default "false";
                    description "Enable support for labeled-unicast IPv6 routes";
                }

            } // container advertise-external

            container backup-path {
                description "Enter the backup-path context";

                leaf ipv4 {
                    type boolean;
                    default "false";
                    description "Enable support for unlabeled unicast IPv4 routes";
                }

                leaf ipv6 {
                    type boolean;
                    default "false";
                    description "Enable support for unlabeled unicast IPv6 routes";
                }

                leaf label-ipv4 {
                    type boolean;
                    default "false";
                    description "Enable support for labeled-unicast IPv4 routes";
                }

                leaf label-ipv6 {
                    type boolean;
                    default "false";
                    description "Enable support for labeled-unicast IPv6 routes";
                }

            } // container backup-path

            container flowspec {
                description "Enter the flowspec context";

                leaf validate-dest-prefix {
                    type boolean;
                    default "false";
                    description "Validate destination prefix in FlowSpec-IPv4/IPv6 route";
                }

                leaf validate-redirect-ip {
                    type boolean;
                    default "false";
                    description "Validate the redirect-to-IPv4 action in FlowSpec route";
                }

            } // container flowspec

            container neighbor-trust {
                description "Enter the neighbor-trust context";

                leaf vpn-ipv4 {
                    type boolean;
                    default "false";
                    description "Enable inter-AS label security for the VPN-IPv4 family";
                }

                leaf vpn-ipv6 {
                    type boolean;
                    default "false";
                    description "Enable inter-AS label security for the VPN-IPv6 family";
                }

            } // container neighbor-trust

            container convergence {
                description "Enter the convergence context";

                leaf min-wait-to-advertise {
                    type uint32 {
                        range "0..3600";
                    }
                    default "0";
                    description "Minimum wait time before advertising routes";
                }

                list family {
                    key "family-type";
                    description "Enter the family list instance";

                    leaf family-type {
                        type enumeration {
                            enum "ipv4"                         { value 1; }
                            enum "ipv6"                         { value 3; }
                        }
                        description "Address family for which convergence selection applies";
                    }

                    leaf max-wait-to-advertise {
                        type uint32 {
                            range "0..3600";
                        }
                        default "0";
                        description "Maximum wait time before advertising routes";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list family

            } // container convergence

            container add-paths {
                presence "Enter the 'add-paths' context";
                description "Enable the add-paths context";

                container ipv4 {
                    description "Enter the ipv4 context";

                    leaf send {
                        type types-bgp:add-paths-send-limit;
                        description "Max paths advertised per unlabeled IPv4 unicast prefix";
                    }

                    leaf receive {
                        type boolean;
                        default "false";
                        description "Receive multiple routes per unlabeled IPv4 prefix";
                    }

                } // container ipv4

                container ipv6 {
                    description "Enter the ipv6 context";

                    leaf send {
                        type types-bgp:add-paths-send-limit;
                        description "Max paths advertised per unlabeled IPv6 unicast prefix";
                    }

                    leaf receive {
                        type boolean;
                        default "false";
                        description "Receive multiple routes per unlabeled IPv6 prefix";
                    }

                } // container ipv6

                container label-ipv4 {
                    description "Enter the label-ipv4 context";

                    leaf send {
                        type types-bgp:add-paths-send-limit;
                        description "Max paths advertised per labeled IPv4 unicast prefix";
                    }

                    leaf receive {
                        type boolean;
                        default "false";
                        description "Receive multiple labeled-unicast routes per IPv4 prefix";
                    }

                } // container label-ipv4

                container label-ipv6 {
                    description "Enter the label-ipv6 context";

                    leaf send {
                        type types-bgp:add-paths-send-limit;
                        description "Max paths advertised per labeled IPv6 unicast prefix";
                    }

                    leaf receive {
                        type boolean;
                        default "false";
                        description "Receive multiple labeled-unicast routes per IPv6 prefix";
                    }

                } // container label-ipv6

                container vpn-ipv4 {
                    description "Enter the vpn-ipv4 context";

                    leaf send {
                        type types-bgp:add-paths-send-limit;
                        description "Maximum paths advertised per VPN-IPv4 prefix";
                    }

                    leaf receive {
                        type boolean;
                        default "false";
                        description "Receive multiple routes per VPN-IPv4 prefix";
                    }

                } // container vpn-ipv4

                container vpn-ipv6 {
                    description "Enter the vpn-ipv6 context";

                    leaf send {
                        type types-bgp:add-paths-send-limit;
                        description "Maximum paths advertised per VPN-IPv6 prefix";
                    }

                    leaf receive {
                        type boolean;
                        default "false";
                        description "Receive multiple routes per VPN-IPv6 prefix";
                    }

                } // container vpn-ipv6

                container mvpn-ipv4 {
                    description "Enter the mvpn-ipv4 context";

                    leaf send {
                        type int32 {
                            range "1..16";
                        }
                        description "Maximum paths advertised per multicast VPN IPv4 NRLI";
                    }

                    leaf receive {
                        type boolean;
                        default "false";
                        description "Receive multiple routes per multicast VPN IPv4 NRLI";
                    }

                } // container mvpn-ipv4

                container mvpn-ipv6 {
                    description "Enter the mvpn-ipv6 context";

                    leaf send {
                        type int32 {
                            range "1..16";
                        }
                        description "Maximum paths advertised per multicast VPN IPv6 NRLI";
                    }

                    leaf receive {
                        type boolean;
                        default "false";
                        description "Receive multiple routes per multicast VPN IPv6 NRLI";
                    }

                } // container mvpn-ipv6

                container mcast-vpn-ipv4 {
                    description "Enter the mcast-vpn-ipv4 context";

                    leaf send {
                        type int32 {
                            range "1..16";
                        }
                        description "Maximum paths advertised per multicast IPv4 VPN prefix";
                    }

                    leaf receive {
                        type boolean;
                        default "false";
                        description "Receive multiple multicast routes per IPv4 VPN prefix";
                    }

                } // container mcast-vpn-ipv4

                container mcast-vpn-ipv6 {
                    description "Enter the mcast-vpn-ipv6 context";

                    leaf send {
                        type int32 {
                            range "1..16";
                        }
                        description "Maximum paths advertised per multicast IPv6 VPN prefix";
                    }

                    leaf receive {
                        type boolean;
                        default "false";
                        description "Receive multiple multicast routes per IPv6 VPN prefix";
                    }

                } // container mcast-vpn-ipv6

            } // container add-paths

            container import {
                presence "Enter the 'import' context";
                description "Enable the import context";

                leaf-list policy {
                    type string {
                        length "1..255";
                        pattern "(.{1,64})|(.*[\\[].*)" {
                            error-message "Policy name too long or expression not valid";
                        }
                    }
                    min-elements 1;
                    max-elements 15;
                    ordered-by user;
                    description "BGP import policy name";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container import

            container export {
                presence "Enter the 'export' context";
                description "Enable the export context";

                leaf-list policy {
                    type string {
                        length "1..255";
                        pattern "(.{1,64})|(.*[\\[].*)" {
                            error-message "Policy name too long or expression not valid";
                        }
                    }
                    min-elements 1;
                    max-elements 15;
                    ordered-by user;
                    description "List of export policy names";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

            } // container export

            container extended-nh-encoding {
                description "Enter the extended-nh-encoding context";

                leaf vpn-ipv4 {
                    type boolean;
                    default "false";
                    description "Advertise encoding capability for VPN-IPv4 routes";
                }

                leaf label-ipv4 {
                    type boolean;
                    default "false";
                    description "Advertise encoding capability for label-IPv4 routes";
                }

                leaf ipv4 {
                    type boolean;
                    default "false";
                    description "Advertise encoding capability for IPv4 routes";
                }

            } // container extended-nh-encoding

            container advertise-ipv6-next-hops {
                description "Enter the advertise-ipv6-next-hops context";

                leaf vpn-ipv6 {
                    type boolean;
                    default "false";
                    description "Advertise VPN IPv6 route with IPv6 next-hop address";
                }

                leaf label-ipv6 {
                    type boolean;
                    default "false";
                    description "Advertise label IPv6 route with IPv6 next-hop address";
                }

                leaf evpn {
                    type boolean;
                    default "false";
                    description "Advertise EVPN route with IPv6 next-hop address";
                }

                leaf vpn-ipv4 {
                    type boolean;
                    default "false";
                    description "Advertise VPN IPv4 route with IPv6 next-hop address";
                }

                leaf label-ipv4 {
                    type boolean;
                    default "false";
                    description "Advertise label IPv4 route with IPv6 next-hop address";
                }

                leaf ipv4 {
                    type boolean;
                    default "false";
                    description "Advertise IPv4 route with IPv6 next-hop address";
                }

            } // container advertise-ipv6-next-hops

            container graceful-restart {
                presence "Enter the 'graceful-restart' context";
                description "Enable the graceful-restart context";

                leaf restart-time {
                    type uint32 {
                        range "0..4095";
                    }
                    default "120";
                    description "Restart time advertised by GR capability";
                }

                leaf stale-routes-time {
                    type uint32 {
                        range "1..3600";
                    }
                    default "360";
                    description "Maximum time to maintain routes after graceful restart";
                }

                leaf gr-notification {
                    type boolean;
                    default "false";
                    description "Perform Graceful Restart procedures";
                }

                container long-lived {
                    presence "Enter the 'long-lived' context";
                    description "Enable the long-lived context";

                    leaf advertised-stale-time {
                        type uint32 {
                            range "0..16777215";
                        }
                        default "86400";
                        description "LLGR stale routes time";
                    }

                    leaf helper-override-stale-time {
                        type uint32 {
                            range "0..16777215";
                        }
                        description "Locally-configured stale routes override time";
                    }

                    leaf helper-override-restart-time {
                        type uint32 {
                            range "0..4095";
                        }
                        description "Locally-configured override for restart time";
                    }

                    leaf forwarding-bits-set {
                        type enumeration {
                            enum "none"                         { value 0; }
                            enum "all"                          { value 1; }
                            enum "non-fwd"                      { value 2; }
                        }
                        default "none";
                        description "BGP LLGR forwarding-bit behavior for address family";
                    }

                    leaf advertise-stale-to-all-neighbors {
                        type boolean;
                        default "false";
                        description "Advertise stale routes to all BGP peers";
                    }

                    leaf without-no-export {
                        type boolean;
                        default "false";
                        description "Advertise LLGR stale routes to non-LLGR peers";
                    }

                    list family {
                        key "family-type";
                        description "Enter the family list instance";

                        leaf family-type {
                            type types-bgp:llgr-family-identifiers;
                            description "Family type for family-specific LLGR configuration";
                        }

                        leaf advertised-stale-time {
                            type uint32 {
                                range "0..16777215";
                            }
                            default "86400";
                            description "LLGR stale routes time for family override";
                        }

                        leaf helper-override-stale-time {
                            type uint32 {
                                range "0..16777215";
                            }
                            description "Locally-configured stale routes override time";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // list family

                } // container long-lived

            } // container graceful-restart

            container optimal-route-reflection {
                description "Enter the optimal-route-reflection context";

                container spf-wait {
                    description "Enter the spf-wait context";

                    leaf max-wait {
                        type uint32 {
                            range "1..600";
                        }
                        default "60";
                        description "Maximum interval between consecutive SPF calculations";
                    }

                    leaf initial-wait {
                        type uint32 {
                            range "1..300";
                        }
                        default "5";
                        description "Initial SPF calculation delay after a topology change";
                    }

                    leaf second-wait {
                        type uint32 {
                            range "1..300";
                        }
                        default "15";
                        description "Delay between first and second SPF calculation";
                    }

                } // container spf-wait

                list location {
                    key "location-id";
                    description "Enter the location list instance";

                    leaf location-id {
                        type uint32 {
                            range "1..255";
                        }
                        description "Optimal route reflection location ID";
                    }

                    leaf primary-ip-address {
                        type types-sros:ipv4-unicast-address;
                        description "Primary IPv4 address of the reference location for ORR";
                    }

                    leaf secondary-ip-address {
                        type types-sros:ipv4-unicast-address;
                        description "Secondary IPv4 address of reference location for ORR";
                    }

                    leaf tertiary-ip-address {
                        type types-sros:ipv4-unicast-address;
                        description "Tertiary IPv4 address of the reference location for ORR";
                    }

                    leaf primary-ipv6-address {
                        type types-sros:ipv6-unicast-address;
                        description "Primary IPv6 address of the reference location for ORR";
                    }

                    leaf secondary-ipv6-address {
                        type types-sros:ipv6-unicast-address;
                        description "Secondary IPv6 address of reference location for ORR";
                    }

                    leaf tertiary-ipv6-address {
                        type types-sros:ipv6-unicast-address;
                        description "Tertiary IPv6 address of the reference location for ORR";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list location

            } // container optimal-route-reflection

            container next-hop-resolution {
                description "Enter the next-hop-resolution context";

                leaf use-bgp-routes {
                    type boolean;
                    default "false";
                    description "Use BGP routes to resolve BGP next hops";
                }

                leaf weighted-ecmp {
                    type boolean;
                    default "false";
                    description "Use weighted ECMP for next-hop tunnel selection for 6PE";
                }

                leaf allow-unresolved-leaking {
                    type boolean;
                    default "false";
                    description "Allow unresolved BGP routes to be leaked to VPRN routes";
                }

                leaf policy {
                    type types-sros:named-item-64;
                    description "Policy that filters routes for BGP next-hop resolution";
                }

                leaf vpn-family-policy {
                    type types-sros:named-item-64;
                    description "Policy to filter routes for next-hop resolution";
                }

                container shortcut-tunnel {
                    description "Enter the shortcut-tunnel context";

                    list family {
                        key "family-type";
                        description "Enter the family list instance";

                        leaf family-type {
                            type enumeration {
                                enum "ipv4"                         { value 1; }
                                enum "ipv6"                         { value 3; }
                            }
                            description "Address family type for shortcut tunnel selection";
                        }

                        leaf resolution {
                            type enumeration {
                                enum "none"                         { value 0; }
                                enum "filter"                       { value 1; }
                                enum "any"                          { value 2; }
                            }
                            default "none";
                            description "Resolution mode for binding BGP routes to tunnel types";
                        }

                        leaf disallow-igp {
                            type boolean;
                            default "false";
                            description "Do not perform route table lookup to resolve BGP route";
                        }

                        leaf enforce-strict-tunnel-tagging {
                            type boolean;
                            default "false";
                            description "Consider only LSPs with an admin-tag for next hop";
                        }

                        leaf allow-flex-algo-fallback {
                            type boolean;
                            default "false";
                            description "Enable flexible algorithm fallback";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                        container resolution-filter {
                            description "Enter the resolution-filter context";

                            leaf bgp {
                                type boolean;
                                default "false";
                                description "Use BGP tunneling for next-hop resolution";
                            }

                            leaf ldp {
                                type boolean;
                                default "false";
                                description "Use LDP tunneling for next-hop resolution";
                            }

                            leaf rsvp {
                                type boolean;
                                default "false";
                                description "Use RSVP tunneling for next-hop resolution";
                            }

                            leaf sr-isis {
                                type boolean;
                                default "false";
                                description "Use IS-IS SR tunneling for next-hop resolution";
                            }

                            leaf sr-ospf {
                                type boolean;
                                default "false";
                                description "Use OSPF SR tunneling for next-hop resolution";
                            }

                            leaf sr-te {
                                type boolean;
                                default "false";
                                description "Use SR-TE tunneling for next-hop resolution";
                            }

                            leaf sr-policy {
                                type boolean;
                                default "false";
                                description "Use SR policies for next-hop resolution";
                            }

                            leaf rib-api {
                                type boolean;
                                default "false";
                                description "Use RIB API gRPC service for next-hop resolution";
                            }

                            leaf mpls-fwd-policy {
                                type boolean;
                                default "false";
                                description "Use MPLS forwarding policy for next-hop resolution";
                            }

                            leaf sr-ospf3 {
                                type boolean;
                                default "false";
                                description "Use OSPFv3 SR tunneling for next-hop resolution";
                            }

                        } // container resolution-filter

                    } // list family

                } // container shortcut-tunnel

                container labeled-routes {
                    description "Enter the labeled-routes context";

                    leaf allow-static {
                        type boolean;
                        default "false";
                        description "Allow static routes to resolve BGP next-hop";
                    }

                    leaf rr-use-route-table {
                        type boolean;
                        default "false";
                        description "Use RTM to resolve BGP next-hop if TTM resolution fails";
                    }

                    container transport-tunnel {
                        description "Enter the transport-tunnel context";

                        list family {
                            key "family-type";
                            description "Enter the family list instance";

                            leaf family-type {
                                type enumeration {
                                    enum "vpn"                          { value 2; }
                                    enum "label-ipv4"                   { value 17; }
                                    enum "label-ipv6"                   { value 18; }
                                }
                                description "Address family type for tunnel selection";
                            }

                            leaf resolution {
                                type enumeration {
                                    enum "none"                         { value 0; }
                                    enum "filter"                       { value 1; }
                                    enum "any"                          { value 2; }
                                }
                                default "filter";
                                description "Resolution mode for binding BGP routes to tunnel types";
                            }

                            leaf enforce-strict-tunnel-tagging {
                                type boolean;
                                default "false";
                                description "Consider only LSPs with an admin-tag for next hop";
                            }

                            leaf allow-flex-algo-fallback {
                                type boolean;
                                default "false";
                                description "Enable flexible algorithm fallback";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                            container resolution-filter {
                                description "Enter the resolution-filter context";

                                leaf bgp {
                                    type boolean;
                                    description "Use BGP tunneling for next-hop resolution";
                                }

                                leaf ldp {
                                    type boolean;
                                    default "true";
                                    description "Use LDP tunneling for next-hop resolution";
                                }

                                leaf rsvp {
                                    type boolean;
                                    default "false";
                                    description "Use RSVP tunneling for next-hop resolution";
                                }

                                leaf sr-isis {
                                    type boolean;
                                    default "false";
                                    description "Use IS-IS SR tunneling for next-hop resolution";
                                }

                                leaf sr-ospf {
                                    type boolean;
                                    default "false";
                                    description "Use OSPF SR tunneling for next-hop resolution";
                                }

                                leaf sr-te {
                                    type boolean;
                                    default "false";
                                    description "Use SR-TE tunneling for next-hop resolution";
                                }

                                leaf udp {
                                    type boolean;
                                    default "false";
                                    description "Use MPLS over UDP tunneling for next-hop resolution";
                                }

                                leaf sr-policy {
                                    type boolean;
                                    default "false";
                                    description "Use SR policies for next-hop resolution";
                                }

                                leaf rib-api {
                                    type boolean;
                                    default "false";
                                    description "Use RIB API gRPC service for next-hop resolution";
                                }

                                leaf mpls-fwd-policy {
                                    type boolean;
                                    default "false";
                                    description "Use MPLS forwarding policy for next-hop resolution";
                                }

                                leaf sr-ospf3 {
                                    type boolean;
                                    default "false";
                                    description "Use OSPFv3 SR tunneling for next-hop resolution";
                                }

                            } // container resolution-filter

                        } // list family

                    } // container transport-tunnel

                } // container labeled-routes

            } // container next-hop-resolution

            container multipath {
                description "Enter the multipath context";

                leaf max-paths {
                    type types-router:ip-ecmp;
                    default "1";
                    description "Maximum multipaths per prefix";
                }

                leaf ebgp {
                    type types-router:ip-ecmp;
                    description "Maximum multipaths per prefix for EBGP learned routes";
                }

                leaf ibgp {
                    type types-router:ip-ecmp;
                    description "Maximum multipaths per prefix for IBGP learned routes";
                }

                leaf restrict {
                    type types-bgp:restrict;
                    default "same-as-path-length";
                    description "AS path restriction for the non-best path";
                }

                leaf unequal-cost {
                    type boolean;
                    default "false";
                    description "Ignore differences in the next-hop cost for multipath";
                }

                list family {
                    key "family-type";
                    description "Enter the family list instance";

                    leaf family-type {
                        type enumeration {
                            enum "ipv4"                         { value 1; }
                            enum "ipv6"                         { value 3; }
                            enum "label-ipv4"                   { value 17; }
                            enum "label-ipv6"                   { value 18; }
                        }
                        description "Address family for which multipath selection applies";
                    }

                    leaf max-paths {
                        type types-router:ip-ecmp;
                        description "Maximum multipaths per prefix or NLRI";
                    }

                    leaf ebgp {
                        type types-router:ip-ecmp;
                        description "Maximum multipaths when best path is EBGP learned route";
                    }

                    leaf ibgp {
                        type types-router:ip-ecmp;
                        description "Maximum multipaths when best path is IBGP learned route";
                    }

                    leaf restrict {
                        type types-bgp:restrict;
                        default "same-as-path-length";
                        description "AS path restriction for the non-best path";
                    }

                    leaf unequal-cost {
                        type boolean;
                        default "false";
                        description "Ignore differences in the next-hop cost for multipath";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list family

            } // container multipath

            list route-target-list {
                key "community-name";
                description "Add a list entry for route-target-list";

                leaf community-name {
                    type types-sros:named-item;
                    description "Route target community name";
                }

            } // list route-target-list

            container outbound-route-filtering {
                presence "Enter the 'outbound-route-filtering' context";
                description "Enable the outbound-route-filtering context";

                container extended-community {
                    presence "Enter the 'extended-community' context";
                    description "Enable the extended-community context";

                    leaf accept-orf {
                        type boolean;
                        default "false";
                        description "Negotiate with peer to accept BGP ORF filters";
                    }

                    container send-orf {
                        presence "Enter the 'send-orf' context";
                        description "Enable the send-orf context";

                        list route-target {
                            key "community-name";
                            description "Add a list entry for route-target";

                            leaf community-name {
                                type types-sros:named-item;
                                description "Route target community name";
                            }

                        } // list route-target

                    } // container send-orf

                } // container extended-community

            } // container outbound-route-filtering

            container monitor {
                presence "Enter the 'monitor' context";
                description "Enable the monitor context";

                leaf all-stations {
                    type boolean;
                    default "false";
                    description "Send BMP messages to all configured stations";
                }

                leaf admin-state {
                    type types-sros:admin-state;
                    default "disable";
                    description "Administrative state of BMP monitoring";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container route-monitoring {
                    description "Enter the route-monitoring context";

                    leaf pre-policy {
                        type boolean;
                        default "false";
                        description "Allow pre-policy route-monitoring messages to be sent";
                    }

                    leaf post-policy {
                        type boolean;
                        default "false";
                        description "Allow post-policy route-monitoring messages to be sent";
                    }

                } // container route-monitoring

                list station {
                    key "station-name";
                    max-elements 8;
                    description "Add a list entry for station";

                    leaf station-name {
                        type leafref {
                            path "../../../../../bmp/station/name";
                        }
                        description "BMP monitoring station";
                    }

                } // list station

            } // container monitor

            container rib-management {
                description "Enter the rib-management context";

                container ipv4 {
                    description "Enter the ipv4 context";

                    container route-table-import {
                        description "Enter the route-table-import context";

                        leaf policy-name {
                            type types-sros:named-item-64;
                            description "Name of policy that controls route importation into RIB";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container route-table-import

                    container leak-import {
                        description "Enter the leak-import context";

                        leaf-list policy {
                            type string {
                                length "1..255";
                                pattern "(.{1,64})|(.*[\\[].*)" {
                                    error-message "Policy name too long or expression not valid";
                                }
                            }
                            max-elements 15;
                            ordered-by user;
                            description "Leak import policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container leak-import

                } // container ipv4

                container ipv6 {
                    description "Enter the ipv6 context";

                    container route-table-import {
                        description "Enter the route-table-import context";

                        leaf policy-name {
                            type types-sros:named-item-64;
                            description "Name of policy that controls route importation into RIB";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container route-table-import

                    container leak-import {
                        description "Enter the leak-import context";

                        leaf-list policy {
                            type string {
                                length "1..255";
                                pattern "(.{1,64})|(.*[\\[].*)" {
                                    error-message "Policy name too long or expression not valid";
                                }
                            }
                            max-elements 15;
                            ordered-by user;
                            description "Leak import policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container leak-import

                } // container ipv6

                container label-ipv4 {
                    description "Enter the label-ipv4 context";

                    container route-table-import {
                        description "Enter the route-table-import context";

                        leaf policy-name {
                            type types-sros:named-item-64;
                            description "Name of policy that controls route importation into RIB";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container route-table-import

                    container leak-import {
                        description "Enter the leak-import context";

                        leaf-list policy {
                            type string {
                                length "1..255";
                                pattern "(.{1,64})|(.*[\\[].*)" {
                                    error-message "Policy name too long or expression not valid";
                                }
                            }
                            max-elements 15;
                            ordered-by user;
                            description "Leak import policy name";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container leak-import

                } // container label-ipv4

                container label-ipv6 {
                    description "Enter the label-ipv6 context";

                    container route-table-import {
                        description "Enter the route-table-import context";

                        leaf policy-name {
                            type types-sros:named-item-64;
                            description "Name of policy that controls route importation into RIB";
                        }

                        leaf-list apply-groups {
                            type leafref {
                                path "../../../../../../groups/group/name";
                            }
                            max-elements 8;
                            ordered-by user;
                            description "Apply a configuration group at this level";
                        }

                        leaf-list apply-groups-exclude {
                            type leafref {
                                path "../../../../../../groups/group/name";
                            }
                            max-elements 8;
                            ordered-by user;
                            description "Exclude a configuration group at this level";
                        }

                    } // container route-table-import

                } // container label-ipv6

            } // container rib-management

            container segment-routing {
                description "Enter the segment-routing context";

                leaf admin-state {
                    type types-sros:admin-state;
                    default "disable";
                    description "Administrative state of segment routing";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container prefix-sid-range {
                    presence "Enter the 'prefix-sid-range' context";
                    description "Enable the prefix-sid-range context";

                    choice type {
                        case global {

                            leaf global {
                                type empty;
                                description "Allow label allocation from entire SRBG space";
                            }

                        }
                        case local {

                            leaf start-label {
                                type uint32 {
                                    range "0..524287";
                                }
                                sros-ext:auto-restart-to-modify;
                                default "0";
                                description "First label value available in a contiguous range";
                            }

                            leaf max-index {
                                type uint32 {
                                    range "0..524287";
                                }
                                sros-ext:auto-restart-to-modify;
                                default "1";
                                description "Last label value available in contiguous range";
                            }

                        }
                    }
                } // container prefix-sid-range

            } // container segment-routing

            list group {
                key "group-name";
                description "Enter the group list instance";

                leaf group-name {
                    type types-sros:named-item-64;
                    description "BGP peer group name";
                }

                leaf description {
                    type types-sros:description;
                    description "Text description";
                }

                leaf connect-retry {
                    type int32 {
                        range "1..65535";
                    }
                    description "BGP connect retry timer value";
                }

                leaf admin-state {
                    type types-sros:admin-state;
                    default "enable";
                    description "Administrative state of the BGP group";
                }

                leaf static-group {
                    type boolean;
                    default "true";
                    description "Use group for static peers";
                }

                leaf keepalive {
                    type int32 {
                        range "0..21845";
                    }
                    description "Time after which the BGP KEEPALIVE message is sent";
                }

                leaf damping {
                    type boolean;
                    description "Use BGP route damping to reduce route flap";
                }

                leaf local-preference {
                    type int64 {
                        range "0..4294967295";
                    }
                    description "Default local preference if not in incoming routes";
                }

                leaf loop-detect {
                    type types-bgp:loop-detect;
                    description "Strategy for loop detection in the AS path";
                }

                leaf loop-detect-threshold {
                    type uint32 {
                        range "0..15";
                    }
                    description "Threshold for the global ASN in a received AS path";
                }

                leaf selective-label-ipv4-install {
                    type boolean;
                    description "Enable/Disable selective download for bgp label-ipv4 routes.";
                }

                leaf min-route-advertisement {
                    type int16 {
                        range "1..255";
                    }
                    description "Minimum time before a prefix can be advertised to peer";
                }

                leaf aggregator-id-zero {
                    type boolean;
                    description "Set router ID in the BGP AGGREGATOR attribute to zero";
                }

                leaf preference {
                    type uint32 {
                        range "1..255";
                    }
                    description "Route preference for routes learned from all peers";
                }

                leaf block-prefix-sid {
                    type boolean;
                    default "false";
                    description "Block the prefix SID attribute";
                }

                leaf multihop {
                    type int32 {
                        range "1..255";
                    }
                    description "TTL in IP packet headers for EBGP peers multi-hops away";
                }

                leaf med-out {
                    type union {
                        type uint32;
                        type enumeration {
                            enum "igp-cost"                     { value -1; }
                        }
                    }
                    description "Default MED attribute value to advertise to peers";
                }

                leaf authentication-key {
                    type types-sros:encrypted-leaf {
                        length "1..370";
                    }
                    description "BGP authentication key for all peers";
                }

                leaf client-reflect {
                    type boolean;
                    description "Allow cluster RR to advertise routes to its clients";
                }

                leaf vpn-apply-export {
                    type boolean;
                    description "Apply base-instance BGP export policies to VPN routes";
                }

                leaf vpn-apply-import {
                    type boolean;
                    description "Apply base-instance BGP import policies to VPN routes";
                }

                leaf as-override {
                    type boolean;
                    default "false";
                    description "Replace the peer ASN with the local ASN in AS Path";
                }

                leaf asn-4-byte {
                    type boolean;
                    description "Advertise the use of 4-byte ASNs";
                }

                leaf path-mtu-discovery {
                    type boolean;
                    description "Enable Path MTU Discovery";
                }

                leaf next-hop-self {
                    type boolean;
                    default "false";
                    description "Advertise routes with local address as next-hop address";
                }

                leaf passive {
                    type boolean;
                    default "false";
                    description "Enable passive mode for BGP communication";
                }

                leaf type {
                    type types-bgp:peer-type;
                    default "no-type";
                    description "BGP peer type";
                }

                leaf peer-as {
                    type uint32 {
                        range "1..4294967295";
                    }
                    description "Peer AS number";
                }

                leaf capability-negotiation {
                    type boolean;
                    default "true";
                    description "Enable capability negotiation";
                }

                leaf enforce-first-as {
                    type boolean;
                    description "Enforce the configured peer AS value in received routes";
                }

                leaf initial-send-delay-zero {
                    type boolean;
                    description "Send BGP updates as soon as the session comes up";
                }

                leaf local-address {
                    type types-bgp:local-address;
                    description "Local IP address used when communicating with BGP peers";
                }

                leaf ttl-security {
                    type uint32 {
                        range "1..255";
                    }
                    description "Minimum TTL value for an incoming BGP packet";
                }

                leaf default-route-target {
                    type boolean;
                    default "false";
                    description "Send default RTC route (zero prefix length) to peers";
                }

                leaf aigp {
                    type boolean;
                    default "false";
                    description "Add AIGP attribute to advertised routes";
                }

                leaf advertise-inactive {
                    type boolean;
                    description "Advertise an inactive BGP route to peers";
                }

                leaf authentication-keychain {
                    type leafref {
                        path "../../../../system/security/keychains/keychain/keychain-name";
                    }
                    description "TCP authentication keychain for the session";
                }

                leaf bfd-liveness {
                    type boolean;
                    description "Enable BFD";
                }

                leaf fast-external-failover {
                    type boolean;
                    description "Drop external BGP session immediately when link fails";
                }

                leaf peer-ip-tracking {
                    type boolean;
                    description "Enable BGP peer tracking";
                }

                leaf dynamic-neighbor-limit {
                    type uint32 {
                        range "1..8192";
                    }
                    description "Maximum dynamic BGP sessions to accept from remote peer";
                }

                leaf split-horizon {
                    type boolean;
                    description "Prevent routes being reflected back to best-route peer";
                }

                leaf third-party-nexthop {
                    type boolean;
                    description "Apply third-party next-hop processing to EBGP peers";
                }

                leaf label-preference {
                    type uint32 {
                        range "1..255";
                    }
                    description "Route preference for routes from labeled-unicast peers";
                }

                leaf def-recv-evpn-encap {
                    type types-bgp:encap;
                    description "Default EVPN encapsulation type";
                }

                leaf multipath-eligible {
                    type boolean;
                    default "false";
                    description "Allow routes from group peers in multipath eligibility";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container hold-time {
                    description "Enter the hold-time context";

                    leaf seconds {
                        type int32 {
                            range "0|3..65535";
                        }
                        description "Maximum time BGP waits between successive messages";
                    }

                    leaf minimum-hold-time {
                        type int32 {
                            range "0|3..65536";
                        }
                        default "0";
                        description "Minimum hold time between successive messages";
                    }

                } // container hold-time

                container family {
                    presence "Enter the 'family' context";
                    description "Enable the family context";

                    leaf ipv4 {
                        type boolean;
                        default "false";
                        description "Add support for the IPv4 address family";
                    }

                    leaf vpn-ipv4 {
                        type boolean;
                        default "false";
                        description "Advertise MP-BGP support for IPv4 VPN address family";
                    }

                    leaf ipv6 {
                        type boolean;
                        default "false";
                        description "Advertise MP-BGP support for the IPv6 address family";
                    }

                    leaf mcast-ipv4 {
                        type boolean;
                        default "false";
                        description "Advertise support for the MCAST-IPv4 address family";
                    }

                    leaf vpn-ipv6 {
                        type boolean;
                        default "false";
                        description "Advertise MP-BGP support for IPv6 VPN address family";
                    }

                    leaf l2-vpn {
                        type boolean;
                        default "false";
                        description "Advertise MP-BGP support for the L2-VPN address family";
                    }

                    leaf mvpn-ipv4 {
                        type boolean;
                        default "false";
                        description "Advertise support for the IPv4 MCAST VPN address family";
                    }

                    leaf mdt-safi {
                        type boolean;
                        default "false";
                        description "Advertise MP-BGP support for MDT-SAFI address family";
                    }

                    leaf ms-pw {
                        type boolean;
                        default "false";
                        description "Advertise support for multi-segment PW address family";
                    }

                    leaf flow-ipv4 {
                        type boolean;
                        default "false";
                        description "Advertise support for the flowspec-IPv4 address family";
                    }

                    leaf route-target {
                        type boolean;
                        default "false";
                        description "Advertise MP-BGP support for RT constraint routes";
                    }

                    leaf mcast-vpn-ipv4 {
                        type boolean;
                        default "false";
                        description "Advertise support for the IPv4 VPN MCAST address family";
                    }

                    leaf mvpn-ipv6 {
                        type boolean;
                        default "false";
                        description "Advertise support for the IPv6 MCAST VPN address family";
                    }

                    leaf flow-ipv6 {
                        type boolean;
                        default "false";
                        description "Advertise support for the flowspec-IPv6 address family";
                    }

                    leaf evpn {
                        type boolean;
                        default "false";
                        description "Advertise MP-BGP support for the EVPN address family";
                    }

                    leaf mcast-ipv6 {
                        type boolean;
                        default "false";
                        description "Advertise support for the MCAST-IPv6 address family";
                    }

                    leaf label-ipv4 {
                        type boolean;
                        default "false";
                        description "Advertise support for the label-IPv4 address family";
                    }

                    leaf label-ipv6 {
                        type boolean;
                        default "false";
                        description "Advertise support for the label-IPv6 address family";
                    }

                    leaf bgp-ls {
                        type boolean;
                        default "false";
                        description "Advertise MP-BGP support for the BGP-LS address family";
                    }

                    leaf mcast-vpn-ipv6 {
                        type boolean;
                        default "false";
                        description "Advertise support for the IPv6 VPN MCAST address family";
                    }

                    leaf sr-policy-ipv4 {
                        type boolean;
                        default "false";
                        description "Advertise MP-BGP support for the SR-policy-IPv4 family";
                    }

                    leaf sr-policy-ipv6 {
                        type boolean;
                        default "false";
                        description "Advertise MP-BGP support for the SR-policy-IPv6 family";
                    }

                } // container family

                container send-default {
                    presence "Enter the 'send-default' context";
                    description "Enable the send-default context";

                    leaf ipv4 {
                        type boolean;
                        default "false";
                        description "Generate and advertise an IPv4 default route (0/0)";
                    }

                    leaf ipv6 {
                        type boolean;
                        default "false";
                        description "Generate and advertise an IPv6 default route (::/0)";
                    }

                    leaf export-policy {
                        type types-sros:named-item-64;
                        description "Export policy name";
                    }

                } // container send-default

                container default-preference {
                    description "Enter the default-preference context";

                    leaf ebgp {
                        type uint32 {
                            range "0..255";
                        }
                        description "Default preference for EBGP";
                    }

                    leaf ibgp {
                        type uint32 {
                            range "0..255";
                        }
                        description "Default preference for IBGP";
                    }

                } // container default-preference

                container default-label-preference {
                    description "Enter the default-label-preference context";

                    leaf ebgp {
                        type uint32 {
                            range "0..255";
                        }
                        description "Default preference for EBGP";
                    }

                    leaf ibgp {
                        type uint32 {
                            range "0..255";
                        }
                        description "Default preference for IBGP";
                    }

                } // container default-label-preference

                container remove-private {
                    presence "Enter the 'remove-private' context";
                    description "Enable the remove-private context";

                    leaf limited {
                        type boolean;
                        default "false";
                        description "Remove private ASNs up to first public ASN encountered";
                    }

                    leaf skip-peer-as {
                        type boolean;
                        default "false";
                        description "Keep private ASN if it is the same as the BGP peer ASN";
                    }

                    leaf replace {
                        type boolean;
                        default "false";
                        description "Replace private ASN with global ASN before advertising";
                    }

                } // container remove-private

                container cluster {
                    description "Enter the cluster context";

                    leaf cluster-id {
                        type types-sros:ipv4-address;
                        description "Route reflector cluster ID";
                    }

                    leaf orr-location {
                        type uint32 {
                            range "1..255";
                        }
                        description "Optimal route reflection location for the cluster";
                    }

                    leaf allow-local-fallback {
                        type boolean;
                        default "false";
                        description "Allow fallback to RR topology location";
                    }

                } // container cluster

                container ebgp-default-reject-policy {
                    presence "Enter the 'ebgp-default-reject-policy' context";
                    description "Enable the ebgp-default-reject-policy context";

                    leaf import {
                        type boolean;
                        default "true";
                        description "Enable default reject import policy for external peers";
                    }

                    leaf export {
                        type boolean;
                        default "true";
                        description "Enable default reject export policy for external peers";
                    }

                } // container ebgp-default-reject-policy

                container local-as {
                    description "Enter the local-as context";

                    leaf as-number {
                        type uint32 {
                            range "1..4294967295";
                        }
                        description "Local (or virtual) BGP AS number";
                    }

                    leaf private {
                        type boolean;
                        default "false";
                        description "Hide the local ASN in sent paths learned from peering";
                    }

                    leaf prepend-global-as {
                        type boolean;
                        default "true";
                        description "Prepend global ASN when advertising routes to BGP peer";
                    }

                } // container local-as

                container next-hop-unchanged {
                    description "Enter the next-hop-unchanged context";

                    leaf label-ipv4 {
                        type boolean;
                        default "false";
                        description "Advertise label-IPv4 routes with unchanged BGP next hop";
                    }

                    leaf label-ipv6 {
                        type boolean;
                        default "false";
                        description "Advertise label-IPv6 routes with unchanged BGP next hop";
                    }

                    leaf vpn-ipv4 {
                        type boolean;
                        default "false";
                        description "Advertise VPN IPv4 routes with unchanged BGP next hop";
                    }

                    leaf vpn-ipv6 {
                        type boolean;
                        default "false";
                        description "Advertise VPN IPv6 routes with unchanged BGP next hop";
                    }

                    leaf evpn {
                        type boolean;
                        default "false";
                        description "Advertise EVPN routes with unchanged BGP next hop";
                    }

                } // container next-hop-unchanged

                container origin-validation {
                    description "Enter the origin-validation context";

                    leaf ipv4 {
                        type boolean;
                        default "false";
                        description "Enable support for unlabeled unicast IPv4 routes";
                    }

                    leaf ipv6 {
                        type boolean;
                        default "false";
                        description "Enable support for unlabeled unicast IPv6 routes";
                    }

                    leaf label-ipv4 {
                        type boolean;
                        default "false";
                        description "Enable support for labeled-unicast IPv4 routes";
                    }

                    leaf label-ipv6 {
                        type boolean;
                        default "false";
                        description "Enable support for labeled-unicast IPv6 routes";
                    }

                } // container origin-validation

                container link-bandwidth {
                    description "Enter the link-bandwidth context";

                    container accept-from-ebgp {
                        description "Enter the accept-from-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container accept-from-ebgp

                    container add-to-received-ebgp {
                        description "Enter the add-to-received-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container add-to-received-ebgp

                    container aggregate-used-paths {
                        description "Enter the aggregate-used-paths context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container aggregate-used-paths

                    container send-to-ebgp {
                        description "Enter the send-to-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container send-to-ebgp

                } // container link-bandwidth

                container send-communities {
                    description "Enter the send-communities context";

                    leaf standard {
                        type boolean;
                        description "Advertise the Communities attribute to peers";
                    }

                    leaf extended {
                        type boolean;
                        description "Advertise the Extended Communities attribute to peers";
                    }

                    leaf large {
                        type boolean;
                        description "Advertise the Large Communities attribute to peers";
                    }

                } // container send-communities

                container error-handling {
                    description "Enter the error-handling context";

                    leaf update-fault-tolerance {
                        type boolean;
                        description "Tolerate non-critical errors in UPDATE messages";
                    }

                } // container error-handling

                container damp-peer-oscillations {
                    presence "Enter the 'damp-peer-oscillations' context";
                    description "Enable the damp-peer-oscillations context";

                    leaf error-interval {
                        type uint32 {
                            range "0..2048";
                        }
                        default "30";
                        description "Time after a reset that the session must be error-free";
                    }

                    container idle-hold-time {
                        description "Enter the idle-hold-time context";

                        leaf initial-wait {
                            type uint32 {
                                range "0..2048";
                            }
                            default "0";
                            description "Time session remains in idle state after stabilization";
                        }

                        leaf second-wait {
                            type uint32 {
                                range "1..2048";
                            }
                            default "5";
                            description "Time that doubles after each repeated session failure";
                        }

                        leaf max-wait {
                            type uint32 {
                                range "1..2048";
                            }
                            default "60";
                            description "Maximum session idle time after repeated instability";
                        }

                    } // container idle-hold-time

                } // container damp-peer-oscillations

                container add-paths {
                    presence "Enter the 'add-paths' context";
                    description "Enable the add-paths context";

                    container ipv4 {
                        description "Enter the ipv4 context";

                        leaf send {
                            type types-bgp:add-paths-send-limit;
                            description "Maximum paths per unlabeled IPv4 unicast prefix";
                        }

                        leaf receive {
                            type boolean;
                            default "false";
                            description "Receive multiple labeled-unicast routes per IPv4 prefix";
                        }

                    } // container ipv4

                    container ipv6 {
                        description "Enter the ipv6 context";

                        leaf send {
                            type types-bgp:add-paths-send-limit;
                            description "Maximum paths per unlabeled IPv6 unicast prefix";
                        }

                        leaf receive {
                            type boolean;
                            default "false";
                            description "Receive multiple routes per IPv6 prefix";
                        }

                    } // container ipv6

                    container label-ipv4 {
                        description "Enter the label-ipv4 context";

                        leaf send {
                            type types-bgp:add-paths-send-limit;
                            description "Maximum paths per labeled IPv4 unicast prefix";
                        }

                        leaf receive {
                            type boolean;
                            default "false";
                            description "Receive multiple labeled-unicast routes per IPv4 prefix";
                        }

                    } // container label-ipv4

                    container label-ipv6 {
                        description "Enter the label-ipv6 context";

                        leaf send {
                            type types-bgp:add-paths-send-limit;
                            description "Maximum paths per labeled IPv6 unicast prefix";
                        }

                        leaf receive {
                            type boolean;
                            default "false";
                            description "Receive multiple labeled-unicast routes per IPv6 prefix";
                        }

                    } // container label-ipv6

                    container vpn-ipv4 {
                        description "Enter the vpn-ipv4 context";

                        leaf send {
                            type types-bgp:add-paths-send-limit;
                            description "Maximum paths per VPN-IPv4 prefix";
                        }

                        leaf receive {
                            type boolean;
                            default "false";
                            description "Receive multiple routes per VPN-IPv4 prefix";
                        }

                    } // container vpn-ipv4

                    container vpn-ipv6 {
                        description "Enter the vpn-ipv6 context";

                        leaf send {
                            type types-bgp:add-paths-send-limit;
                            description "Maximum paths per VPN-IPv6 prefix";
                        }

                        leaf receive {
                            type boolean;
                            default "false";
                            description "Receive multiple routes per VPN-IPv6 prefix";
                        }

                    } // container vpn-ipv6

                    container mvpn-ipv4 {
                        description "Enter the mvpn-ipv4 context";

                        leaf send {
                            type int32 {
                                range "1..16";
                            }
                            description "Maximum paths per multicast VPN IPv4 prefix";
                        }

                        leaf receive {
                            type boolean;
                            default "false";
                            description "Receive multiple multicast VPN routes per IPv4 prefix";
                        }

                    } // container mvpn-ipv4

                    container mvpn-ipv6 {
                        description "Enter the mvpn-ipv6 context";

                        leaf send {
                            type int32 {
                                range "1..16";
                            }
                            description "Maximum paths per multicast VPN IPv6 prefix";
                        }

                        leaf receive {
                            type boolean;
                            default "false";
                            description "Receive multiple multicast VPN routes per IPv6 prefix";
                        }

                    } // container mvpn-ipv6

                    container mcast-vpn-ipv4 {
                        description "Enter the mcast-vpn-ipv4 context";

                        leaf send {
                            type int32 {
                                range "1..16";
                            }
                            description "Maximum paths per multicast IPv4 VPN prefix";
                        }

                        leaf receive {
                            type boolean;
                            default "false";
                            description "Receive multiple multicast routes per IPv4 VPN prefix";
                        }

                    } // container mcast-vpn-ipv4

                    container mcast-vpn-ipv6 {
                        description "Enter the mcast-vpn-ipv6 context";

                        leaf send {
                            type int32 {
                                range "1..16";
                            }
                            description "Maximum paths per multicast IPv6 VPN prefix";
                        }

                        leaf receive {
                            type boolean;
                            default "false";
                            description "Receive multiple multicast routes per IPv6 VPN prefix";
                        }

                    } // container mcast-vpn-ipv6

                } // container add-paths

                container import {
                    presence "Enter the 'import' context";
                    description "Enable the import context";

                    leaf-list policy {
                        type string {
                            length "1..255";
                            pattern "(.{1,64})|(.*[\\[].*)" {
                                error-message "Policy name too long or expression not valid";
                            }
                        }
                        min-elements 1;
                        max-elements 15;
                        ordered-by user;
                        description "BGP import policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container import

                container export {
                    presence "Enter the 'export' context";
                    description "Enable the export context";

                    leaf-list policy {
                        type string {
                            length "1..255";
                            pattern "(.{1,64})|(.*[\\[].*)" {
                                error-message "Policy name too long or expression not valid";
                            }
                        }
                        min-elements 1;
                        max-elements 15;
                        ordered-by user;
                        description "BGP export policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container export

                container extended-nh-encoding {
                    presence "Enter the 'extended-nh-encoding' context";
                    description "Enable the extended-nh-encoding context";

                    leaf vpn-ipv4 {
                        type boolean;
                        default "false";
                        description "Advertise encoding capability for VPN-IPv4 routes";
                    }

                    leaf label-ipv4 {
                        type boolean;
                        default "false";
                        description "Advertise encoding capability for label-IPv4 routes";
                    }

                    leaf ipv4 {
                        type boolean;
                        default "false";
                        description "Advertise encoding capability for IPv4 routes";
                    }

                } // container extended-nh-encoding

                container advertise-ipv6-next-hops {
                    presence "Enter the 'advertise-ipv6-next-hops' context";
                    description "Enable the advertise-ipv6-next-hops context";

                    leaf vpn-ipv6 {
                        type boolean;
                        default "false";
                        description "Advertise VPN IPv6 route with IPv6 next-hop address";
                    }

                    leaf label-ipv6 {
                        type boolean;
                        default "false";
                        description "Advertise label IPv6 route with IPv6 next-hop address";
                    }

                    leaf evpn {
                        type boolean;
                        default "false";
                        description "Advertise EVPN route with IPv6 next-hop address";
                    }

                    leaf vpn-ipv4 {
                        type boolean;
                        default "false";
                        description "Advertise VPN IPv4 route with IPv6 next-hop address";
                    }

                    leaf label-ipv4 {
                        type boolean;
                        default "false";
                        description "Advertise label IPv4 route with IPv6 next-hop address";
                    }

                    leaf ipv4 {
                        type boolean;
                        default "false";
                        description "Advertise IPv4 route with IPv6 next-hop address";
                    }

                } // container advertise-ipv6-next-hops

                container graceful-restart {
                    presence "Enter the 'graceful-restart' context";
                    description "Enable the graceful-restart context";

                    leaf restart-time {
                        type uint32 {
                            range "0..4095";
                        }
                        default "300";
                        description "Restart time advertised by GR capability";
                    }

                    leaf stale-routes-time {
                        type uint32 {
                            range "1..3600";
                        }
                        default "360";
                        description "Maximum time to maintain routes after graceful restart";
                    }

                    leaf gr-notification {
                        type boolean;
                        default "false";
                        description "Perform graceful restart procedures after NOTIFICATION";
                    }

                    container long-lived {
                        presence "Enter the 'long-lived' context";
                        description "Enable the long-lived context";

                        leaf advertised-stale-time {
                            type uint32 {
                                range "0..16777215";
                            }
                            default "86400";
                            description "Advertised long-lived stale time for LLGR routes";
                        }

                        leaf helper-override-stale-time {
                            type uint32 {
                                range "0..16777215";
                            }
                            description "Locally-configured stale routes override time";
                        }

                        leaf helper-override-restart-time {
                            type uint32 {
                                range "0..4095";
                            }
                            description "Locally-configured override for restart time";
                        }

                        leaf forwarding-bits-set {
                            type enumeration {
                                enum "none"                         { value 0; }
                                enum "all"                          { value 1; }
                                enum "non-fwd"                      { value 2; }
                            }
                            default "none";
                            description "BGP LLGR forwarding-bit behavior for address family";
                        }

                        leaf advertise-stale-to-all-neighbors {
                            type boolean;
                            default "false";
                            description "Advertise stale routes to all BGP peers";
                        }

                        leaf without-no-export {
                            type boolean;
                            default "false";
                            description "Advertise LLGR stale routes to non-LLGR peers";
                        }

                        list family {
                            key "family-type";
                            description "Enter the family list instance";

                            leaf family-type {
                                type types-bgp:llgr-family-identifiers;
                                description "Family type for family-specific LLGR configuration";
                            }

                            leaf advertised-stale-time {
                                type uint32 {
                                    range "0..16777215";
                                }
                                default "86400";
                                description "LLGR stale routes time for family override";
                            }

                            leaf helper-override-stale-time {
                                type uint32 {
                                    range "0..16777216";
                                }
                                default "16777216";
                                description "Locally-configured stale routes override time";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list family

                    } // container long-lived

                } // container graceful-restart

                container outbound-route-filtering {
                    presence "Enter the 'outbound-route-filtering' context";
                    description "Enable the outbound-route-filtering context";

                    container extended-community {
                        presence "Enter the 'extended-community' context";
                        description "Enable the extended-community context";

                        leaf accept-orf {
                            type boolean;
                            description "Negotiate with peer to accept BGP ORF filters";
                        }

                        container send-orf {
                            presence "Enter the 'send-orf' context";
                            description "Enable the send-orf context";

                            list route-target {
                                key "community-name";
                                description "Add a list entry for route-target";

                                leaf community-name {
                                    type types-sros:named-item;
                                    description "Route target community name";
                                }

                            } // list route-target

                        } // container send-orf

                    } // container extended-community

                } // container outbound-route-filtering

                list prefix-limit {
                    key "family";
                    description "Enter the prefix-limit list instance";

                    leaf family {
                        type types-bgp:ip-family-identifier;
                        description "Address family to which the limit applies";
                    }

                    leaf maximum {
                        type uint32 {
                            range "1..4294967295";
                        }
                        mandatory true;
                        description "Maximum number of routes to be learned from a peer";
                    }

                    leaf log-only {
                        type boolean;
                        default "false";
                        description "Send warning message at threshold instead of take-down";
                    }

                    leaf threshold {
                        type uint32 {
                            range "1..100";
                        }
                        default "90";
                        description "Percentage threshold that triggers a warning message";
                    }

                    leaf idle-timeout {
                        type int32 {
                            range "1..1024";
                        }
                        description "Time BGP peering remains idle before reconnecting";
                    }

                    leaf post-import {
                        type boolean;
                        default "false";
                        description "Apply limit only to routes accepted by import policies";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list prefix-limit

                container dynamic-neighbor {
                    description "Enter the dynamic-neighbor context";

                    container match {
                        description "Enter the match context";

                        list prefix {
                            key "ip-prefix";
                            description "Enter the prefix list instance";

                            leaf ip-prefix {
                                type types-sros:ip-prefix;
                                description "Dynamic peer prefix for the group";
                            }

                            leaf-list allowed-peer-as {
                                type string {
                                    pattern "(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))|(([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5])\\.\\.([1-9]|[1-9][0-9]{1,8}|[1-3][0-9]{9}|4[0-1][0-9]{8}|42[0-8][0-9]{7}|429[0-3][0-9]{6}|4294[0-8][0-9]{5}|42949[0-5][0-9]{4}|429496[0-6][0-9]{3}|4294967[0-1][0-9]{2}|42949672[0-8][0-9]|429496729[0-5]))";
                                }
                                max-elements 32;
                                ordered-by user;
                                description "Allowed peer AS range";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list prefix

                    } // container match

                } // container dynamic-neighbor

                container monitor {
                    presence "Enter the 'monitor' context";
                    description "Enable the monitor context";

                    leaf all-stations {
                        type boolean;
                        default "false";
                        description "Send BMP messages to all configured stations";
                    }

                    leaf admin-state {
                        type types-sros:admin-state;
                        default "disable";
                        description "Administrative state of BMP monitoring";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container route-monitoring {
                        description "Enter the route-monitoring context";

                        leaf pre-policy {
                            type boolean;
                            default "false";
                            description "Allow pre-policy route-monitoring messages to be sent";
                        }

                        leaf post-policy {
                            type boolean;
                            default "false";
                            description "Allow post-policy route-monitoring messages to be sent";
                        }

                    } // container route-monitoring

                    list station {
                        key "station-name";
                        max-elements 8;
                        description "Add a list entry for station";

                        leaf station-name {
                            type leafref {
                                path "../../../../../../bmp/station/name";
                            }
                            description "BMP monitoring station";
                        }

                    } // list station

                } // container monitor

            } // list group

            list neighbor {
                key "ip-address";
                description "Enter the neighbor list instance";

                leaf ip-address {
                    type types-sros:ip-address-with-zone;
                    description "IP address of the BGP peer router";
                }

                leaf advertise-ldp-prefix {
                    type boolean;
                    default "false";
                    description "Advertise active /32 LDP FEC prefixes to BGP peers";
                }

                leaf ttl-security {
                    type uint32 {
                        range "1..255";
                    }
                    description "Minimum TTL value for an incoming BGP packet";
                }

                leaf default-route-target {
                    type boolean;
                    description "Send default RTC route (zero prefix length) to peers";
                }

                leaf aigp {
                    type boolean;
                    description "Add AIGP attribute to advertised routes";
                }

                leaf advertise-inactive {
                    type boolean;
                    description "Advertise an inactive BGP route to peers";
                }

                leaf authentication-keychain {
                    type leafref {
                        path "../../../../system/security/keychains/keychain/keychain-name";
                    }
                    description "TCP authentication keychain for the session";
                }

                leaf bfd-liveness {
                    type boolean;
                    description "Enable BFD";
                }

                leaf fast-external-failover {
                    type boolean;
                    description "Drop external BGP session immediately when link fails";
                }

                leaf peer-ip-tracking {
                    type boolean;
                    description "Enable BGP peer tracking";
                }

                leaf split-horizon {
                    type boolean;
                    description "Prevent routes being reflected back to best-route peer";
                }

                leaf third-party-nexthop {
                    type boolean;
                    description "Apply third-party next-hop processing to EBGP peers";
                }

                leaf label-preference {
                    type uint32 {
                        range "1..255";
                    }
                    description "Route preference for routes from labeled-unicast peers";
                }

                leaf def-recv-evpn-encap {
                    type types-bgp:encap;
                    description "Default EVPN encapsulation type";
                }

                leaf multipath-eligible {
                    type boolean;
                    description "Allow routes from this peer in multipath eligibility";
                }

                leaf group {
                    type leafref {
                        path "../../group/group-name";
                    }
                    sros-ext:immutable;
                    mandatory true;
                    description "BGP peer group";
                }

                leaf peer-creation-type {
                    type types-bgp:peer-creation-type;
                    default "static";
                    description "Peer creation type";
                }

                leaf connect-retry {
                    type int32 {
                        range "1..65535";
                    }
                    description "BGP connect retry timer value";
                }

                leaf description {
                    type types-sros:description;
                    description "Text description";
                }

                leaf admin-state {
                    type types-sros:admin-state;
                    default "enable";
                    description "Administrative state of the BGP neighbor";
                }

                leaf keepalive {
                    type int32 {
                        range "0..21845";
                    }
                    description "Time after which the BGP KEEPALIVE message is sent";
                }

                leaf damping {
                    type boolean;
                    description "Use BGP route damping to reduce route flap";
                }

                leaf local-preference {
                    type int64 {
                        range "0..4294967295";
                    }
                    description "Default local preference if not in incoming routes";
                }

                leaf loop-detect {
                    type types-bgp:loop-detect;
                    description "Strategy for loop detection in the AS path";
                }

                leaf loop-detect-threshold {
                    type uint32 {
                        range "0..15";
                    }
                    description "Threshold for the global ASN in a received AS path";
                }

                leaf selective-label-ipv4-install {
                    type boolean;
                    description "Enable/Disable selective download for bgp label-ipv4 routes.";
                }

                leaf min-route-advertisement {
                    type int16 {
                        range "1..255";
                    }
                    description "Minimum interval between successive prefix updates";
                }

                leaf aggregator-id-zero {
                    type boolean;
                    description "Set router ID in the BGP AGGREGATOR attribute to zero";
                }

                leaf preference {
                    type uint32 {
                        range "1..255";
                    }
                    description "Route preference for routes learned from all peers";
                }

                leaf block-prefix-sid {
                    type boolean;
                    default "false";
                    description "Block the prefix SID attribute";
                }

                leaf multihop {
                    type int32 {
                        range "1..255";
                    }
                    description "TTL in IP packet headers for EBGP peers multi-hops away";
                }

                leaf med-out {
                    type union {
                        type uint32;
                        type enumeration {
                            enum "igp-cost"                     { value -1; }
                        }
                    }
                    description "Default MED attribute value to advertise to peers";
                }

                leaf authentication-key {
                    type types-sros:encrypted-leaf {
                        length "1..370";
                    }
                    description "BGP authentication key for all peers";
                }

                leaf client-reflect {
                    type boolean;
                    description "Allow cluster RR to advertise routes to its clients";
                }

                leaf vpn-apply-export {
                    type boolean;
                    description "Apply base-instance BGP export policies to VPN routes";
                }

                leaf vpn-apply-import {
                    type boolean;
                    description "Apply base-instance BGP import policies to VPN routes";
                }

                leaf as-override {
                    type boolean;
                    description "Replace the peer's ASN with the local ASN in AS Path";
                }

                leaf asn-4-byte {
                    type boolean;
                    description "Advertise the use of 4-byte ASNs";
                }

                leaf path-mtu-discovery {
                    type boolean;
                    description "Enable path MTU discovery";
                }

                leaf local-address {
                    type types-bgp:local-address;
                    description "Local IP address used when communicating with BGP peers";
                }

                leaf l2vpn-cisco-interop {
                    type boolean;
                    default "false";
                    description "Allow translation from Cisco non-compliant NLRI format";
                }

                leaf next-hop-self {
                    type boolean;
                    description "Advertise routes with local address as next-hop address";
                }

                leaf passive {
                    type boolean;
                    description "Use passive mode for BGP communication";
                }

                leaf type {
                    type types-bgp:peer-type;
                    description "BGP peer type";
                }

                leaf peer-as {
                    type uint32 {
                        range "1..4294967295";
                    }
                    description "Peer AS number";
                }

                leaf capability-negotiation {
                    type boolean;
                    description "Enable capability negotiation";
                }

                leaf enforce-first-as {
                    type boolean;
                    description "Enforce the configured peer AS value in received routes";
                }

                leaf initial-send-delay-zero {
                    type boolean;
                    description "Send BGP updates as soon as the session comes up";
                }

                leaf-list apply-groups {
                    type leafref {
                        path "../../../../groups/group/name";
                    }
                    max-elements 8;
                    ordered-by user;
                    description "Apply a configuration group at this level";
                }

                leaf-list apply-groups-exclude {
                    type leafref {
                        path "../../../../groups/group/name";
                    }
                    max-elements 8;
                    ordered-by user;
                    description "Exclude a configuration group at this level";
                }

                container next-hop-unchanged {
                    presence "Enter the 'next-hop-unchanged' context";
                    description "Enable the next-hop-unchanged context";

                    leaf label-ipv4 {
                        type boolean;
                        default "false";
                        description "Advertise label-IPv4 routes with unchanged BGP next hop";
                    }

                    leaf label-ipv6 {
                        type boolean;
                        default "false";
                        description "Advertise label-IPv6 routes with unchanged BGP next hop";
                    }

                    leaf vpn-ipv4 {
                        type boolean;
                        default "false";
                        description "Advertise VPN IPv4 routes with unchanged BGP next hop";
                    }

                    leaf vpn-ipv6 {
                        type boolean;
                        default "false";
                        description "Advertise VPN IPv6 routes with unchanged BGP next hop";
                    }

                    leaf evpn {
                        type boolean;
                        default "false";
                        description "Advertise EVPN routes with unchanged BGP next hop";
                    }

                } // container next-hop-unchanged

                container origin-validation {
                    presence "Enter the 'origin-validation' context";
                    description "Enable the origin-validation context";

                    leaf ipv4 {
                        type boolean;
                        default "false";
                        description "Enable support for unlabeled unicast IPv4 routes";
                    }

                    leaf ipv6 {
                        type boolean;
                        default "false";
                        description "Enable support for unlabeled unicast IPv6 routes";
                    }

                    leaf label-ipv4 {
                        type boolean;
                        default "false";
                        description "Enable support for labeled-unicast IPv4 routes";
                    }

                    leaf label-ipv6 {
                        type boolean;
                        default "false";
                        description "Enable support for labeled-unicast IPv6 routes";
                    }

                } // container origin-validation

                container link-bandwidth {
                    description "Enter the link-bandwidth context";

                    container accept-from-ebgp {
                        presence "Enter the 'accept-from-ebgp' context";
                        description "Enable the accept-from-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container accept-from-ebgp

                    container add-to-received-ebgp {
                        presence "Enter the 'add-to-received-ebgp' context";
                        description "Enable the add-to-received-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container add-to-received-ebgp

                    container aggregate-used-paths {
                        presence "Enter the 'aggregate-used-paths' context";
                        description "Enable the aggregate-used-paths context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container aggregate-used-paths

                    container send-to-ebgp {
                        presence "Enter the 'send-to-ebgp' context";
                        description "Enable the send-to-ebgp context";

                        leaf ipv4 {
                            type boolean;
                            default "false";
                            description "Support Link Bandwidth EC in IPv4 routes";
                        }

                        leaf ipv6 {
                            type boolean;
                            default "false";
                            description "Support Link Bandwidth EC in IPv6 routes";
                        }

                        leaf vpn-ipv4 {
                            type boolean;
                            default "false";
                            description "Support Link Bandwidth EC in VPN-IPv4 routes";
                        }

                        leaf vpn-ipv6 {
                            type boolean;
                            default "false";
                            description "Support Link Bandwidth EC in VPN-IPv6 routes";
                        }

                        leaf label-ipv4 {
                            type boolean;
                            default "false";
                            description "Support Link Bandwidth EC in label-IPv4 routes";
                        }

                        leaf label-ipv6 {
                            type boolean;
                            default "false";
                            description "Support Link Bandwidth EC in label-IPv6 routes";
                        }

                    } // container send-to-ebgp

                } // container link-bandwidth

                container send-communities {
                    description "Enter the send-communities context";

                    leaf standard {
                        type boolean;
                        description "Advertise the Communities attribute to peers";
                    }

                    leaf extended {
                        type boolean;
                        description "Advertise the Extended Communities attribute to peers";
                    }

                    leaf large {
                        type boolean;
                        description "Advertise the Large Communities attribute to peers";
                    }

                } // container send-communities

                container error-handling {
                    description "Enter the error-handling context";

                    leaf update-fault-tolerance {
                        type boolean;
                        description "Tolerate non-critical errors in UPDATE messages";
                    }

                } // container error-handling

                container damp-peer-oscillations {
                    presence "Enter the 'damp-peer-oscillations' context";
                    description "Enable the damp-peer-oscillations context";

                    leaf error-interval {
                        type uint32 {
                            range "0..2048";
                        }
                        default "30";
                        description "Time after a reset that the session must be error-free";
                    }

                    container idle-hold-time {
                        description "Enter the idle-hold-time context";

                        leaf initial-wait {
                            type uint32 {
                                range "0..2048";
                            }
                            default "0";
                            description "Time session remains in idle state after stabilization";
                        }

                        leaf second-wait {
                            type uint32 {
                                range "1..2048";
                            }
                            default "5";
                            description "Time that doubles after each repeated session failure";
                        }

                        leaf max-wait {
                            type uint32 {
                                range "1..2048";
                            }
                            default "60";
                            description "Maximum session idle time after repeated instability";
                        }

                    } // container idle-hold-time

                } // container damp-peer-oscillations

                container hold-time {
                    description "Enter the hold-time context";

                    leaf seconds {
                        type int32 {
                            range "0|3..65535";
                        }
                        description "Maximum hold time between successive messages";
                    }

                    leaf minimum-hold-time {
                        type int32 {
                            range "0|3..65536";
                        }
                        default "0";
                        description "Minimum time BGP waits between successive messages";
                    }

                } // container hold-time

                container family {
                    presence "Enter the 'family' context";
                    description "Enable the family context";

                    leaf ipv4 {
                        type boolean;
                        default "false";
                        description "Add support for the IPv4 address family";
                    }

                    leaf vpn-ipv4 {
                        type boolean;
                        default "false";
                        description "Advertise MP-BGP support for IPv4 VPN address family";
                    }

                    leaf ipv6 {
                        type boolean;
                        default "false";
                        description "Advertise MP-BGP support for the IPv6 address family";
                    }

                    leaf mcast-ipv4 {
                        type boolean;
                        default "false";
                        description "Advertise support for the MCAST-IPv4 address family";
                    }

                    leaf vpn-ipv6 {
                        type boolean;
                        default "false";
                        description "Advertise MP-BGP support for IPv6 VPN address family";
                    }

                    leaf l2-vpn {
                        type boolean;
                        default "false";
                        description "Advertise MP-BGP support for the L2-VPN address family";
                    }

                    leaf mvpn-ipv4 {
                        type boolean;
                        default "false";
                        description "Advertise support for the IPv4 MCAST VPN address family";
                    }

                    leaf mdt-safi {
                        type boolean;
                        default "false";
                        description "Advertise MP-BGP support for MDT-SAFI address family";
                    }

                    leaf ms-pw {
                        type boolean;
                        default "false";
                        description "Advertise support for multi-segment PW address family";
                    }

                    leaf flow-ipv4 {
                        type boolean;
                        default "false";
                        description "Advertise support for the flowspec-IPv4 address family";
                    }

                    leaf route-target {
                        type boolean;
                        default "false";
                        description "Advertise MP-BGP support for RT constraint routes";
                    }

                    leaf mcast-vpn-ipv4 {
                        type boolean;
                        default "false";
                        description "Advertise support for the IPv4 VPN MCAST address family";
                    }

                    leaf mvpn-ipv6 {
                        type boolean;
                        default "false";
                        description "Advertise support for the IPv6 MCAST VPN address family";
                    }

                    leaf flow-ipv6 {
                        type boolean;
                        default "false";
                        description "Advertise support for the flowspec-IPv6 address family";
                    }

                    leaf evpn {
                        type boolean;
                        default "false";
                        description "Advertise MP-BGP support for the EVPN address family";
                    }

                    leaf mcast-ipv6 {
                        type boolean;
                        default "false";
                        description "Advertise support for the MCAST-IPv6 address family";
                    }

                    leaf label-ipv4 {
                        type boolean;
                        default "false";
                        description "Advertise support for the label-IPv4 address family";
                    }

                    leaf label-ipv6 {
                        type boolean;
                        default "false";
                        description "Advertise support for the label-IPv6 address family";
                    }

                    leaf bgp-ls {
                        type boolean;
                        default "false";
                        description "Advertise MP-BGP support for the BGP-LS address family";
                    }

                    leaf mcast-vpn-ipv6 {
                        type boolean;
                        default "false";
                        description "Advertise support for the IPv6 VPN MCAST address family";
                    }

                    leaf sr-policy-ipv4 {
                        type boolean;
                        default "false";
                        description "Advertise MP-BGP support for the SR-policy-IPv4 family";
                    }

                    leaf sr-policy-ipv6 {
                        type boolean;
                        default "false";
                        description "Advertise MP-BGP support for the SR-policy-IPv6 family";
                    }

                } // container family

                container send-default {
                    presence "Enter the 'send-default' context";
                    description "Enable the send-default context";

                    leaf ipv4 {
                        type boolean;
                        default "false";
                        description "Enable IPv4 family type";
                    }

                    leaf ipv6 {
                        type boolean;
                        default "false";
                        description "Enable IPv6 family type";
                    }

                    leaf export-policy {
                        type types-sros:named-item-64;
                        description "Export policy name";
                    }

                } // container send-default

                container default-preference {
                    description "Enter the default-preference context";

                    leaf ebgp {
                        type uint32 {
                            range "0..255";
                        }
                        description "Default preference for EBGP";
                    }

                    leaf ibgp {
                        type uint32 {
                            range "0..255";
                        }
                        description "Default preference for IBGP";
                    }

                } // container default-preference

                container default-label-preference {
                    description "Enter the default-label-preference context";

                    leaf ebgp {
                        type uint32 {
                            range "0..255";
                        }
                        description "Default preference for EBGP";
                    }

                    leaf ibgp {
                        type uint32 {
                            range "0..255";
                        }
                        description "Default preference for IBGP";
                    }

                } // container default-label-preference

                container remove-private {
                    presence "Enter the 'remove-private' context";
                    description "Enable the remove-private context";

                    leaf limited {
                        type boolean;
                        default "false";
                        description "Remove private ASNs up to first public ASN encountered";
                    }

                    leaf skip-peer-as {
                        type boolean;
                        default "false";
                        description "Keep private ASN if it is the same as the BGP peer ASN";
                    }

                    leaf replace {
                        type boolean;
                        default "false";
                        description "Replace private ASN with global ASN before advertising";
                    }

                } // container remove-private

                container cluster {
                    description "Enter the cluster context";

                    leaf cluster-id {
                        type types-sros:ipv4-address;
                        description "Route reflector cluster ID";
                    }

                    leaf orr-location {
                        type uint32 {
                            range "1..255";
                        }
                        description "Optimal route reflection location for the cluster";
                    }

                    leaf allow-local-fallback {
                        type boolean;
                        default "false";
                        description "Allow fallback to RR topology";
                    }

                } // container cluster

                container ebgp-default-reject-policy {
                    presence "Enter the 'ebgp-default-reject-policy' context";
                    description "Enable the ebgp-default-reject-policy context";

                    leaf import {
                        type boolean;
                        default "true";
                        description "Enable default reject import policy for external peers";
                    }

                    leaf export {
                        type boolean;
                        default "true";
                        description "Enable default reject export policy for external peers";
                    }

                } // container ebgp-default-reject-policy

                container local-as {
                    description "Enter the local-as context";

                    leaf as-number {
                        type uint32 {
                            range "1..4294967295";
                        }
                        description "Local (or virtual) BGP AS number";
                    }

                    leaf private {
                        type boolean;
                        default "false";
                        description "Hide the local ASN in sent paths learned from peering";
                    }

                    leaf prepend-global-as {
                        type boolean;
                        default "true";
                        description "Prepend global ASN when advertising routes to BGP peer";
                    }

                } // container local-as

                container add-paths {
                    presence "Enter the 'add-paths' context";
                    description "Enable the add-paths context";

                    container ipv4 {
                        description "Enter the ipv4 context";

                        leaf send {
                            type types-bgp:add-paths-send-limit;
                            description "Maximum paths per unlabeled IPv4 unicast prefix";
                        }

                        leaf receive {
                            type boolean;
                            default "false";
                            description "Receive multiple labeled-unicast routes per IPv4 prefix";
                        }

                    } // container ipv4

                    container ipv6 {
                        description "Enter the ipv6 context";

                        leaf send {
                            type types-bgp:add-paths-send-limit;
                            description "Maximum paths per unlabeled IPv6 unicast prefix";
                        }

                        leaf receive {
                            type boolean;
                            default "false";
                            description "Receive multiple routes per IPv6 prefix";
                        }

                    } // container ipv6

                    container label-ipv4 {
                        description "Enter the label-ipv4 context";

                        leaf send {
                            type types-bgp:add-paths-send-limit;
                            description "Maximum paths per labeled IPv4 unicast prefix";
                        }

                        leaf receive {
                            type boolean;
                            default "false";
                            description "Receive multiple labeled-unicast routes per IPv4 prefix";
                        }

                    } // container label-ipv4

                    container label-ipv6 {
                        description "Enter the label-ipv6 context";

                        leaf send {
                            type types-bgp:add-paths-send-limit;
                            description "Maximum paths per labeled IPv6 unicast prefix";
                        }

                        leaf receive {
                            type boolean;
                            default "false";
                            description "Receive multiple labeled-unicast routes per IPv6 prefix";
                        }

                    } // container label-ipv6

                    container vpn-ipv4 {
                        description "Enter the vpn-ipv4 context";

                        leaf send {
                            type types-bgp:add-paths-send-limit;
                            description "Maximum paths per VPN-IPv4 prefix";
                        }

                        leaf receive {
                            type boolean;
                            default "false";
                            description "Receive multiple routes per VPN-IPv4 prefix";
                        }

                    } // container vpn-ipv4

                    container vpn-ipv6 {
                        description "Enter the vpn-ipv6 context";

                        leaf send {
                            type types-bgp:add-paths-send-limit;
                            description "Maximum paths per VPN-IPv6 prefix";
                        }

                        leaf receive {
                            type boolean;
                            default "false";
                            description "Receive multiple routes per VPN-IPv6 prefix";
                        }

                    } // container vpn-ipv6

                    container mvpn-ipv4 {
                        description "Enter the mvpn-ipv4 context";

                        leaf send {
                            type int32 {
                                range "1..16";
                            }
                            description "Maximum paths per multicast VPN IPv4 prefix";
                        }

                        leaf receive {
                            type boolean;
                            default "false";
                            description "Receive multiple multicast VPN routes per IPv4 prefix";
                        }

                    } // container mvpn-ipv4

                    container mvpn-ipv6 {
                        description "Enter the mvpn-ipv6 context";

                        leaf send {
                            type int32 {
                                range "1..16";
                            }
                            description "Maximum paths per multicast VPN IPv6 prefix";
                        }

                        leaf receive {
                            type boolean;
                            default "false";
                            description "Receive multiple multicast VPN routes per IPv6 prefix";
                        }

                    } // container mvpn-ipv6

                    container mcast-vpn-ipv4 {
                        description "Enter the mcast-vpn-ipv4 context";

                        leaf send {
                            type int32 {
                                range "1..16";
                            }
                            description "Maximum paths per multicast IPv4 VPN prefix";
                        }

                        leaf receive {
                            type boolean;
                            default "false";
                            description "Receive multiple multicast routes per IPv4 VPN prefix";
                        }

                    } // container mcast-vpn-ipv4

                    container mcast-vpn-ipv6 {
                        description "Enter the mcast-vpn-ipv6 context";

                        leaf send {
                            type int32 {
                                range "1..16";
                            }
                            description "Maximum paths per multicast IPv6 VPN prefix";
                        }

                        leaf receive {
                            type boolean;
                            default "false";
                            description "Receive multiple multicast routes per IPv6 VPN prefix";
                        }

                    } // container mcast-vpn-ipv6

                } // container add-paths

                container import {
                    presence "Enter the 'import' context";
                    description "Enable the import context";

                    leaf-list policy {
                        type string {
                            length "1..255";
                            pattern "(.{1,64})|(.*[\\[].*)" {
                                error-message "Policy name too long or expression not valid";
                            }
                        }
                        min-elements 1;
                        max-elements 15;
                        ordered-by user;
                        description "Names of the BGP import policies";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container import

                container export {
                    presence "Enter the 'export' context";
                    description "Enable the export context";

                    leaf-list policy {
                        type string {
                            length "1..255";
                            pattern "(.{1,64})|(.*[\\[].*)" {
                                error-message "Policy name too long or expression not valid";
                            }
                        }
                        min-elements 1;
                        max-elements 15;
                        ordered-by user;
                        description "BGP export policy name";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // container export

                container extended-nh-encoding {
                    presence "Enter the 'extended-nh-encoding' context";
                    description "Enable the extended-nh-encoding context";

                    leaf vpn-ipv4 {
                        type boolean;
                        default "false";
                        description "Advertise encoding capability for VPN-IPv4 routes";
                    }

                    leaf label-ipv4 {
                        type boolean;
                        default "false";
                        description "Advertise encoding capability for label-IPv4 routes";
                    }

                    leaf ipv4 {
                        type boolean;
                        default "false";
                        description "Advertise encoding capability for IPv4 routes";
                    }

                } // container extended-nh-encoding

                container advertise-ipv6-next-hops {
                    presence "Enter the 'advertise-ipv6-next-hops' context";
                    description "Enable the advertise-ipv6-next-hops context";

                    leaf vpn-ipv6 {
                        type boolean;
                        default "false";
                        description "Advertise VPN IPv6 route with IPv6 next-hop address";
                    }

                    leaf label-ipv6 {
                        type boolean;
                        default "false";
                        description "Advertise label IPv6 route with IPv6 next-hop address";
                    }

                    leaf evpn {
                        type boolean;
                        default "false";
                        description "Advertise EVPN route with IPv6 next-hop address";
                    }

                    leaf vpn-ipv4 {
                        type boolean;
                        default "false";
                        description "Advertise VPN IPv4 route with IPv6 next-hop address";
                    }

                    leaf label-ipv4 {
                        type boolean;
                        default "false";
                        description "Advertise label IPv4 route with IPv6 next-hop address";
                    }

                    leaf ipv4 {
                        type boolean;
                        default "false";
                        description "Advertise IPv4 route with IPv6 next-hop address";
                    }

                } // container advertise-ipv6-next-hops

                container graceful-restart {
                    presence "Enter the 'graceful-restart' context";
                    description "Enable the graceful-restart context";

                    leaf restart-time {
                        type uint32 {
                            range "0..4095";
                        }
                        default "300";
                        description "Restart time advertised by GR capability";
                    }

                    leaf stale-routes-time {
                        type uint32 {
                            range "1..3600";
                        }
                        default "360";
                        description "Maximum time to maintain routes after graceful restart";
                    }

                    leaf gr-notification {
                        type boolean;
                        default "false";
                        description "Perform graceful restart procedures after NOTIFICATION";
                    }

                    container long-lived {
                        presence "Enter the 'long-lived' context";
                        description "Enable the long-lived context";

                        leaf advertised-stale-time {
                            type uint32 {
                                range "0..16777215";
                            }
                            default "86400";
                            description "Advertised long-lived stale time for LLGR routes";
                        }

                        leaf helper-override-stale-time {
                            type uint32 {
                                range "0..16777215";
                            }
                            description "Locally-configured stale routes override time";
                        }

                        leaf helper-override-restart-time {
                            type uint32 {
                                range "0..4095";
                            }
                            description "Locally-configured override for restart time";
                        }

                        leaf forwarding-bits-set {
                            type enumeration {
                                enum "none"                         { value 0; }
                                enum "all"                          { value 1; }
                                enum "non-fwd"                      { value 2; }
                            }
                            default "none";
                            description "BGP LLGR forwarding-bit behavior for address family";
                        }

                        leaf advertise-stale-to-all-neighbors {
                            type boolean;
                            default "false";
                            description "Advertise stale routes to all BGP peers";
                        }

                        leaf without-no-export {
                            type boolean;
                            default "false";
                            description "Advertise LLGR stale routes to non-LLGR peers";
                        }

                        list family {
                            key "family-type";
                            description "Enter the family list instance";

                            leaf family-type {
                                type types-bgp:llgr-family-identifiers;
                                description "Family type for family-specific LLGR configuration";
                            }

                            leaf advertised-stale-time {
                                type uint32 {
                                    range "0..16777215";
                                }
                                default "86400";
                                description "LLGR stale routes time for family override";
                            }

                            leaf helper-override-stale-time {
                                type uint32 {
                                    range "0..16777216";
                                }
                                default "16777216";
                                description "Locally-configured stale routes override time";
                            }

                            leaf-list apply-groups {
                                type leafref {
                                    path "../../../../../../../groups/group/name";
                                }
                                max-elements 8;
                                ordered-by user;
                                description "Apply a configuration group at this level";
                            }

                            leaf-list apply-groups-exclude {
                                type leafref {
                                    path "../../../../../../../groups/group/name";
                                }
                                max-elements 8;
                                ordered-by user;
                                description "Exclude a configuration group at this level";
                            }

                        } // list family

                    } // container long-lived

                } // container graceful-restart

                container outbound-route-filtering {
                    presence "Enter the 'outbound-route-filtering' context";
                    description "Enable the outbound-route-filtering context";

                    container extended-community {
                        presence "Enter the 'extended-community' context";
                        description "Enable the extended-community context";

                        leaf accept-orf {
                            type boolean;
                            description "Negotiate with peer to accept BGP ORF filters";
                        }

                        container send-orf {
                            presence "Enter the 'send-orf' context";
                            description "Enable the send-orf context";

                            list route-target {
                                key "community-name";
                                description "Add a list entry for route-target";

                                leaf community-name {
                                    type types-sros:named-item;
                                    description "Route target community name";
                                }

                            } // list route-target

                        } // container send-orf

                    } // container extended-community

                } // container outbound-route-filtering

                container monitor {
                    presence "Enter the 'monitor' context";
                    description "Enable the monitor context";

                    leaf all-stations {
                        type boolean;
                        default "false";
                        description "Send BMP messages to all configured stations";
                    }

                    leaf admin-state {
                        type types-sros:admin-state;
                        default "disable";
                        description "Administrative state of BMP monitoring";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                    container route-monitoring {
                        description "Enter the route-monitoring context";

                        leaf pre-policy {
                            type boolean;
                            default "false";
                            description "Allow pre-policy route-monitoring messages to be sent";
                        }

                        leaf post-policy {
                            type boolean;
                            default "false";
                            description "Allow post-policy route-monitoring messages to be sent";
                        }

                    } // container route-monitoring

                    list station {
                        key "station-name";
                        max-elements 8;
                        description "Add a list entry for station";

                        leaf station-name {
                            type leafref {
                                path "../../../../../../bmp/station/name";
                            }
                            description "BMP monitoring station";
                        }

                    } // list station

                } // container monitor

                list prefix-limit {
                    key "family";
                    description "Enter the prefix-limit list instance";

                    leaf family {
                        type types-bgp:ip-family-identifier;
                        description "Address family to which the limit applies";
                    }

                    leaf maximum {
                        type uint32 {
                            range "1..4294967295";
                        }
                        mandatory true;
                        description "Maximum number of routes to be learned from a peer";
                    }

                    leaf log-only {
                        type boolean;
                        default "false";
                        description "Send warning message at threshold instead of take-down";
                    }

                    leaf threshold {
                        type uint32 {
                            range "1..100";
                        }
                        default "90";
                        description "Percentage threshold that triggers a warning message";
                    }

                    leaf idle-timeout {
                        type int32 {
                            range "1..1024";
                        }
                        description "Time which BGP peering remains idle before reconnecting";
                    }

                    leaf post-import {
                        type boolean;
                        default "false";
                        description "Apply limit only to routes accepted by import policies";
                    }

                    leaf-list apply-groups {
                        type leafref {
                            path "../../../../../groups/group/name";
                        }
                        max-elements 8;
                        ordered-by user;
                        description "Apply a configuration group at this level";
                    }

                    leaf-list apply-groups-exclude {
                        type leafref {
                            path "../../../../../groups/group/name";
                        }
                        max-elements 8;
                        ordered-by user;
                        description "Exclude a configuration group at this level";
                    }

                } // list prefix-limit

            } // list neighbor

            container bgp-tunnel-metric {
                description "Enter the bgp-tunnel-metric context";

                leaf value {
                    type uint32 {
                        range "0..4294967295";
                    }
                    default "1000";
                    description "BGP tunnel metric value";
                }

                leaf prefer-aigp {
                    type boolean;
                    default "false";
                    description "Use the AIGP attribute as tunnel metric when present";
                }

            } // container bgp-tunnel-metric

        } // container bgp

    } // grouping conf-router-bgp

}
