submodule nokia-state-filter-ip-exception {

    yang-version "1.1";

    belongs-to nokia-state { prefix "state"; }

    import ietf-yang-types                { prefix "yang"; }
    import nokia-sros-yang-extensions     { prefix "sros-ext"; }
    import nokia-types-filter             { prefix "types-filter"; }


    sros-ext:sros-major-release "rel20";

    organization "Nokia";

    contact
        "Nokia SR OS Support
         Web: <http://www.nokia.com>";

    description
        "Nokia YANG Data model with operational state for IP exception filters on SR OS based routers.

         Copyright 2016 Nokia. All rights reserved. Reproduction of this document
         is authorized on the condition that the foregoing copyright notice is included.

         This nokia-state-filter-ip-exception YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2020-11-13";

    grouping state-filter-ip-exception {
        list ip-exception {
            key "filter-name";
            description "Enter the ip-exception list instance";

            leaf filter-name {
                type types-filter:filter-name;
                description "Filter name";
            }

            leaf applied {
                type boolean;
                description "Indicates whether the filter is applied.";
            }

            leaf num-entries {
                type uint32;
                description "Number of entries in this filter.";
            }

            leaf oper-filter-id {
                type uint32;
                description "The value of this object uniquely identifies a filter. User-configured filters have values between (1..65535). Other values are reserved for filters that are created (auto-generated) by the system.";
            }

            list entry {
                key "entry-id";
                description "Enter the entry list instance";

                leaf entry-id {
                    type types-filter:entry-id;
                    description "ID for a match criteria and the corresponding action";
                }

                container statistics {
                    description "Enter the statistics context";

                    leaf ingress-hit-pkt {
                        type yang:zero-based-counter64;
                        description "This object indicates the number of times an ingress packet matched this entry.";
                    }

                    leaf ingress-hit-byte {
                        type yang:zero-based-counter64;
                        description "The value of this object indicates the number of bytes of all ingress packets that matched this entry.";
                    }

                    leaf egress-hit-pkt {
                        type yang:zero-based-counter64;
                        description "This object indicates the number of times an egress packet matched this entry.";
                    }

                    leaf egress-hit-byte {
                        type yang:zero-based-counter64;
                        description "This object indicates the number of bytes of all egress packets that matched this entry.";
                    }

                } // container statistics

            } // list entry

        } // list ip-exception

    } // grouping state-filter-ip-exception

    grouping state-filter-ip-exception-ipv6-exception {
        list ipv6-exception {
            key "filter-name";
            description "Enter the ipv6-exception list instance";

            leaf filter-name {
                type types-filter:filter-name;
                description "Filter name";
            }

            leaf applied {
                type boolean;
                description "Indicates whether the filter is applied.";
            }

            leaf num-entries {
                type uint32;
                description "Number of entries in this filter.";
            }

            leaf oper-filter-id {
                type uint32;
                description "The value of this object uniquely identifies a filter. User-configured filters have values between (1..65535). Other values are reserved for filters that are created (auto-generated) by the system.";
            }

            leaf num-sub-entries {
                type uint32;
                description "Number of sub-entries.";
            }

            list entry {
                key "entry-id";
                description "Enter the entry list instance";

                leaf entry-id {
                    type types-filter:entry-id;
                    description "ID for a match criteria and the corresponding action";
                }

                leaf num-sub-entries {
                    type uint32;
                    description "Number of sub-entries.";
                }

                container statistics {
                    description "Enter the statistics context";

                    leaf ingress-hit-pkt {
                        type yang:zero-based-counter64;
                        description "This object indicates the number of times an ingress packet matched this entry.";
                    }

                    leaf ingress-hit-byte {
                        type yang:zero-based-counter64;
                        description "The value of this object indicates the number of bytes of all ingress packets that matched this entry.";
                    }

                    leaf egress-hit-pkt {
                        type yang:zero-based-counter64;
                        description "This object indicates the number of times an egress packet matched this entry.";
                    }

                    leaf egress-hit-byte {
                        type yang:zero-based-counter64;
                        description "This object indicates the number of bytes of all egress packets that matched this entry.";
                    }

                } // container statistics

            } // list entry

        } // list ipv6-exception

    } // grouping state-filter-ip-exception-ipv6-exception

}
