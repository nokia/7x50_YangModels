submodule nokia-state-lag {

    yang-version "1.1";

    belongs-to nokia-state { prefix "state"; }

    import ietf-yang-types                { prefix "yang"; }
    import nokia-sros-yang-extensions     { prefix "sros-ext"; }
    import nokia-types-eth-cfm            { prefix "types-eth-cfm"; }
    import nokia-types-sros               { prefix "types-sros"; }
    import nokia-types-subscriber-mgmt    { prefix "types-submgt"; }

    include nokia-state-eth-cfm;
    include nokia-state-port;

    sros-ext:sros-major-release "rel20";

    organization "Nokia";

    contact
        "Nokia SR OS Support
         Web: <http://www.nokia.com>";

    description
        "Nokia YANG Data model with operational state for link aggregation group on SR OS based routers.

         Copyright 2016 Nokia. All rights reserved. Reproduction of this document
         is authorized on the condition that the foregoing copyright notice is included.

         This nokia-state-lag YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2021-05-19";

    grouping state-lag {
        list lag {
            key "lag-index";
            description "Enter the lag list instance";

            leaf lag-index {
                type types-sros:lag-interface;
                description "LAG index";
            }

            leaf oper-state {
                type types-sros:oper-state;
                description "Operational state of the LAG.";
            }

            leaf lacp-admin-key-autogen {
                type boolean;
                description "lacp-admin-key-autogen is set to 'true' if the LAG administrative key in the lag-configwas auto generated. lacp-admin-key-autogen is set to 'false', if the LAG administrative key was manually configured.";
            }

            leaf threshold-rising {
                type yang:counter32;
                description "counts the number of linkUp or dynamic/static-cost events for the LAG caused by the number of physical ports being greater than tLagPortThreshold value.";
            }

            leaf threshold-falling {
                type yang:counter32;
                description "counts the number of linkDown or dynamic/static-cost events for the LAG caused by the number of physical ports being less or equal than tLagPortThreshold value.";
            }

            leaf if-index {
                type uint32;
                description "ifIndex for the LAG.";
            }

            leaf hardware-mac-address {
                type yang:mac-address;
                description "System generated MAC address for the LAG.";
            }

            leaf forced {
                type enumeration {
                    enum "not-appl"                     { value 0; }
                    enum "active"                       { value 1; }
                    enum "standby"                      { value 2; }
                }
                description "Selection state forced by the tools command";
            }

            leaf available-bandwidth {
                type yang:counter64;
                units "kilobps";
                description "The administrative bandwidth that is still free for booking on this LAG.";
            }

            leaf booked-bandwidth {
                type yang:counter64;
                units "kilobps";
                description "The administrative bandwidth that has been booked.";
            }

            leaf remaining-hold-time {
                type union {
                    type int32 {
                        range "0..2000";
                    }
                    type enumeration {
                        enum "infinite"                     { value -1; }
                    }
                }
                units "deciseconds";
                description "The value indicates the time remaining before this system would switch to the newly eligible sub-group. The value zero indicates that the system would immediately switch back. The value all ones indicates that the system would never switch back autonomously.";
            }

            leaf selected-sub-group {
                type union {
                    type uint32 {
                        range "0..16";
                    }
                    type enumeration {
                        enum "mc-peer"                      { value -1; }
                    }
                }
                description "This value indicates the currently selected sub-group. The value zero indicates that the value is not applicable. The value minus one can appear in a multi-chassis LAG configuration and indicates that the selected sub-group is in the scope of the multi-chassis peer.";
            }

            leaf candidate-sub-group {
                type union {
                    type uint32 {
                        range "1..16";
                    }
                    type enumeration {
                        enum "mc-peer"                      { value -1; }
                    }
                }
                description "This value indicates the candidate sub-group. The value zero indicates that the value is not applicable. The value minus one can appear in a multi-chassis LAG configuration and indicates that the candidate sub-group is in the scope of the multi-chassis peer.";
            }

            leaf sub-group-count {
                type uint32;
                description "This value indicates the number of subgroups configured in this LAG.";
            }

            leaf operational-key {
                type int32 {
                    range "0..65535";
                }
                description "LACP operational key";
            }

            leaf system-id {
                type yang:mac-address;
                description "LACP system identifier.";
            }

            leaf system-priority {
                type int32 {
                    range "0..65535";
                }
                description "LACP system priority.";
            }

            leaf partner-system-id {
                type yang:mac-address;
                description "LACP partner system identifier.";
            }

            leaf partner-priority {
                type int32 {
                    range "0..65535";
                }
                description "LACP partner priority.";
            }

            leaf partner-operational-key {
                type int32 {
                    range "0..65535";
                }
                description "LACP partner operational key";
            }

            leaf number-weight-up {
                type yang:gauge32;
                description "This value indicates the weight of the physical ports that are operational (link up).";
            }

            leaf bandwidth {
                type yang:gauge64;
                description "This value indicates the bandwidth of the lag.";
            }

            leaf number-port-up {
                type yang:gauge32;
                description "This value indicates the number of physical ports that are operational (link up).";
            }

            leaf total-weight {
                type yang:gauge32;
                description "This value indicates the total weight of the physical ports.";
            }

            leaf adaptive-load-balancing-number-rebalance {
                type yang:gauge32;
                description "This value indicates the total number of rebalances.";
            }

            leaf adaptive-load-balancing-diff-most-least-loaded-link {
                type types-sros:percent {
                    range "0..100";
                }
                description "This value indicates the diff in percentage between the most and least loaded link.";
            }

            container multi-chassis {
                description "Enter the multi-chassis context";

                leaf active-standby {
                    type enumeration {
                        enum "active"                       { value 1; }
                        enum "stand-by"                     { value 2; }
                    }
                    description "Indicates active standby state of the MC-LAG.";
                }

                leaf selection-reason {
                    type types-sros:display-string-or-empty {
                        length "0..255";
                    }
                    description "Selection reason";
                }

                leaf config-mismatch-reason {
                    type types-sros:display-string-or-empty {
                        length "0..255";
                    }
                    description "Configuration mismatch reason";
                }

                leaf extended-timeout {
                    type boolean;
                    description "Extended timeout";
                }

            } // container multi-chassis

            container eth-cfm {
                description "Enter the eth-cfm context";

                list mep {
                    key "md-admin-name ma-admin-name mep-id";
                    description "Enter the mep list instance";

                    leaf md-admin-name {
                        type leafref {
                            path "../../../../eth-cfm/domain/md-admin-name";
                        }
                        description "Admin-assigned maintenance domain index value";
                    }

                    leaf ma-admin-name {
                        type leafref {
                            path "../../../../eth-cfm/domain[md-admin-name=current()/../md-admin-name]/association/ma-admin-name";
                        }
                        description "Maintenance association name";
                    }

                    leaf mep-id {
                        type types-eth-cfm:mep-id-type;
                        description "Maintenance endpoint ID";
                    }

                } // list mep

            } // container eth-cfm

            list port {
                key "port-id";
                description "Enter the port list instance";

                leaf port-id {
                    type leafref {
                        path "../../../port/port-id";
                    }
                    description "Identifier to uniquely identify the port in the LAG";
                }

                leaf active-standby {
                    type enumeration {
                        enum "active"                       { value 1; }
                        enum "stand-by"                     { value 2; }
                    }
                    description "Active/standby selection state of the port in the LAG.";
                }

                leaf oper-state {
                    type types-sros:oper-state;
                    description "Operational state of the member port. This leaf was deprecated in release 21.10 on Nokia SROS series systems. It is replaced by /state/port/oper-state.";
                }

                leaf primary {
                    type boolean;
                    description "Primary port indication.";
                }

                leaf forced {
                    type enumeration {
                        enum "not-appl"                     { value 0; }
                        enum "active"                       { value 1; }
                        enum "standby"                      { value 2; }
                    }
                    description "Selection state forced by the tools command";
                }

                leaf actor-oper-state {
                    type bits {
                        bit lacp-activity                  { position 0; }
                        bit lacp-timeout                   { position 1; }
                        bit aggregation                    { position 2; }
                        bit synchronization                { position 3; }
                        bit collecting                     { position 4; }
                        bit distributing                   { position 5; }
                        bit defaulted                      { position 6; }
                        bit expired                        { position 7; }
                    }
                    description "Actor states for LACP protocol.";
                }

                leaf partner-oper-state {
                    type bits {
                        bit lacp-activity                  { position 0; }
                        bit lacp-timeout                   { position 1; }
                        bit aggregation                    { position 2; }
                        bit synchronization                { position 3; }
                        bit collecting                     { position 4; }
                        bit distributing                   { position 5; }
                        bit defaulted                      { position 6; }
                        bit expired                        { position 7; }
                    }
                    description "Partner states for LACP protocol.";
                }

                leaf actor-port {
                    type int32;
                    description "Actor port for LACP protocol.";
                }

                leaf partner-port {
                    type int32;
                    description "Partner port for LACP protocol.";
                }

                leaf adaptive-load-balancing-egress-rate {
                    type int64;
                    units "kilobps";
                    description "egress rate in kilobps";
                }

                container bfd {
                    description "Enter the bfd context";

                    leaf bfd-state {
                        type enumeration {
                            enum "idle"                         { value 0; }
                            enum "failed"                       { value 1; }
                            enum "failed-fwd"                   { value 2; }
                            enum "waiting"                      { value 3; }
                            enum "waiting-fwd"                  { value 4; }
                            enum "up"                           { value 5; }
                            enum "down"                         { value 6; }
                        }
                        description "The state of the micro-BFD session of this port in this LAG.";
                    }

                    leaf admin-down-time-left {
                        type uint32;
                        units "seconds";
                        description "The time left before this system will react upon the 'AdminDown' State indication.";
                    }

                    leaf setup-time-left {
                        type uint32;
                        units "milliseconds";
                        description "The set-up time left.";
                    }

                } // container bfd

                container lacp-statistics {
                    description "Enter the lacp-statistics context";

                    leaf rx-packets {
                        type yang:counter32;
                        description "number of valid lacp pdu packets received";
                    }

                    leaf tx-packets {
                        type yang:counter32;
                        description "number of valid lacp pdu packets transmitted";
                    }

                    leaf rx-illegal {
                        type yang:counter32;
                        description "number of illegal lacp pdu packets received";
                    }

                    leaf rx-errors {
                        type yang:counter32;
                        description "number of errornous lacp pdu packets received";
                    }

                } // container lacp-statistics

            } // list port

            list link-map-profile {
                key "link-map-profile-id";
                description "Enter the link-map-profile list instance";

                leaf link-map-profile-id {
                    type int32 {
                        range "1..64";
                    }
                    description "Link map profile to control LAG ports";
                }

                leaf active-link {
                    type types-sros:port;
                    description "The active link port for the link map profile.";
                }

            } // list link-map-profile

            container subscriber-management {
                description "Enter the subscriber-management context";

                container statistics {
                    description "Enter the statistics context";

                    leaf last-reset-peak-values {
                        type yang:date-and-time;
                        description "Timestamp of the last reset of the peak values";
                    }

                    list ipv4-hosts {
                        key "counter";
                        description "Enter the ipv4-hosts list instance";

                        leaf counter {
                            type types-submgt:submgt-statistics-ipv4-type;
                            description "Type of submgt ipv4 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv4-hosts

                    list ipv6-hosts {
                        key "counter";
                        description "Enter the ipv6-hosts list instance";

                        leaf counter {
                            type types-submgt:submgt-statistics-ipv6-type;
                            description "Type of submgt ipv6 hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list ipv6-hosts

                    list total-hosts {
                        key "counter";
                        description "Enter the total-hosts list instance";

                        leaf counter {
                            type types-submgt:submgt-statistics-total-type;
                            description "Type of submgt total hosts counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list total-hosts

                    list sessions {
                        key "counter";
                        description "Enter the sessions list instance";

                        leaf counter {
                            type types-submgt:submgt-statistics-session-type;
                            description "Type of submgt sessions counter";
                        }

                        leaf current-value {
                            type uint32;
                            description "Current value of submgt counter";
                        }

                        leaf peak-value {
                            type uint32;
                            description "Peak value of submgt counter";
                        }

                        leaf peak-timestamp {
                            type yang:date-and-time;
                            description "Peak timestamp of submgt counter";
                        }

                    } // list sessions

                } // container statistics

                list svlan {
                    key "vlan-id";
                    description "Enter the svlan list instance";

                    leaf vlan-id {
                        type uint32 {
                            range "0..4094";
                        }
                        description "The VLAN identifier.";
                    }

                    container statistics {
                        description "Enter the statistics context";

                        leaf last-cleared-time {
                            type yang:date-and-time;
                            description "The time when the counters were last cleared.";
                        }

                        leaf ingress-packets {
                            type yang:counter64;
                            description "The number of IP packets received through this port and VLAN.";
                        }

                        leaf ingress-octets {
                            type yang:counter64;
                            description "The number of octets in IP packets received through this port and VLAN.";
                        }

                        leaf egress-packets {
                            type yang:counter64;
                            description "The number of IP packets sent through this port and VLAN.";
                        }

                        leaf egress-octets {
                            type yang:counter64;
                            description "The number of octets in IP packets sent through this port and VLAN.";
                        }

                    } // container statistics

                } // list svlan

            } // container subscriber-management

            container port-scheduler-policy {
                description "Enter the port-scheduler-policy context";

                container statistics {
                    description "Enter the statistics context";

                    leaf policy-name {
                        type types-sros:named-item-or-empty;
                        description "Specifies an port scheduler policy.";
                    }

                    leaf total-forwarded-octets {
                        type yang:counter64;
                        description "Indicates the total number of octets forwarded.";
                    }

                    leaf total-forwarded-packets {
                        type yang:counter64;
                        description "Indicates the total number of packets forwarded.";
                    }

                    leaf total-dropped-octets {
                        type yang:counter64;
                        description "Indicates the total number of octets dropped.";
                    }

                    leaf total-dropped-packets {
                        type yang:counter64;
                        description "Indicates the total number of packets dropped.";
                    }

                    list level {
                        key "priority-level";
                        description "Enter the level list instance";

                        leaf priority-level {
                            type uint32 {
                                range "1..8";
                            }
                            description "Specifies the priority level of the port scheduler policy.";
                        }

                        leaf forwarded-octets {
                            type yang:counter64;
                            description "Indicates the number of octets forwarded for this level.";
                        }

                        leaf forwarded-packets {
                            type yang:counter64;
                            description "Indicates the number of packets forwarded for this level.";
                        }

                        leaf dropped-octets {
                            type yang:counter64;
                            description "Indicates the number of octets dropped for this level.";
                        }

                        leaf dropped-packets {
                            type yang:counter64;
                            description "Indicates the number of packets dropped for this level.";
                        }

                    } // list level

                } // container statistics

            } // container port-scheduler-policy

        } // list lag

    } // grouping state-lag

}
