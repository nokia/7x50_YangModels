module alu-conf-port-cell-sim-r13 {
  yang-version "1";

  namespace "urn:alcatel-lucent.com:sros:ns:yang:conf-port-cell-sim-r13";

  prefix "conf-port-cell-sim-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure SIM cards for a cellular port on 
       SR OS based routers. 
       
       Copyright 2014-2015 Alcatel-Lucent, 2016 Nokia. All rights reserved. 
       Reproduction of this document is authorized on the condition that the 
       foregoing copyright notice is included. 
       
       This alu-conf-port-cell-sim-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-port-cell-sim-r13 {
    container sim {
      description
          "Configure SIM cards for a cellular port";
      leaf sim-card-number {
        type uint32 {
          range "1..2";
        }
      } //sim-card-number

      container description {
        description
            "Configure a description for the SIM card";
        leaf description-string {
          type string {
            length "1..80";
          }
        } //description-string

      } //container description

      container pin {
        description
            "Configure the PIN for the SIM card";
        leaf pin-string {
          type string {
            length "1..500";
          }
        } //pin-string

        leaf hash-hash2-custom {
          type enumeration {
            enum hash;
            enum hash2;
            enum custom;
          }
        } //hash-hash2-custom

      } //container pin

    } //container sim

  } //grouping alu-conf-port-cell-sim-r13

} //module  alu-conf-port-cell-sim-r13
