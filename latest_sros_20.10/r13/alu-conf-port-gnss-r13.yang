module alu-conf-port-gnss-r13 {
  yang-version "1";

  namespace "urn:alcatel-lucent.com:sros:ns:yang:conf-port-gnss-r13";

  prefix "conf-port-gnss-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure Global Navigation Satellite 
       Systems (GNSS) port settings on SR OS based routers. 
       
       Copyright 2014-2015 Alcatel-Lucent, 2016 Nokia. All rights reserved. 
       Reproduction of this document is authorized on the condition that the 
       foregoing copyright notice is included. 
       
       This alu-conf-port-gnss-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-01-17";

  grouping alu-conf-port-gnss-r13 {
    container gnss {
      description
          "Configure Global Navigation Satellite Systems (GNSS) port settings";
      container antenna-cable-delay {
        description
            "Configure the gnss receiver antenna cable delay";
        leaf nanoseconds {
          type uint32 {
            range "0..32767";
          }
          description
              "Attribute nanoseconds for antenna-cable-delay";
        } //nanoseconds

      } //container antenna-cable-delay

      container constellation {
        description
            "Configure the gnss receiver constellation type";
        leaf-list constellation-id {
          type enumeration {
            enum gps;
            enum glonass;
          }
          max-elements 2;
        } //constellation-id

      } //container constellation

      container elevation-mask-angle {
        description
            "Configure the gnss receiver elevation mask angle";
        leaf degrees {
          type uint32 {
            range "0..89";
          }
          description
              "Attribute degrees for elevation-mask-angle";
        } //degrees

      } //container elevation-mask-angle

    } //container gnss

  } //grouping alu-conf-port-gnss-r13

} //module  alu-conf-port-gnss-r13
