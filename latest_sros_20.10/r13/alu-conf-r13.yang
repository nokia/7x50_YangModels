module alu-conf-r13 {
  yang-version "1";

  namespace "urn:alcatel-lucent.com:sros:ns:yang:conf-r13";

  prefix "conf-r13";

  import alu-conf-aa-r13 {
    prefix "conf-aa-r13";
  }
  import alu-conf-aaa-r13 {
    prefix "conf-aaa-r13";
  }
  import alu-conf-bfd-r13 {
    prefix "conf-bfd-r13";
  }
  import alu-conf-bmp-r13 {
    prefix "conf-bmp-r13";
  }
  import alu-conf-calltrace-r13 {
    prefix "conf-calltrace-r13";
  }
  import alu-conf-card-r13 {
    prefix "conf-card-r13";
  }
  import alu-conf-cflowd-r13 {
    prefix "conf-cflowd-r13";
  }
  import alu-conf-con-profvlan-r13 {
    prefix "conf-con-profvlan-r13";
  }
  import alu-conf-conn-prof-r13 {
    prefix "conf-conn-prof-r13";
  }
  import alu-conf-esa-r13 {
    prefix "conf-esa-r13";
  }
  import alu-conf-eth-cfm-r13 {
    prefix "conf-eth-cfm-r13";
  }
  import alu-conf-eth-ring-r13 {
    prefix "conf-eth-ring-r13";
  }
  import alu-conf-eth-tunnel-r13 {
    prefix "conf-eth-tunnel-r13";
  }
  import alu-conf-filter-r13 {
    prefix "conf-filter-r13";
  }
  import alu-conf-gmpls-tunnel-r13 {
    prefix "conf-gmpls-tunnel-r13";
  }
  import alu-conf-grpencryp-r13 {
    prefix "conf-grpencryp-r13";
  }
  import alu-conf-ifgrphandler-r13 {
    prefix "conf-ifgrphandler-r13";
  }
  import alu-conf-isa-r13 {
    prefix "conf-isa-r13";
  }
  import alu-conf-lag-r13 {
    prefix "conf-lag-r13";
  }
  import alu-conf-li-r13 {
    prefix "conf-li-r13";
  }
  import alu-conf-log-r13 {
    prefix "conf-log-r13";
  }
  import alu-conf-macsec-r13 {
    prefix "conf-macsec-r13";
  }
  import alu-conf-mcastmgmt-r13 {
    prefix "conf-mcastmgmt-r13";
  }
  import alu-conf-mirror-r13 {
    prefix "conf-mirror-r13";
  }
  import alu-conf-oam-pm-r13 {
    prefix "conf-oam-pm-r13";
  }
  import alu-conf-open-flow-r13 {
    prefix "conf-open-flow-r13";
  }
  import alu-conf-port-policy-r13 {
    prefix "conf-port-policy-r13";
  }
  import alu-conf-port-r13 {
    prefix "conf-port-r13";
  }
  import alu-conf-pxc-r13 {
    prefix "conf-pxc-r13";
  }
  import alu-conf-python-r13 {
    prefix "conf-python-r13";
  }
  import alu-conf-qos-r13 {
    prefix "conf-qos-r13";
  }
  import alu-conf-redundancy-r13 {
    prefix "conf-redundancy-r13";
  }
  import alu-conf-router-r13 {
    prefix "conf-router-r13";
  }
  import alu-conf-saa-r13 {
    prefix "conf-saa-r13";
  }
  import alu-conf-service-r13 {
    prefix "conf-service-r13";
  }
  import alu-conf-sflow-r13 {
    prefix "conf-sflow-r13";
  }
  import alu-conf-sfm-r13 {
    prefix "conf-sfm-r13";
  }
  import alu-conf-subscrmgmt-r13 {
    prefix "conf-subscrmgmt-r13";
  }
  import alu-conf-system-r13 {
    prefix "conf-system-r13";
  }
  import alu-conf-vrrp-r13 {
    prefix "conf-vrrp-r13";
  }
  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure SR OS based routers. 
       
       Copyright 2014-2015 Alcatel-Lucent, 2016 Nokia. All rights reserved. 
       Reproduction of this document is authorized on the condition that the 
       foregoing copyright notice is included. 
       
       This alu-conf-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-09-23";

  container configure {
    description
        "Configuration commands";
    uses "conf-aaa-r13:alu-conf-aaa-r13";
    uses "conf-aa-r13:alu-conf-aa-r13";
    uses "conf-bfd-r13:alu-conf-bfd-r13";
    uses "conf-bmp-r13:alu-conf-bmp-r13";
    uses "conf-calltrace-r13:alu-conf-calltrace-r13";
    uses "conf-card-r13:alu-conf-card-r13";
    uses "conf-cflowd-r13:alu-conf-cflowd-r13";
    uses "conf-conn-prof-r13:alu-conf-conn-prof-r13";
    uses "conf-con-profvlan-r13:alu-conf-con-profvlan-r13";
    uses "conf-esa-r13:alu-conf-esa-r13";
    uses "conf-eth-cfm-r13:alu-conf-eth-cfm-r13";
    uses "conf-eth-ring-r13:alu-conf-eth-ring-r13";
    uses "conf-eth-tunnel-r13:alu-conf-eth-tunnel-r13";
    uses "conf-filter-r13:alu-conf-filter-r13";
    container fwd-path-ext {
      description
          "Configure forward path extension information";
      container sdp-id-range {
        description
            "Configure FPE Sdp Id Range information";
        leaf from {
          type uint32 {
            range "1..32767";
          }
        } //from

        leaf to {
          type uint32 {
            range "1..32767";
          }
          description
              "id";
        } //to

      } //container sdp-id-range

      list fpe {
        key "fpe-id";
        description
            "Configure FPE information";
        leaf fpe-id {
          type uint32 {
            range "1..64";
          }
        } //fpe-id

        container description {
          description
              "Configure FPE description";
          leaf description-string {
            type string {
              length "1..80";
            }
          } //description-string

        } //container description

        container path {
          description
              "Configure FPE path information";
          leaf pxc {
            type uint32 {
              range "1..64";
            }
          } //pxc

          leaf xc-a {
            type string;
            description
                "Attribute lag-id for path";
          } //xc-a

          leaf xc-b {
            type string;
            description
                "lag-id";
          } //xc-b

        } //container path

        leaf pw-port {
          type boolean;
          description
              "Configure FPE pw-port setup";
        }

        leaf sub-mgmt-extensions {
          type boolean;
          description
              "Configure FPE for subscriber management";
        }

        container vxlan-termination {
          description
              "Configure FPE VXLAN termination";
          leaf router {
            type string {
              length "1..32";
            }
            description
                "Attribute router-name for vxlan-termination";
          } //router

          leaf service-name {
            type string;
          } //service-name

        } //container vxlan-termination

      } //list fpe

    } //container fwd-path-ext

    uses "conf-gmpls-tunnel-r13:alu-conf-gmpls-tunnel-r13";
    uses "conf-grpencryp-r13:alu-conf-grpencryp-r13";
    uses "conf-ifgrphandler-r13:alu-conf-ifgrphandler-r13";
    container ipsec {
      description
          "Configure IPsec Parameters";
      leaf show-ipsec-keys {
        type boolean;
        description
            "Enable/disable showing IPsec IKE or ESP keys";
      }

      list cert-profile {
        key "profile-name";
        description
            "Configure certificate profile";
        leaf profile-name {
          type string;
        } //profile-name

        leaf shutdown {
          type boolean;
          description
              "Administratively enable/disable the certificate profile";
        }

        list entry {
          key "entry-id";
          description
              "Configure certificate profile entry information";
          leaf entry-id {
            type uint32 {
              range "1..8";
            }
          } //entry-id

          container cert {
            description
                "Configure certificate file name";
            leaf cert-filename {
              type string {
                length "1..95";
              }
            } //cert-filename

          } //container cert

          container key {
            description
                "Configure key file";
            leaf key-filename {
              type string {
                length "1..95";
              }
            } //key-filename

          } //container key

          container rsa-signature {
            description
                "The RSA signature algorithm";
            leaf rsa-signature-id {
              type enumeration {
                enum pkcs1;
                enum pss;
              }
            } //rsa-signature-id

          } //container rsa-signature

          container send-chain {
            presence
                "Configure chain information";
            list ca-profile {
              key "name";
              description
                  "Configure a Certificate-Authority profile to the send-chain";
              leaf name {
                type string;
              } //name

            } //list ca-profile

          } //container send-chain

        } //list entry

      } //list cert-profile

      list client-db {
        key "db-name";
        description
            "Configure IPsec client database";
        leaf db-name {
          type string;
        } //db-name

        container description {
          description
              "Configure the description for this IPsec client database";
          leaf description-string {
            type string {
              length "1..80";
            }
          } //description-string

        } //container description

        leaf shutdown {
          type boolean;
          description
              "Enable/disable an IPsec client database";
        }

        list client {
          key "client-index";
          description
              "Configure IPsec client information";
          leaf client-index {
            type string {
            }
            description
                "[1..8000]";
          } //client-index

          container client-name {
            description
                "Configure the name of this IPsec client";
            leaf name {
              type string;
            } //name

          } //container client-name

          container private-interface {
            description
                "Configure the private interface name of this IPsec client";
            leaf ip-int-name {
              type string {
                length "1..32";
              }
            } //ip-int-name

          } //container private-interface

          container private-service {
            description
                "Configure the private VPRN service of this IPsec client";
            leaf service-id {
              type string;
              description
                  "Attribute service-id for private-service";
            } //service-id

            leaf name {
              type string;
            } //name

          } //container private-service

          leaf shutdown {
            type boolean;
            description
                "Enable/disable an IPsec client entry";
          }

          container ts-negotiation {
            description
                "Configure the traffic-selector negotiation list of this IPsec client";
            leaf ts-list {
              type string;
            } //ts-list

          } //container ts-negotiation

          container tunnel-template {
            description
                "Configure the tunnel template ID of this IPsec client";
            leaf tunnel-template-id {
              type uint32 {
                range "1..2048";
              }
            } //tunnel-template-id

          } //container tunnel-template

          container client-identification {
            description
                "Configure client ID information of this IPsec client";
            container idi {
              description
                  "Configure the Identification Initiator (IDi) field in the client ID of this 
                   IPsec client";
              leaf any {
                type boolean;
                description
                    "keyword - Match any value in the IDi field of the 
                     client ID";
              } //any

              leaf ipv4-prefix {
                type string {
                }
                description
                    "Attribute any|ipv4-prefix/ipv4-prefix-length for idi";
              } //ipv4-prefix

              leaf ipv6-prefix {
                type string {
                }
                description
                    "Attribute any|ipv6-prefix/ipv6-prefix-length for idi";
              } //ipv6-prefix

              leaf string-type {
                type enumeration {
                  enum fqdn;
                  enum fqdn-suffix;
                  enum rfc822;
                  enum rfc822-suffix;
                }
              } //string-type

              leaf string-value {
                type string {
                }
              } //string-value

            } //container idi

            container peer-ip-prefix {
              description
                  "Configure the peer IP prefix field in the client ID of this IPsec client";
              leaf ipv4-any {
                type boolean;
                description
                    "keyword - match any IPv4 prefix";
              } //ipv4-any

              leaf ipv6-any {
                type boolean;
                description
                    "keyword - match any IPv6 prefix";
              } //ipv6-any

              leaf ip-prefix-ip-prefix-length {
                type string {
                  length "1..64";
                }
                description
                    "Attribute ip-prefix/ip-prefix-length for peer-ip-prefix";
              } //ip-prefix-ip-prefix-length

            } //container peer-ip-prefix

          } //container client-identification

          container credential {
            description
                "Configure credential information of this IPsec client";
            container pre-shared-key {
              description
                  "Configure the pre-shared key of this IPsec client";
              leaf key {
                type string {
                  length "1..500";
                }
                description
                    "64 chars max";
              } //key

              leaf hash-hash2-custom {
                type enumeration {
                  enum hash;
                  enum hash2;
                  enum custom;
                }
                description
                    "keyword - hashing scheme used in the hashed key";
              } //hash-hash2-custom

            } //container pre-shared-key

          } //container credential

        } //list client

        container match-list {
          description
              "Configure client ID types used in the IPsec client matching";
          leaf idi {
            type boolean;
            description
                "Configure Identification Initiator (IDi) type in the IPsec client matching";
          }

          leaf peer-ip-prefix {
            type boolean;
            description
                "Configure peer IP prefix type in the IPsec client matching";
          }

        } //container match-list

      } //list client-db

      list ike-policy {
        key "ike-policy-id";
        description
            "Configure IPsec IKE Policy";
        leaf ike-policy-id {
          type uint32 {
            range "1..2048";
          }
        } //ike-policy-id

        container auth-algorithm {
          status "obsolete";
          description
              "Configure Authentication Algorithm for this IKE policy";
          leaf auth-algorithm {
            type enumeration {
              enum md5;
              enum sha1;
              enum sha256;
              enum sha384;
              enum sha512;
              enum aes-xcbc;
            }
            description
                "Attribute auth-algorithm for auth-algorithm";
          } //auth-algorithm

        } //container auth-algorithm

        container auth-method {
          description
              "Configure authentication method for this IKE policy";
          leaf auth-method-id {
            type enumeration {
              enum psk;
              enum plain-psk-xauth;
              enum cert-auth;
              enum psk-radius;
              enum cert-radius;
              enum eap;
              enum auto-eap-radius;
              enum auto-eap;
            }
          } //auth-method-id

        } //container auth-method

        container auto-eap-method {
          description
              "Configure auto EAP method";
          leaf auto-eap-method-id {
            type enumeration {
              enum psk;
              enum cert;
              enum psk-or-cert;
            }
          } //auto-eap-method-id

        } //container auto-eap-method

        container auto-eap-own-method {
          description
              "Configure auto EAP method for itself";
          leaf auto-eap-own-method-id {
            type enumeration {
              enum psk;
              enum cert;
            }
          } //auto-eap-own-method-id

        } //container auto-eap-own-method

        container description {
          description
              "Configure description for this IKE policy";
          leaf description-string {
            type string {
              length "1..80";
            }
          } //description-string

        } //container description

        container dh-group {
          status "obsolete";
          description
              "Configure dh-group for this IKE policy";
          leaf dh-group-id {
            type enumeration {
              enum 1;
              enum 2;
              enum 5;
              enum 14;
              enum 15;
            }
          } //dh-group-id

        } //container dh-group

        container dpd {
          description
              "Configure DPD Parameters";
          leaf interval {
            type uint32 {
              range "10..300";
            }
            description
                "[10..300] in seconds";
          } //interval

          leaf max-retries {
            type uint32 {
              range "2..5";
            }
          } //max-retries

          leaf reply-only {
            type boolean;
            description
                "keyword to enable reply only mode";
          } //reply-only

        } //container dpd

        container encryption-algorithm {
          status "obsolete";
          description
              "Configure Encryption Algorithm for this IKE policy";
          leaf encryption-algorithm {
            type enumeration {
              enum des;
              enum 3des;
              enum aes128;
              enum aes192;
              enum aes256;
            }
          } //encryption-algorithm

        } //container encryption-algorithm

        container ike-mode {
          description
              "Configure IKE mode for this IKE policy";
          leaf ike-mode-id {
            type enumeration {
              enum main;
              enum aggressive;
            }
          } //ike-mode-id

        } //container ike-mode

        container ike-transform {
          description
              "Configure transforms of IKE";
          leaf-list ike-transform-id {
            type uint32 {
              range "1..4096";
            }
            max-elements 4;
          } //ike-transform-id

        } //container ike-transform

        container ike-version {
          description
              "Configure version of IKE";
          leaf ike-version-id {
            type int32 {
              range "1..2";
            }
          } //ike-version-id

        } //container ike-version

        leaf ikev1-ph1-responder-delete-notify {
          type boolean;
          description
              "Enable/disable sending a delete message to the peer, as a responder, when an 
               IKEv1 phase 1 is expired or removed";
        }

        container ikev2-fragment {
          description
              "Configure IKEv2 fragmentation parameters";
          leaf mtu {
            type uint32 {
              range "512..9000";
            }
          } //mtu

          leaf reassembly-timeout {
            type uint32 {
              range "1..5";
            }
          } //reassembly-timeout

        } //container ikev2-fragment

        container ipsec-lifetime {
          description
              "Configure Phase2 life time for this IKE policy";
          leaf ipsec-lifetime {
            type uint32 {
              range "1200..31536000";
            }
            description
                "[1200..31536000] in seconds";
          } //ipsec-lifetime

        } //container ipsec-lifetime

        container isakmp-lifetime {
          status "obsolete";
          description
              "Configure Phase1 life time for this IKE policy";
          leaf isakmp-lifetime {
            type uint32 {
              range "1200..172800";
            }
            description
                "[1200..172800] in seconds";
          } //isakmp-lifetime

        } //container isakmp-lifetime

        container limit-init-exchange {
          description
              "Limits the number of in-progress initial IKE exchanges to one per IPsec tunnel";
          leaf reduced-max-exchange-timeout {
            type string {
            }
            description
                "[2..60]|disabled 
                 Default: limit-init-exchange reduced-max-exchange-timeout 2";
          } //reduced-max-exchange-timeout

        } //container limit-init-exchange

        container lockout {
          description
              "Configure IPsec Lockout for this IKE policy";
          leaf failed-attempts {
            type uint32 {
              range "1..64";
            }
            default 3;
            description
                "[1..64] - Default: 3";
          } //failed-attempts

          leaf duration {
            type uint32 {
              range "1..60";
            }
            default 5;
            description
                "[1..60] - Default: 5";
          } //duration

          leaf block {
            type string {
            }
            description
                "[1..1440]|infinite - Default: 10";
          } //block

          leaf max-port-per-ip {
            type uint32 {
              range "1..32000";
            }
            default 16;
            description
                "[1..32000] - Default: 16";
          } //max-port-per-ip

        } //container lockout

        leaf match-peer-id-to-cert {
          type boolean;
          description
              "Enable/disable matching of peer identifier with certificate";
        }

        container nat-traversal {
          description
              "Configure NAT Traversal Parameters";
          leaf force {
            type boolean;
            description
                "keyword to enable force mode";
          } //force

          leaf keep-alive-interval {
            type uint32 {
              range "120..600";
            }
            description
                "[120..600] in seconds";
          } //keep-alive-interval

          leaf force-keep-alive {
            type boolean;
            description
                "keyword to send keep alives even when not behind a NAT";
          } //force-keep-alive

        } //container nat-traversal

        container own-auth-method {
          description
              "Configure authentication method for IKE policy itself";
          leaf own-auth-method-id {
            type enumeration {
              enum psk;
              enum cert;
              enum eap-only;
            }
          } //own-auth-method-id

        } //container own-auth-method

        container pfs {
          description
              "Configure PFS for this IKE policy";
          leaf dh-group {
            type enumeration {
              enum 1;
              enum 2;
              enum 5;
              enum 14;
              enum 15;
              enum 19;
              enum 20;
              enum 21;
            }
          } //dh-group

        } //container pfs

        leaf send-idr-after-eap-success {
          type boolean;
          description
              "Enable/disable sending the IDr payload in the last IKE authentication response 
               after an EAP success";
        }

        container relay-unsolicited-cfg-attribute {
          description
              "Configure unsolicited attributes for this IKE policy";
          leaf internal-ip4-address {
            type boolean;
            description
                "Configure internalIp4Address attribute for this IKE policy";
          }

          leaf internal-ip4-dns {
            type boolean;
            description
                "Configure internalIp4Dns attribute for this IKE policy";
          }

          leaf internal-ip4-netmask {
            type boolean;
            description
                "Configure internalIp4Netmask attribute for this IKE policy";
          }

          leaf internal-ip6-address {
            type boolean;
            description
                "Configure internalIp6Address attribute for this IKE policy";
          }

          leaf internal-ip6-dns {
            type boolean;
            description
                "Configure internalIp6Dns attribute for this IKE policy";
          }

        } //container relay-unsolicited-cfg-attribute

      } //list ike-policy

      list ike-transform {
        key "ike-transform-id";
        description
            "Configure IKE Transform";
        leaf ike-transform-id {
          type uint32 {
            range "1..4096";
          }
        } //ike-transform-id

        container dh-group {
          description
              "Configure the Diffie-Hellman (DH) group for this IKE transform";
          leaf dh-group-id {
            type enumeration {
              enum 1;
              enum 2;
              enum 5;
              enum 14;
              enum 15;
              enum 19;
              enum 20;
              enum 21;
            }
          } //dh-group-id

        } //container dh-group

        container ike-auth-algorithm {
          description
              "Configure the authentication algorithm for this IKE transform";
          leaf ike-auth-algorithm-id {
            type enumeration {
              enum md5;
              enum sha1;
              enum sha256;
              enum sha384;
              enum sha512;
              enum aes-xcbc;
              enum auth-encryption;
            }
          } //ike-auth-algorithm-id

        } //container ike-auth-algorithm

        container ike-encryption-algorithm {
          description
              "Configure the encryption algorithm for this IKE transform";
          leaf ike-encryption-algorithm-id {
            type enumeration {
              enum des;
              enum 3des;
              enum aes128;
              enum aes192;
              enum aes256;
              enum aes128-gcm8;
              enum aes128-gcm16;
              enum aes256-gcm8;
              enum aes256-gcm16;
            }
          } //ike-encryption-algorithm-id

        } //container ike-encryption-algorithm

        container ike-prf-algorithm {
          description
              "Configure the PRF algorithm for this IKE transform";
          leaf ike-prf-algorithm-id {
            type enumeration {
              enum md5;
              enum sha1;
              enum sha256;
              enum sha384;
              enum sha512;
              enum aes-xcbc;
              enum same-as-auth;
            }
          } //ike-prf-algorithm-id

        } //container ike-prf-algorithm

        container isakmp-lifetime {
          description
              "Configure the Phase 1 life time for this IKE transform";
          leaf seconds {
            type uint32 {
              range "1200..31536000";
            }
            default 86400;
            description
                "[1200..31536000] - Default: 86400";
          } //seconds

        } //container isakmp-lifetime

      } //list ike-transform

      list ipsec-transform {
        key "transform-id";
        description
            "Configure IPsec Transform";
        leaf transform-id {
          type uint32 {
            range "1..2048";
          }
        } //transform-id

        container esp-auth-algorithm {
          description
              "Configure Authentication Algorithm for this transform";
          leaf esp-auth-algorithm-id {
            type enumeration {
              enum null;
              enum md5;
              enum sha1;
              enum sha256;
              enum sha384;
              enum sha512;
              enum aes-xcbc;
              enum auth-encryption;
            }
          } //esp-auth-algorithm-id

        } //container esp-auth-algorithm

        container esp-encryption-algorithm {
          description
              "Configure Encryption Algorithm for this transform";
          leaf esp-encryption-algorithm-id {
            type enumeration {
              enum null;
              enum des;
              enum 3des;
              enum aes128;
              enum aes192;
              enum aes256;
              enum aes128-gcm8;
              enum aes128-gcm12;
              enum aes128-gcm16;
              enum aes192-gcm8;
              enum aes192-gcm12;
              enum aes192-gcm16;
              enum aes256-gcm8;
              enum aes256-gcm12;
              enum aes256-gcm16;
              enum null-aes128-gmac;
              enum null-aes192-gmac;
              enum null-aes256-gmac;
            }
          } //esp-encryption-algorithm-id

        } //container esp-encryption-algorithm

        container ipsec-lifetime {
          description
              "Configure the phase 2 lifetime for this transform";
          leaf seconds {
            type uint32 {
              range "1200..31536000";
            }
            default 3600;
          } //seconds

          leaf inherit {
            type boolean;
            description
                "Default - inherit the value from IKE policy ipsec-lifetime";
          } //inherit

        } //container ipsec-lifetime

        container pfs-dh-group {
          description
              "Configure the Diffie-Hellman (DH) group for this transform";
          leaf pfs-dh-group-id {
            type enumeration {
              enum 1;
              enum 2;
              enum 5;
              enum 14;
              enum 15;
              enum 19;
              enum 20;
              enum 21;
            }
          } //pfs-dh-group-id

          leaf inherit {
            type boolean;
            description
                "Default - inherit the value from IKE policy dh-group";
          } //inherit

        } //container pfs-dh-group

      } //list ipsec-transform

      list radius-accounting-policy {
        key "name";
        description
            "Configure a RADIUS accounting policy";
        leaf name {
          type string {
            length "1..32";
          }
        } //name

        container radius-server-policy {
          description
              "Configure a RADIUS server policy for this policy";
          leaf radius-server-policy-name {
            type string {
              length "1..32";
            }
          } //radius-server-policy-name

        } //container radius-server-policy

        container update-interval {
          description
              "Configure a RADIUS update interval for this policy";
          leaf minutes {
            type uint32 {
              range "5..259200";
            }
          } //minutes

          leaf jitter {
            type int32 {
              range "0..3600";
            }
          } //jitter

        } //container update-interval

        container include-radius-attribute {
          presence
              "Configure RADIUS attributes to be included";
          leaf acct-stats {
            type boolean;
            description
                "Enable/disable include of accouting statistics attribute";
          }

          leaf called-station-id {
            type boolean;
            description
                "Enable/disable include of called-station-id attribute";
          }

          leaf calling-station-id {
            type boolean;
            description
                "Enable/disable include of calling-station-id attribute";
          }

          leaf framed-ip-addr {
            type boolean;
            description
                "Enable/disable include of framed-ip-addr attribute";
          }

          leaf framed-ipv6-prefix {
            type boolean;
            description
                "Enable/disable include of framed-ipv6-prefix attribute";
          }

          leaf nas-identifier {
            type boolean;
            description
                "Enable/disable include of the NAS-Identifier attribute";
          }

          leaf nas-ip-addr {
            type boolean;
            description
                "Enable/disable include of the NAS ip-address attribute";
          }

          leaf nas-port-id {
            type boolean;
            description
                "Enable/disable include of the NAS-Port-Id attribute";
          }

        } //container include-radius-attribute

      } //list radius-accounting-policy

      list radius-authentication-policy {
        key "name";
        description
            "Configure a RADIUS authentication policy";
        leaf name {
          type string {
            length "1..32";
          }
        } //name

        container password {
          description
              "Configure the password used in the RADIUS request";
          leaf password {
            type string {
              length "1..500";
            }
            description
                "secret-key - [64 chars max] 
                 hash-key 
                 hash2-key 
                 custom-key";
          } //password

          leaf hash-hash2-custom {
            type enumeration {
              enum hash;
              enum hash2;
              enum custom;
            }
            description
                "keywords - specify hashing scheme";
          } //hash-hash2-custom

        } //container password

        container radius-server-policy {
          description
              "Configure a RADIUS server policy for this policy";
          leaf radius-server-policy-name {
            type string {
              length "1..32";
            }
          } //radius-server-policy-name

        } //container radius-server-policy

        container include-radius-attribute {
          presence
              "Configure applicable RADIUS attributes";
          leaf called-station-id {
            type boolean;
            description
                "Enable/disable generation of the called-station-id RADIUS attribute";
          }

          leaf calling-station-id {
            type boolean;
            description
                "Enable/disable generation of the calling-station-id RADIUS attribute";
          }

          leaf client-cert-subject-key-id {
            type boolean;
            description
                "Enable/disable generation of the subject key identifier RADIUS attribute";
          }

          leaf nas-identifier {
            type boolean;
            description
                "Enable/disable generation of the NAS-Identifier RADIUS attribute";
          }

          leaf nas-ip-addr {
            type boolean;
            description
                "Enable/disable include of the NAS ip-address attribute";
          }

          leaf nas-port-id {
            type boolean;
            description
                "Enable/disable generation of the NAS-Port-Id RADIUS attribute";
          }

        } //container include-radius-attribute

      } //list radius-authentication-policy

      list static-sa {
        key "sa-name";
        description
            "Configure IPsec static Security Association";
        leaf sa-name {
          type string {
            length "1..32";
          }
        } //sa-name

        container authentication {
          description
              "Configure authentication algorithm for this SA";
          leaf auth-algorithm {
            type enumeration {
              enum md5;
              enum sha1;
            }
          } //auth-algorithm

          leaf ascii-key {
            type string {
              length "1..500";
            }
            description
                "md5=16 characters, sha1=20 characters";
          } //ascii-key

          leaf hex-key {
            type string {
              length "1..114";
            }
            description
                "0x... (md5=32 hex nibbles, sha1=40 hex nibbles)";
          } //hex-key

          leaf hash-hash2-custom {
            type enumeration {
              enum hash;
              enum hash2;
              enum custom;
            }
          } //hash-hash2-custom

        } //container authentication

        container description {
          description
              "Configure description for this SA";
          leaf description-string {
            type string {
              length "1..32";
            }
          } //description-string

        } //container description

        container direction {
          description
              "Configure direction for this SA";
          leaf ipsec-direction {
            type enumeration {
              enum inbound;
              enum outbound;
              enum bidirectional;
            }
            description
                "inbound|outbound|bidirectional";
          } //ipsec-direction

        } //container direction

        container protocol {
          description
              "Configure protocol for this SA";
          leaf ipsec-protocol {
            type enumeration {
              enum ah;
              enum esp;
            }
            description
                "ah|esp";
          } //ipsec-protocol

        } //container protocol

        container spi {
          description
              "Configure Security Parameter Index for this SA";
          leaf spi {
            type uint32 {
              range "256..16383";
            }
            description
                "[256..16383]";
          } //spi

        } //container spi

      } //list static-sa

      list trust-anchor-profile {
        key "name";
        description
            "Configure IPsec Trust Anchor profile information";
        leaf name {
          type string;
        } //name

        list trust-anchor {
          key "ca-profile-name";
          description
              "Configure IPsec Trust Anchor";
          leaf ca-profile-name {
            type string {
              length "1..32";
            }
          } //ca-profile-name

        } //list trust-anchor

      } //list trust-anchor-profile

      list ts-list {
        key "list-name";
        description
            "Configure IPsec traffic-selector list information";
        leaf list-name {
          type string;
        } //list-name

        container local {
          description
              "Configure IPsec traffic selector list local information";
          list entry {
            key "entry-id";
            description
                "Configure IPsec traffic selector list local entry information";
            leaf entry-id {
              type uint32 {
                range "1..32";
              }
            } //entry-id

            container address {
              description
                  "Configure address range for the local entry";
              leaf from {
                type string {
                }
                description
                    "Attribute begin-ip-address for address";
              } //from

              leaf to {
                type string {
                }
                description
                    "end-ip-address";
              } //to

              leaf prefix {
                type string {
                }
                description
                    "Attribute ip-prefix/ip-prefix-len for address";
              } //prefix

            } //container address

            container protocol {
              description
                  "Configure the protocol port range for the local entry";
              leaf protocol-id {
                type string {
                }
                description
                    "[1..255] | <tcp|udp|sctp|icmp|icmp6|ipv6-mh>";
              } //protocol-id

              leaf port {
                type boolean;
              } //port

              leaf any {
                type boolean;
                description
                    "keyword - Match any value in the selected field";
              } //any

              leaf opaque {
                type boolean;
                description
                    "keyword - Match only when the selected field is 
                     not available";
              } //opaque

              leaf from {
                type string {
                }
                description
                    "Attribute begin-port-identifier for protocol";
              } //from

              leaf to {
                type string {
                }
                description
                    "same as <begin-port-identifier>";
              } //to

            } //container protocol

          } //list entry

        } //container local

        container remote {
          description
              "Configure IPsec traffic selector list remote information";
          list entry {
            key "entry-id";
            description
                "Configure IPsec traffic selector list remote entry information";
            leaf entry-id {
              type uint32 {
                range "1..32";
              }
            } //entry-id

            container address {
              description
                  "Configure address range for the remote entry";
              leaf from {
                type string {
                }
                description
                    "Attribute begin-ip-address for address";
              } //from

              leaf to {
                type string {
                }
                description
                    "end-ip-address";
              } //to

              leaf prefix {
                type string {
                }
                description
                    "Attribute ip-prefix/ip-prefix-len for address";
              } //prefix

            } //container address

            container protocol {
              description
                  "Configure the protocol port range for the remote entry";
              leaf protocol-id {
                type string {
                }
                description
                    "[1..255] | <tcp|udp|sctp|icmp|icmp6|ipv6-mh>";
              } //protocol-id

              leaf port {
                type boolean;
              } //port

              leaf any {
                type boolean;
                description
                    "keyword - Match any value in the selected field";
              } //any

              leaf opaque {
                type boolean;
                description
                    "keyword - Match only when the selected field is 
                     not available";
              } //opaque

              leaf from {
                type string {
                }
                description
                    "Attribute begin-port-identifier for protocol";
              } //from

              leaf to {
                type string {
                }
                description
                    "same as <begin-port-identifier>";
              } //to

            } //container protocol

          } //list entry

        } //container remote

      } //list ts-list

      list tunnel-template {
        key "ipsec-template-identifier";
        description
            "Configure IPSec Tunnel Template";
        leaf ipsec-template-identifier {
          type uint32 {
            range "1..2048";
          }
        } //ipsec-template-identifier

        leaf clear-df-bit {
          type boolean;
          description
              "Enable/disable clearing of Do-not-Fragment bit";
        }

        container description {
          description
              "Configure description";
          leaf description-string {
            type string {
              length "1..80";
            }
            description
                "80 char max";
          } //description-string

        } //container description

        container encapsulated-ip-mtu {
          description
              "Configure the template encapsulated IP MTU";
          leaf octets {
            type uint32 {
              range "512..9000";
            }
          } //octets

        } //container encapsulated-ip-mtu

        container ip-mtu {
          description
              "Configure the template IP MTU";
          leaf octets {
            type uint32 {
              range "512..9000";
            }
          } //octets

        } //container ip-mtu

        container private-tcp-mss-adjust {
          description
              "Configure the TCP MSS on private network";
          leaf octets {
            type uint32 {
              range "512..9000";
            }
          } //octets

        } //container private-tcp-mss-adjust

        container public-tcp-mss-adjust {
          description
              "Configure the TCP MSS on public network";
          leaf octets {
            type uint32 {
              range "512..9000";
            }
          } //octets

          leaf auto {
            type boolean;
          } //auto

        } //container public-tcp-mss-adjust

        container replay-window {
          description
              "Configure Anti replay window for the tunnel template";
          leaf replay-window-id {
            type enumeration {
              enum 32;
              enum 64;
              enum 128;
              enum 256;
              enum 512;
            }
          } //replay-window-id

        } //container replay-window

        container sp-reverse-route {
          description
              "Configure reverse-route";
          leaf ignore-default-route {
            type boolean;
          } //ignore-default-route

        } //container sp-reverse-route

        container transform {
          description
              "Configure IPSec transform";
          leaf-list transform-id {
            type uint32 {
              range "1..2048";
            }
            max-elements 4;
            description
                "[1..2048]";
          } //transform-id

        } //container transform

        container icmp6-generation {
          description
              "Configure ICMPv6 generation information";
          container packet-too-big {
            status "obsolete";
            description
                "Configures the rate for ICMPv6 packet-too-big messages";
            leaf number {
              type uint32 {
                range "10..1000";
              }
            } //number

            leaf seconds {
              type uint32 {
                range "1..60";
              }
            } //seconds

          } //container packet-too-big

          container pkt-too-big {
            presence
                "Enable/disable the generation of the ICMPv6 packet too big messages";
            container interval {
              description
                  "Configure the maximum interval that the ICMPv6 messages can be sent";
              leaf seconds {
                type uint32 {
                  range "1..60";
                }
                default 10;
                description
                    "[1..60] - Default: 10";
              } //seconds

            } //container interval

            container message-count {
              description
                  "Configure the maximum number of ICMPv6 messages that can be sent during the 
                   period specified by 'interval'";
              leaf count {
                type uint32 {
                  range "10..1000";
                }
                default 100;
                description
                    "[10..1000] - Default: 100";
              } //count

            } //container message-count

          } //container pkt-too-big

        } //container icmp6-generation

      } //list tunnel-template

    } //container ipsec

    uses "conf-isa-r13:alu-conf-isa-r13";
    uses "conf-lag-r13:alu-conf-lag-r13";
    uses "conf-li-r13:alu-conf-li-r13";
    uses "conf-log-r13:alu-conf-log-r13";
    uses "conf-macsec-r13:alu-conf-macsec-r13";
    uses "conf-mcastmgmt-r13:alu-conf-mcastmgmt-r13";
    uses "conf-mirror-r13:alu-conf-mirror-r13";
    uses "conf-oam-pm-r13:alu-conf-oam-pm-r13";
    uses "conf-open-flow-r13:alu-conf-open-flow-r13";
    uses "conf-port-r13:alu-conf-port-r13";
    uses "conf-port-policy-r13:alu-conf-port-policy-r13";
    uses "conf-pxc-r13:alu-conf-pxc-r13";
    list pw-port {
      key "pw-port-id";
      description
          "Configure a pseudo-wire port";
      leaf pw-port-id {
        type uint32 {
          range "1..32767";
        }
      } //pw-port-id

      list description {
        key "description-string";
        description
            "Add/remove a text description for the pw-port";
        leaf description-string {
          type string {
            length "1..160";
          }
        } //description-string

      } //list description

      container dot1q-etype {
        description
            "Configure Dot1Q Eth-Type encapsulation";
        leaf dot1q-etype {
          type string;
          description
              "Attribute dot1q-etype for dot1q-etype";
        } //dot1q-etype

      } //container dot1q-etype

      container encap-type {
        description
            "Configure encap-type for pseudo-wire port";
        leaf encap-type-id {
          type enumeration {
            enum dot1q;
            enum qinq;
          }
        } //encap-type-id

      } //container encap-type

      container qinq-etype {
        description
            "Configure QinQ Eth-Type encapsulation";
        leaf qinq-etype {
          type string;
          description
              "Attribute qinq-etype for qinq-etype";
        } //qinq-etype

      } //container qinq-etype

    } //list pw-port

    uses "conf-python-r13:alu-conf-python-r13";
    uses "conf-qos-r13:alu-conf-qos-r13";
    uses "conf-redundancy-r13:alu-conf-redundancy-r13";
    uses "conf-router-r13:alu-conf-router-r13";
    uses "conf-saa-r13:alu-conf-saa-r13";
    uses "conf-service-r13:alu-conf-service-r13";
    uses "conf-sflow-r13:alu-conf-sflow-r13";
    uses "conf-sfm-r13:alu-conf-sfm-r13";
    uses "conf-subscrmgmt-r13:alu-conf-subscrmgmt-r13";
    uses "conf-system-r13:alu-conf-system-r13";
    container test-oam {
      description
          "Configure Operations, Administration, and Maintenance test parameters";
      container mpls-echo-request-downstream-map {
        description
            "Configure the default type of downstream map TLV to send in MPLS echo request 
             PDUs";
        leaf dsmap-ddmap {
          type enumeration {
            enum dsmap;
            enum ddmap;
          }
          default "dsmap";
          description
              "keywords - Downstream Map TLV, or Detailed Downstream Map TLV. Default: dsmap";
        } //dsmap-ddmap

      } //container mpls-echo-request-downstream-map

      container mpls-time-stamp-format {
        description
            "Configure the time stamp format to write and expect in MPLS ping request and 
             reply PDUs";
        leaf rfc4379-unix {
          type enumeration {
            enum rfc4379;
            enum unix;
          }
          default "unix";
          description
              "keyword - Default: unix";
        } //rfc4379-unix

      } //container mpls-time-stamp-format

      container build-packet {
        description
            "Configure a packet to be launched by the OAM find-egress tool";
        list header {
          key "header-number";
          description
              "Configure a packet header to be launched by the OAM find-egress tool";
          leaf header-number {
            type uint64 {
              range "1..65535";
            }
          } //header-number

          leaf control-word {
            type boolean;
            description
                "Configure an Pseudowire Emulation Edge-to-Edge (PWE3) Control Word packet 
                 header to be launched by the OAM find-egress tool";
          }

          leaf gre {
            type boolean;
            description
                "Configure a Generic Routing Encapsulation (GRE) packet header to be launched 
                 by the OAM find-egress tool";
          }

          leaf ipv6-fragment {
            type boolean;
            description
                "Configure an IPv6 Fragment packet header to be launched by the OAM find-egress 
                 tool";
          }

          container dot1q {
            description
                "Configure an IEEE 802.1Q packet header to be launched by the OAM find-egress 
                 tool";
            container prio-code-point {
              description
                  "Configure a Priority Code Point (PCP) for an IEEE 802.1Q packet header to be 
                   launched by the OAM find-egress tool";
              leaf priority-code-point {
                type uint64 {
                  range "0..7";
                }
                default 0;
                description
                    "[0..7] - Default: 0";
              } //priority-code-point

            } //container prio-code-point

            container tag-protocol-id {
              description
                  "Configure a Tag Protocol Identifier (TPID) for an IEEE 802.1Q packet header to 
                   be launched by the OAM find-egress tool";
              leaf t0x0600..0xffff {
                type string {
                  length "1..6";
                }
                description
                    "[1536..65535] - Default: 0x8100 (33024). 
                     Accepts decimal or hex.";
              } //t0x0600..0xffff

            } //container tag-protocol-id

            container vlan-id {
              description
                  "Configure a VLAN Identifier for an IEEE 802.1Q packet header to be launched by 
                   the OAM find-egress tool";
              leaf vlan-id {
                type uint64 {
                  range "0..4095";
                }
                default 0;
                description
                    "[0..4095] - Default: 0";
              } //vlan-id

            } //container vlan-id

          } //container dot1q

          container ethernet {
            description
                "Configure an Ethernet packet header to be launched by the OAM find-egress tool";
            container dst-mac-address {
              description
                  "Configure a destination MAC address for an Ethernet packet header to be 
                   launched by the OAM find-egress tool";
              leaf ieee-address {
                type yang:mac-address;
                default "00:00:00:00:00:00";
                description
                    "<xx:xx:xx:xx:xx:xx> - Default: 00:00:00:00:00:00";
              } //ieee-address

            } //container dst-mac-address

            container src-mac-address {
              description
                  "Configure a source MAC address for an Ethernet packet header to be launched by 
                   the OAM find-egress tool";
              leaf ieee-address {
                type yang:mac-address;
                default "00:00:00:00:00:00";
                description
                    "<xx:xx:xx:xx:xx:xx> - Default: 00:00:00:00:00:00";
              } //ieee-address

            } //container src-mac-address

          } //container ethernet

          container gtp-user {
            description
                "Configure a GPRS Tunneling Protocol, User (GTP-U, version 1) packet header to 
                 be launched by the OAM find-egress tool";
            container tunnel-endpoint-id {
              description
                  "Configure a Tunnel Endpoint Identifier (TEID) for a GTP-U packet header to be 
                   launched by the OAM find-egress tool";
              leaf tunnel-endpoint-id {
                type uint64;
                default 0;
                description
                    "[0..4294967295] - Default: 0";
              } //tunnel-endpoint-id

            } //container tunnel-endpoint-id

          } //container gtp-user

          container ipsec-auth {
            description
                "Configure an IPsec Authentication packet header to be launched by the OAM 
                 find-egress tool";
            container security-param-index {
              description
                  "Configure a Security Parameter Index (SPI) for an IPsec Authentication packet 
                   header to be launched by the OAM find-egress tool";
              leaf security-parameter-index {
                type uint64 {
                  range "1..4294967295";
                }
                default 1;
                description
                    "[1..4294967295] - Default: 1";
              } //security-parameter-index

            } //container security-param-index

          } //container ipsec-auth

          container ipv4 {
            description
                "Configure an IPv4 packet header to be launched by the OAM find-egress tool";
            container dscp {
              description
                  "Configure a Differentiated Services Code Point (DSCP) for an IPv4 packet 
                   header to be launched by the OAM find-egress tool";
              leaf dscp-name {
                type string {
                  length "1..4";
                }
                description
                    "Attribute dscp-name for dscp";
              } //dscp-name

            } //container dscp

            container dst-ipv4-address {
              description
                  "Configure a destination address for an IPv4 packet header to be launched by 
                   the OAM find-egress tool";
              leaf a.b.c.d {
                type inet:ip-address;
                default "0.0.0.0";
                description
                    "Default: 0.0.0.0";
              } //a.b.c.d

            } //container dst-ipv4-address

            container more-fragments {
              description
                  "Configure a More Fragments (MF) flag for an IPv4 packet header to be launched 
                   by the OAM find-egress tool";
              leaf more-fragments {
                type uint64 {
                  range "0..1";
                }
                default 0;
                description
                    "[0..1] - Default: 0 
                     1 means there are more fragments to be sent.";
              } //more-fragments

            } //container more-fragments

            container src-ipv4-address {
              description
                  "Configure a source address for an IPv4 packet header to be launched by the OAM 
                   find-egress tool";
              leaf a.b.c.d {
                type inet:ip-address;
                default "0.0.0.0";
                description
                    "Default: 0.0.0.0";
              } //a.b.c.d

            } //container src-ipv4-address

          } //container ipv4

          container ipv6 {
            description
                "Configure an IPv6 packet header to be launched by the OAM find-egress tool";
            container dscp {
              description
                  "Configure a Differentiated Services Code Point (DSCP) for an IPv6 packet 
                   header to be launched by the OAM find-egress tool";
              leaf dscp-name {
                type string {
                  length "1..4";
                }
                description
                    "Attribute dscp-name for dscp";
              } //dscp-name

            } //container dscp

            container dst-ipv6-address {
              description
                  "Configure a destination address for an IPv6 packet header to be launched by 
                   the OAM find-egress tool";
              leaf ipv6-address {
                type string;
                description
                    "Attribute ipv6-address for dst-ipv6-address";
              } //ipv6-address

            } //container dst-ipv6-address

            container src-ipv6-address {
              description
                  "Configure a source address for an IPv6 packet header to be launched by the OAM 
                   find-egress tool";
              leaf ipv6-address {
                type string;
                description
                    "Attribute ipv6-address for src-ipv6-address";
              } //ipv6-address

            } //container src-ipv6-address

          } //container ipv6

          container l2tp {
            description
                "Configure a Layer 2 Tunneling Protocol (L2TP) packet header to be launched by 
                 the OAM find-egress tool";
            container session-id {
              description
                  "Configure a Session Identifier for an L2TP packet header to be launched by the 
                   OAM find-egress tool";
              leaf session-id {
                type uint64 {
                  range "0..65535";
                }
                default 0;
                description
                    "[0..65535] - Default: 0";
              } //session-id

            } //container session-id

            container tunnel-id {
              description
                  "Configure a Tunnel Identifier for an L2TP packet header to be launched by the 
                   OAM find-egress tool";
              leaf tunnel-id {
                type uint64 {
                  range "0..65535";
                }
                default 0;
                description
                    "[0..65535] - Default: 0";
              } //tunnel-id

            } //container tunnel-id

          } //container l2tp

          container mpls {
            description
                "Configure an MPLS packet header to be launched by the OAM find-egress tool";
            container label {
              description
                  "Configure an MPLS label for an MPLS packet header to be launched by the OAM 
                   find-egress tool";
              leaf label {
                type uint64 {
                  range "0..1048575";
                }
                default 0;
                description
                    "[0..1048575] - Default: 0";
              } //label

            } //container label

            container traffic-class {
              description
                  "Configure an MPLS traffic class for an MPLS packet header to be launched by 
                   the OAM find-egress tool";
              leaf traffic-class {
                type uint64 {
                  range "0..7";
                }
                default 0;
                description
                    "[0..7] - Default: 0";
              } //traffic-class

            } //container traffic-class

          } //container mpls

          container pbb {
            description
                "Configure a Provider Backbone Bridge (PBB) packet header to be launched by the 
                 OAM find-egress tool";
            container i-sid {
              description
                  "Configure a Service Instance Identifier (I-SID) for a PBB packet header to be 
                   launched by the OAM find-egress tool";
              leaf i-sid {
                type uint64 {
                  range "0..16777215";
                }
                default 0;
                description
                    "[0..16777215] - Default: 0";
              } //i-sid

            } //container i-sid

            container tag-protocol-id {
              description
                  "Configure a Tag Protocol Identifier (TPID) for a PBB packet header to be 
                   launched by the OAM find-egress tool";
              leaf t0x0600..0xffff {
                type string {
                  length "1..6";
                }
                description
                    "[1536..65535] - Default: 0x88E7 (35047). 
                     Accepts decimal or hex.";
              } //t0x0600..0xffff

            } //container tag-protocol-id

          } //container pbb

          container tcp {
            description
                "Configure a TCP packet header to be launched by the OAM find-egress tool";
            container dst-tcp-port {
              description
                  "Configure a destination TCP port for a TCP packet header to be launched by the 
                   OAM find-egress tool";
              leaf tcp-port {
                type uint64 {
                  range "0..65535";
                }
                default 0;
                description
                    "[0..65535] - Default: 0";
              } //tcp-port

            } //container dst-tcp-port

            container src-tcp-port {
              description
                  "Configure a source TCP port for a TCP packet header to be launched by the OAM 
                   find-egress tool";
              leaf tcp-port {
                type uint64 {
                  range "0..65535";
                }
                default 0;
                description
                    "[0..65535] - Default: 0";
              } //tcp-port

            } //container src-tcp-port

          } //container tcp

          container udp {
            description
                "Configure a UDP packet header to be launched by the OAM find-egress tool";
            container dst-udp-port {
              description
                  "Configure a destination UDP port for a UDP packet header to be launched by the 
                   OAM find-egress tool";
              leaf udp-port {
                type uint64 {
                  range "0..65535";
                }
                default 0;
                description
                    "[0..65535] - Default: 0";
              } //udp-port

            } //container dst-udp-port

            container src-udp-port {
              description
                  "Configure a source UDP port for a UDP packet header to be launched by the OAM 
                   find-egress tool";
              leaf udp-port {
                type string {
                }
                description
                    "[0..65535] - Default: 0";
              } //udp-port

            } //container src-udp-port

          } //container udp

        } //list header

      } //container build-packet

      container icmp {
        description
            "Configure ICMP test OAM";
        list ping-template {
          key "template-name";
          description
              "set the ping-template for Background Interface Control using ICMP";
          leaf template-name {
            type string;
          } //template-name

          container description {
            description
                "set the description for the ping-template";
            leaf description-string {
              type string {
                length "1..80";
              }
            } //description-string

          } //container description

          container dot1p {
            description
                "Ethernet dot1p bits in outer and any inner header";
            leaf dot1p-value {
              type string;
            } //dot1p-value

          } //container dot1p

          container dscp {
            description
                "set the DSCP to be carried in IP header of the ICMP packet";
            leaf dscp-name {
              type string {
                length "1..32";
              }
            } //dscp-name

          } //container dscp

          container failure-threshold {
            description
                "count operational up to down because of ping-template failures";
            leaf failure-threshold-id {
              type uint32 {
                range "2..10";
              }
            } //failure-threshold-id

          } //container failure-threshold

          container interval {
            description
                "set the packet transmit interval";
            leaf seconds {
              type uint32 {
                range "1..60";
              }
            } //seconds

          } //container interval

          container reactivation-failure-threshold {
            description
                "set number of consecutive failures without previous successes";
            leaf reactivation-failure-threshold-id {
              type uint32 {
                range "1..10";
              }
            } //reactivation-failure-threshold-id

          } //container reactivation-failure-threshold

          container reactivation-interval {
            description
                "packet transmit interval used when IP interface is operational down";
            leaf seconds {
              type uint32 {
                range "1..60";
              }
            } //seconds

          } //container reactivation-interval

          container reactivation-threshold {
            description
                "number of successful ICMP probes to transition from operationally down to up";
            leaf reactivation-threshold-id {
              type uint32 {
                range "1..10";
              }
            } //reactivation-threshold-id

          } //container reactivation-threshold

          container reactivation-timeout {
            description
                "wait time before declaring the packet is lost";
            leaf seconds {
              type uint32 {
                range "1..60";
              }
            } //seconds

          } //container reactivation-timeout

          container size {
            description
                "size of ICMP Echo ping padding field, in bytes";
            leaf octets {
              type uint32 {
                range "12..9786";
              }
            } //octets

          } //container size

          container timeout {
            description
                "time before declaring an ICMP echo request being lost";
            leaf seconds {
              type uint32 {
                range "1..60";
              }
            } //seconds

          } //container timeout

          container ttl {
            description
                "time to live in ICMP packet";
            leaf ttl-id {
              type uint32 {
                range "1..255";
              }
            } //ttl-id

          } //container ttl

        } //list ping-template

      } //container icmp

      container ldp-treetrace {
        presence
            "Configure background LDP tree trace";
        container fc {
          description
              "Configure the QoS forwarding class and profile for packets sent by LDP tree 
               trace";
          leaf fc-name {
            type enumeration {
              enum be;
              enum l2;
              enum af;
              enum l1;
              enum h2;
              enum ef;
              enum h1;
              enum nc;
            }
            default "be";
            description
                "be|l2|af|l1|h2|ef|h1|nc - Default: be";
          } //fc-name

          leaf profile {
            type enumeration {
              enum in;
              enum out;
            }
            default "out";
            description
                "keywords - Default: out";
          } //profile

        } //container fc

        leaf shutdown {
          type boolean;
          description
              "Administratively enable/disable the background LDP tree discovery process";
        }

        container path-discovery {
          description
              "Configure path discovery parameters";
          container interval {
            description
                "Configure path discovery interval";
            leaf minutes {
              type int32 {
                range "60..1440";
              }
              default 60;
              description
                  "[60..1440] - Default: 60";
            } //minutes

          } //container interval

          container max-path {
            description
                "Configure path discovery max-path";
            leaf max-paths {
              type uint8 {
                range "1..128";
              }
              default 128;
              description
                  "[1..128] - Default: 128";
            } //max-paths

          } //container max-path

          container max-ttl {
            description
                "Configure path discovery maximum TTL";
            leaf ttl-value {
              type uint8 {
                range "1..255";
              }
              default 30;
              description
                  "[1..255] - Default: 30";
            } //ttl-value

          } //container max-ttl

          container policy-statement {
            description
                "Configure path discovery policy names";
            leaf-list policy-name {
              type string {
                length "1..32";
              }
              max-elements 5;
            } //policy-name

          } //container policy-statement

          container retry-count {
            description
                "Configure path discovery maximum retries per destination";
            leaf count {
              type uint32 {
                range "1..10";
              }
              default 3;
              description
                  "[1..10] - Default: 3";
            } //count

          } //container retry-count

          container timeout {
            description
                "Configure path discovery timeout";
            leaf timeout {
              type uint64 {
                range "1..60";
              }
              default 30;
              description
                  "[1..60] seconds - Default: 30";
            } //timeout

          } //container timeout

        } //container path-discovery

        container path-probing {
          description
              "Configure path probing parameters";
          container interval {
            description
                "Configure path probing interval";
            leaf minutes {
              type int32 {
                range "1..60";
              }
              default 1;
              description
                  "[1..60] - Default: 1";
            } //minutes

          } //container interval

          container retry-count {
            description
                "Configure path probing maximum retries per destination";
            leaf retry-count {
              type uint32 {
                range "1..10";
              }
              default 3;
              description
                  "[1..10] - Default: 3";
            } //retry-count

          } //container retry-count

          container timeout {
            description
                "Configure path probing timeout";
            leaf timeout {
              type uint64 {
                range "1..3";
              }
              default 1;
              description
                  "[1..3] minutes - Default: 1";
            } //timeout

          } //container timeout

        } //container path-probing

      } //container ldp-treetrace

      container mpls-dm {
        description
            "Configure MPLS Delay Measurement (MPLS-DM)";
        leaf shutdown {
          type boolean;
          description
              "Disable or enable receive processing and transmission of MPLS Delay 
               Measurement (MPLS-DM) packets";
        }

      } //container mpls-dm

      container twamp {
        description
            "Configure the Two Way Active Measurement Protocol (TWAMP)";
        container server {
          description
              "Configure the TWAMP server";
          container inactivity-timeout {
            description
                "Configure the inactivity timeout for the TWAMP server";
            leaf timer {
              type uint32 {
                range "60..3600";
              }
              default 900;
              description
                  "[60..3600] seconds - Default: 900";
            } //timer

          } //container inactivity-timeout

          container max-conn-server {
            description
                "Configure the maximum number of control connections supported by the TWAMP 
                 server";
            leaf count {
              type uint32 {
                range "0..64";
              }
              default 32;
              description
                  "[0..64] connections - Default: 32";
            } //count

          } //container max-conn-server

          container max-sess-server {
            description
                "Configure the maximum number of sessions supported by the TWAMP server";
            leaf count {
              type uint32 {
                range "0..128";
              }
              default 32;
              description
                  "[0..128] sessions - Default: 32";
            } //count

          } //container max-sess-server

          container ref-inactivity-timeout {
            description
                "Configure the reflector inactivity timeout for TWAMP";
            leaf timer {
              type uint64 {
                range "60..3600";
              }
              default 900;
              description
                  "[60..3600] seconds - Default: 900";
            } //timer

          } //container ref-inactivity-timeout

          leaf shutdown {
            type boolean;
            description
                "Administratively enable/disable the TWAMP server";
          }

          list prefix {
            key "ip-prefix-prefix-length";
            description
                "Configure the prefix table for the TWAMP server";
            leaf ip-prefix-prefix-length {
              type string;
              description
                  "Attribute ip-prefix/prefix-length for prefix";
            } //ip-prefix-prefix-length

            container description {
              description
                  "Configure a description for the prefix";
              leaf description-string {
                type string {
                  length "1..80";
                }
              } //description-string

            } //container description

            container max-conn-prefix {
              description
                  "Configure the maximum number of TWAMP control connections supported for the 
                   prefix";
              leaf count {
                type uint32 {
                  range "0..64";
                }
                default 32;
                description
                    "[0..64] connections - Default: 32";
              } //count

            } //container max-conn-prefix

            container max-sess-prefix {
              description
                  "Configure the maximum number of TWAMP sessions supported for the prefix";
              leaf count {
                type uint32 {
                  range "0..128";
                }
                default 32;
                description
                    "[0..128] sessions - Default: 32";
              } //count

            } //container max-sess-prefix

          } //list prefix

        } //container server

        container twamp-light {
          description
              "Configure TWAMP-Light parameters";
          container inactivity-timeout {
            description
                "Configure the inactivity timeout for a TWAMP-Light reflector session";
            leaf seconds {
              type uint64 {
                range "10..100";
              }
              default 100;
              description
                  "[10..100] - Default: 100 seconds";
            } //seconds

          } //container inactivity-timeout

        } //container twamp-light

      } //container twamp

    } //container test-oam

    uses "conf-vrrp-r13:alu-conf-vrrp-r13";
  } //container configure

} //module  alu-conf-r13
