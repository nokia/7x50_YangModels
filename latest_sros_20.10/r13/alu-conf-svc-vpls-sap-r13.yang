module alu-conf-svc-vpls-sap-r13 {
  yang-version "1";

  namespace "urn:alcatel-lucent.com:sros:ns:yang:conf-svc-vpls-sap-r13";

  prefix "conf-svc-vpls-sap-r13";

  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure SAPs for VPLS services on SR OS 
       based routers. 
       
       Copyright 2014-2015 Alcatel-Lucent, 2016 Nokia. All rights reserved. 
       Reproduction of this document is authorized on the condition that the 
       foregoing copyright notice is included. 
       
       This alu-conf-svc-vpls-sap-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-12-04";

  grouping alu-conf-svc-vpls-sap-r13 {
    list sap {
      key "sap-id";
      description
          "Configure SAPs for VPLS services";
      leaf sap-id {
        type string;
        description
            "Attribute sap-id for sap";
      } //sap-id

      leaf split-horizon-group {
        type string {
          length "1..32";
        }
      } //split-horizon-group

      leaf capture-sap {
        type boolean;
      } //capture-sap

      leaf eth-ring {
        type string;
        description
            "Attribute ring-index for sap";
      } //eth-ring

      leaf root-leaf-tag {
        type boolean;
      } //root-leaf-tag

      leaf leaf-tag {
        type uint32 {
          range "1..4094";
        }
      } //leaf-tag

      leaf leaf-ac {
        type boolean;
      } //leaf-ac

      leaf multicast-source {
        type boolean;
      } //multicast-source

      list accounting-policy {
        key "acct-policy-id";
        description
            "Configure accounting-policy to be used";
        leaf acct-policy-id {
          type uint64 {
            range "1..99";
          }
        } //acct-policy-id

      } //list accounting-policy

      leaf allow-dot1q-msaps {
        type boolean;
        description
            "Enable/disable creation of IEEE 802.1q Managed SAP's on an IEEE 802.1ad port";
      }

      container anti-spoof {
        description
            "Configures anti-spoof filtering for this SAP";
        leaf type {
          type enumeration {
            enum ip;
            enum ip-mac;
            enum mac;
            enum nh-mac;
          }
          description
              "Attribute type for anti-spoof";
        } //type

      } //container anti-spoof

      container app-profile {
        description
            "Configure the application profile name";
        leaf app-profile-name {
          type string {
            length "1..32";
          }
        } //app-profile-name

      } //container app-profile

      container arp-reply-agent {
        description
            "Enable/disable arp-reply-agent function";
        leaf sub-ident {
          type boolean;
        } //sub-ident

      } //container arp-reply-agent

      container authentication-policy {
        description
            "Configures the authentication policy for this SAP";
        leaf-list name {
          type string {
            length "1..32";
          }
          max-elements 1;
          description
              "[32 chars max]";
        } //name

      } //container authentication-policy

      container auto-learn-mac-protect {
        description
            "Enable/disable automatic update of MAC protect list";
        leaf exclude-list {
          type string;
        } //exclude-list

      } //container auto-learn-mac-protect

      container bandwidth {
        description
            "Configure SAP Bandwidth";
        leaf bandwidth-in-kbps {
          type string;
          description
              "[1..6400000000]";
        } //bandwidth-in-kbps

      } //container bandwidth

      container bgp-vpls-mh-ve-id {
        description
            "Configure BGP-VPLS multi-homing virtual edge identifier";
        leaf bgp-vpls-mh-ve-id-id {
          type uint32 {
            range "1..65535";
          }
        } //bgp-vpls-mh-ve-id-id

      } //container bgp-vpls-mh-ve-id

      container bpdu-translation {
        description
            "Configure the bpdu translation on this SAP";
        leaf bpdu-translation-id {
          type enumeration {
            enum auto;
            enum auto-rw;
            enum pvst;
            enum pvst-rw;
            enum stp;
          }
        } //bpdu-translation-id

      } //container bpdu-translation

      container calling-station-id {
        description
            "Configure the RADIUS calling-station-id to include in auth/acct requests";
        leaf calling-station-id {
          type string {
            length "1..64";
          }
        } //calling-station-id

      } //container calling-station-id

      leaf cflowd {
        type boolean;
        description
            "Configure Cflowd collection and analysis on this SAP";
      }

      leaf collect-stats {
        type boolean;
        description
            "Enable/disable statistics collection";
      }

      container cpu-protection {
        description
            "Configure CPU protection";
        leaf policy-id {
          type uint32 {
            range "1..255";
          }
        } //policy-id

        leaf mac-monitoring {
          type boolean;
          description
              "keyword - enable MAC monitoring";
        } //mac-monitoring

        leaf eth-cfm-monitoring {
          type boolean;
          description
              "keyword - enable Ethernet Connectivity Fault Management monitoring";
        } //eth-cfm-monitoring

        leaf aggregate {
          type boolean;
          description
              "keyword - apply the rate limit to the sum of the per peer packet rates";
        } //aggregate

        leaf car {
          type boolean;
          description
              "keyword - Committed Access Rate - ignore Eth-CFM packets when enforcing 
               overall-rate";
        } //car

      } //container cpu-protection

      list description {
        key "long-description-string";
        description
            "Description for the SAP";
        leaf long-description-string {
          type string {
            length "1..160";
          }
        } //long-description-string

      } //list description

      container dhcp-python-policy {
        description
            "Configure the Python Policy for DHCP discover";
        leaf policy-name {
          type string {
            length "1..32";
          }
        } //policy-name

      } //container dhcp-python-policy

      container dhcp-user-db {
        description
            "Assign a local user database for DHCP clients (capture SAP only)";
        leaf local-user-db-name {
          type string {
            length "1..32";
          }
        } //local-user-db-name

      } //container dhcp-user-db

      container dhcp6-python-policy {
        description
            "Configure the Python Policy for DHCP6 solicit";
        leaf policy-name {
          type string {
          }
        } //policy-name

      } //container dhcp6-python-policy

      container dhcp6-user-db {
        description
            "Assign a local user database for DHCP6 clients (capture SAP only)";
        leaf local-user-db-name {
          type string {
            length "1..32";
          }
        } //local-user-db-name

      } //container dhcp6-user-db

      container diameter-auth-policy {
        description
            "Configure the Diameter NASREQ application policy to use for authentication";
        leaf name {
          type string;
        } //name

      } //container diameter-auth-policy

      leaf disable-aging {
        type boolean;
        description
            "Enable/disable aging of MAC addresses";
      }

      leaf disable-learning {
        type boolean;
        description
            "Enable/disable learning of new MAC addresses";
      }

      leaf disable-send-bvpls-evpn-flush {
        type boolean;
        description
            "Enable/disable sending of B-VPLS EVPN flush";
      }

      leaf discard-unknown-source {
        type boolean;
        description
            "Enable/disable discarding of frames with unknown source MAC address";
      }

      container dist-cpu-protection {
        description
            "Assign Distributed CPU protection policy for the SAP";
        leaf policy-name {
          type string;
        } //policy-name

      } //container dist-cpu-protection

      list fault-propagation-bmac {
        key "mac-name-ieee-address";
        description
            "Configure a backbone MAC address or backbone MAC name for fault propagation";
        leaf mac-name-ieee-address {
          type string {
            length "1..32";
          }
          description
              "32 char max";
        } //mac-name-ieee-address

      } //list fault-propagation-bmac

      container force-l2pt-boundary {
        description
            "Force L2PT termination on managed VLANs";
        leaf cdp {
          type boolean;
          description
              "keyword - cisco discovery protocol";
        } //cdp

        leaf dtp {
          type boolean;
          description
              "keyword - dynamic trunking protocol";
        } //dtp

        leaf pagp {
          type boolean;
          description
              "keyword - port aggregation protocol";
        } //pagp

        leaf stp {
          type boolean;
          description
              "keyword - all spanning tree protocols: stp, rstp, mstp, pvst (default)";
        } //stp

        leaf udld {
          type boolean;
          description
              "keyword - unidirectional link detection";
        } //udld

        leaf vtp {
          type boolean;
          description
              "keyword - virtual trunk protocol";
        } //vtp

      } //container force-l2pt-boundary

      container host-connectivity-verify {
        description
            "Enable/disable host connectivity verification for all hosts on this SAP";
        leaf source-ip {
          type inet:ip-address;
          description
              "a.b.c.d";
        } //source-ip

        leaf source-mac {
          type alu:ieee-address;
          description
              "xx:xx:xx:xx:xx:xx or xx-xx-xx-xx-xx-xx";
        } //source-mac

        leaf interval {
          type uint64 {
            range "1..6000";
          }
          description
              "[1..6000] minutes";
        } //interval

        leaf action {
          type enumeration {
            enum remove;
            enum alarm;
          }
          description
              "keywords";
        } //action

        leaf timeout {
          type uint8 {
            range "10..60";
          }
          description
              "[10..60] seconds";
        } //timeout

        leaf retry-count {
          type uint8 {
            range "2..29";
          }
          description
              "[2..29]";
        } //retry-count

      } //container host-connectivity-verify

      container host-lockout-policy {
        description
            "Configure host lockout policy";
        leaf policy-name {
          type string {
            length "1..32";
          }
        } //policy-name

      } //container host-lockout-policy

      leaf host-shutdown {
        type boolean;
        description
            "Administratively enable/disable host creation on this SAP";
      }

      container l2pt-termination {
        description
            "Configure L2PT termination on this SAP";
        leaf cdp {
          type boolean;
          description
              "keyword - cisco discovery protocol";
        } //cdp

        leaf dtp {
          type boolean;
          description
              "keyword - dynamic trunking protocol";
        } //dtp

        leaf pagp {
          type boolean;
          description
              "keyword - port aggregation protocol";
        } //pagp

        leaf stp {
          type boolean;
          description
              "keyword - all spanning tree protocols: stp, rstp, mstp, pvst (default)";
        } //stp

        leaf udld {
          type boolean;
          description
              "keyword - unidirectional link detection";
        } //udld

        leaf vtp {
          type boolean;
          description
              "keyword - virtual trunk protocol";
        } //vtp

      } //container l2pt-termination

      container lag-link-map-profile {
        description
            "Configure lag link profile";
        leaf link-map-profile-id {
          type string;
          description
              "Attribute link-map-profile-id for lag-link-map-profile";
        } //link-map-profile-id

      } //container lag-link-map-profile

      container lag-per-link-hash {
        description
            "Configure per-link-hash information";
        leaf class {
          type enumeration {
            enum 1;
            enum 2;
            enum 3;
          }
        } //class

        leaf weight {
          type uint32 {
            range "1..1024";
          }
        } //weight

      } //container lag-per-link-hash

      container limit-mac-move {
        description
            "Configure mac move";
        leaf blockable-non-blockable {
          type enumeration {
            enum blockable;
            enum non-blockable;
          }
        } //blockable-non-blockable

      } //container limit-mac-move

      leaf mac-pinning {
        type boolean;
        description
            "Enable/disable MAC address pinning on this SAP";
      }

      container max-nbr-mac-addr {
        description
            "Configure the maximum number of MAC entries in the FDB from this SAP";
        leaf table-size {
          type string;
          description
              "Attribute table-size for max-nbr-mac-addr";
        } //table-size

      } //container max-nbr-mac-addr

      container monitor-oper-group {
        description
            "Configure an Operational-Group to monitor";
        leaf group-name {
          type string {
            length "1..32";
          }
        } //group-name

      } //container monitor-oper-group

      container multi-service-site {
        description
            "Specify the multi-service-site to which this SAP belongs";
        leaf customer-site-name {
          type string {
            length "1..32";
          }
        } //customer-site-name

      } //container multi-service-site

      container oper-group {
        description
            "Configure operational-group";
        leaf group-name {
          type string {
            length "1..32";
          }
        } //group-name

      } //container oper-group

      container ppp-policy {
        description
            "Assign a PPP policy for PPPoA sessions (ATM capture SAP only)";
        leaf ppp-policy-name {
          type string {
            length "1..32";
          }
        } //ppp-policy-name

      } //container ppp-policy

      container ppp-user-db {
        description
            "Assign a local user database for PPPoA sessions (ATM capture SAP only)";
        leaf local-user-db-name {
          type string {
          }
        } //local-user-db-name

      } //container ppp-user-db

      container pppoe-policy {
        description
            "Assign a PPP policy for PPPoE sessions (capture SAP only)";
        leaf pppoe-policy-name {
          type string {
            length "1..32";
          }
        } //pppoe-policy-name

      } //container pppoe-policy

      container pppoe-python-policy {
        description
            "Configure the Python Policy for PPPoE packets";
        leaf policy-name {
          type string {
            length "1..32";
          }
        } //policy-name

      } //container pppoe-python-policy

      container pppoe-user-db {
        description
            "Assign a local user database for PPPoE sessions (capture SAP only)";
        leaf local-user-db-name {
          type string {
            length "1..32";
          }
        } //local-user-db-name

      } //container pppoe-user-db

      leaf process-cpm-traffic-on-sap-down {
        type boolean;
        description
            "Configure to process CPM traffic on SAP down event";
      }

      container restrict-protected-src {
        description
            "Enable/disable protected src MAC restriction";
        leaf alarm-only {
          type boolean;
          description
              "keyword - only trap on a protected MAC";
        } //alarm-only

        leaf discard-frame {
          type boolean;
          description
              "keyword - discard frame and trap on a protected MAC";
        } //discard-frame

      } //container restrict-protected-src

      leaf restrict-unprotected-dst {
        type boolean;
        description
            "Enable/disable unprotected dest MAC restriction";
      }

      container ring-node {
        description
            "Configure a multi-chassis ring-node for this SAP";
        leaf ring-node-name {
          type string {
            length "1..32";
          }
        } //ring-node-name

      } //container ring-node

      container rtr-solicit-user-db {
        description
            "Configure the local-user-database used for the router-solicit sessions 
             (capture SAP only)";
        leaf local-user-db-name {
          type string {
            length "1..32";
          }
        } //local-user-db-name

      } //container rtr-solicit-user-db

      container shcv-policy-ipv4 {
        description
            "Configure the Subscriber Host Connectivity Verification policy for IPv4";
        leaf policy-name {
          type string;
        } //policy-name

      } //container shcv-policy-ipv4

      leaf shutdown {
        type boolean;
        description
            "Administratively enable/disable the SAP";
      }

      list static-mac {
        key "ieee-address";
        description
            "Configure a static mac entry";
        leaf ieee-address {
          type string;
          description
              "xx:xx:xx:xx:xx:xx or xx-xx-xx-xx-xx-xx (cannot be all zeros)";
        } //ieee-address

      } //list static-mac

      container tod-suite {
        status "obsolete";
        description
            "Configure a time-of-day suite for this SAP";
        leaf tod-suite-name {
          type string {
            length "1..32";
          }
        } //tod-suite-name

      } //container tod-suite

      container track-srrp {
        description
            "Configure the SRRP instance this capture sap will track";
        leaf srrp-id {
          type uint32 {
            range "1..4294967295";
          }
        } //srrp-id

      } //container track-srrp

      container transit-policy {
        description
            "Configure transit policy id";
        leaf prefix {
          type uint32 {
            range "1..65535";
          }
        } //prefix

        leaf ip {
          type uint32 {
            range "1..65535";
          }
        } //ip

      } //container transit-policy

      container trigger-packet {
        description
            "Configure triggering packets for a capture SAP";
        leaf dhcp {
          type boolean;
        } //dhcp

        leaf pppoe {
          type boolean;
        } //pppoe

        leaf arp {
          type boolean;
        } //arp

        leaf dhcp6 {
          type boolean;
        } //dhcp6

        leaf ppp {
          type boolean;
        } //ppp

        leaf rtr-solicit {
          type boolean;
        } //rtr-solicit

        leaf data {
          type boolean;
        } //data

      } //container trigger-packet

      container arp-host {
        description
            "Configure ARP host parameters";
        container host-limit {
          description
              "Configure the maximum number of ARP hosts";
          leaf max-num-hosts {
            type int32 {
              range "1..131071";
            }
            description
                "Attribute max-num-hosts for host-limit";
          } //max-num-hosts

        } //container host-limit

        container min-auth-interval {
          description
              "Configure the minimum authentication interval";
          leaf min-auth-interval {
            type uint32 {
              range "1..6000";
            }
            description
                "[1..6000] minutes";
          } //min-auth-interval

        } //container min-auth-interval

        leaf shutdown {
          type boolean;
          description
              "Enable/disable ARP hosts";
        }

      } //container arp-host

      container atm {
        description
            "Configure ATM properties";
        container encapsulation {
          description
              "Configure the ATM encap-type";
          leaf atm-encap-type {
            type enumeration {
              enum aal5auto;
              enum aal5mux-bridged-eth-nofcs;
              enum aal5mux-ppp;
              enum aal5nlpid-ppp;
              enum aal5snap-bridged;
            }
          } //atm-encap-type

        } //container encapsulation

        list vc-range {
          key "vc-range-id";
          description
              "Configure ATM Virtual Circuit ranges";
          leaf vc-range-id {
            type uint16 {
              range "1..5";
            }
          } //vc-range-id

          leaf vpi-range {
            type string {
            }
            description
                "Attribute vpi-range for vc-range";
          } //vpi-range

          leaf vci-range {
            type string {
            }
            description
                "Attribute vci-range for vc-range";
          } //vci-range

        } //list vc-range

        container egress {
          description
              "Configure egress parameters";
          container traffic-desc {
            description
                "Assign ATM traffic descriptor profile";
            leaf traffic-desc-profile-id {
              type int32 {
                range "1..1000";
              }
            } //traffic-desc-profile-id

          } //container traffic-desc

        } //container egress

        container ingress {
          description
              "Configure ingress parameters";
          container traffic-desc {
            description
                "Assign ATM traffic descriptor profile";
            leaf traffic-desc-profile-id {
              type int32 {
                range "1..1000";
              }
            } //traffic-desc-profile-id

          } //container traffic-desc

        } //container ingress

        container oam {
          description
              "Configure OAM properties";
          leaf alarm-cells {
            type boolean;
            description
                "Disable/enable handling and generation of AIS/RDI";
          }

        } //container oam

      } //container atm

      container dhcp {
        description
            "configures DHCP parameters for this SAP";
        container description {
          description
              "Add/remove a text description for DHCP";
          leaf description-string {
            type string {
              length "1..80";
            }
          } //description-string

        } //container description

        container lease-populate {
          description
              "Configure the maximum number of DHCPv4 leases";
          leaf nbr-of-leases {
            type int32 {
              range "1..131071";
            }
            description
                "Attribute nbr-of-leases for lease-populate";
          } //nbr-of-leases

        } //container lease-populate

        leaf shutdown {
          type boolean;
          description
              "Administratively enable/disable DHCP on this SAP";
        }

        leaf snoop {
          type boolean;
          description
              "Enable/disable DHCP snooping on this SAP";
        }

        container option {
          presence
              "Configure the DHCP information options";
          container action {
            description
                "Configure the DHCP option action";
            leaf dhcp-action {
              type enumeration {
                enum replace;
                enum drop;
                enum keep;
              }
              description
                  "replace|drop|keep - keywords";
            } //dhcp-action

          } //container action

          container circuit-id {
            description
                "Configure the circuit-id suboption of the DHCP Relay packet";
            leaf circuit-id-id {
              type enumeration {
                enum ascii-tuple;
                enum vlan-ascii-tuple;
              }
            } //circuit-id-id

            leaf hex {
              type string {
                length "1..66";
              }
              description
                  "[0x0..0xFFFFFFFF...(64 hex nibbles)]";
            } //hex

          } //container circuit-id

          container remote-id {
            description
                "Configure the remote-id suboption of the DHCP Relay packet";
            leaf mac {
              type boolean;
            } //mac

            leaf string {
              type string {
                length "1..32";
              }
              description
                  "Max 32 chars";
            } //string

            leaf hex {
              type string {
                length "1..66";
              }
              description
                  "[0x0..0xFFFFFFFF...(64 hex nibbles)]";
            } //hex

          } //container remote-id

          container vendor-specific-option {
            presence
                "Configure the Nokia vendor specific suboption of the DHCP Relay packet";
            leaf client-mac-address {
              type boolean;
              description
                  "Enable/disable sending of the MAC address in the Nokia vendor specific 
                   suboption of the DHCP Relay packet";
            }

            leaf sap-id {
              type boolean;
              description
                  "Enable/disable sending of the SAP-id in the Nokia vendor specific suboption of 
                   the DHCP Relay packet";
            }

            leaf service-id {
              type boolean;
              description
                  "Enable/disable sending of the service-id in the Nokia vendor specific 
                   suboption of the DHCP Relay packet";
            }

            container string {
              description
                  "Specifies the string in the Nokia vendor specific suboption of the DHCP Relay 
                   packet";
              leaf text {
                type string {
                  length "1..32";
                }
              } //text

            } //container string

            leaf system-id {
              type boolean;
              description
                  "Enable/disable sending of the system-id in the Nokia vendor specific suboption 
                   of the DHCP Relay packet";
            }

          } //container vendor-specific-option

        } //container option

        container proxy-server {
          description
              "Configure the DHCP proxy server";
          container emulated-server {
            description
                "Specify the emulated server address";
            leaf ip-address {
              type inet:ip-address;
            } //ip-address

          } //container emulated-server

          container lease-time {
            description
                "Configure the DHCP lease time";
            leaf days {
              type int32 {
                range "0..3650";
              }
            } //days

            leaf hrs {
              type int32 {
                range "0..23";
              }
            } //hrs

            leaf min {
              type int32 {
                range "0..59";
              }
            } //min

            leaf sec {
              type int32 {
                range "0..59";
              }
            } //sec

            leaf radius-override {
              type boolean;
            } //radius-override

          } //container lease-time

          leaf shutdown {
            type boolean;
            description
                "Administratively enable/disable DHCP proxy on this SAP";
          }

        } //container proxy-server

      } //container dhcp

      container dhcp6 {
        description
            "configures DHCP6 parameters for this SAP";
        container description {
          description
              "Add/remove a text description for DHCP6";
          leaf description-string {
            type string {
              length "1..80";
            }
          } //description-string

        } //container description

        leaf shutdown {
          type boolean;
          description
              "Administratively enable/disable DHCP6 on this SAP";
        }

        leaf snoop {
          type boolean;
          description
              "Enable/disable DHCP6 snooping on this SAP";
        }

        container option {
          presence
              "Configure the DHCP6 information options";
          container interface-id {
            description
                "Configure the interface-id suboption of the DHCP6 Relay packet";
            leaf ascii-tuple {
              type boolean;
            } //ascii-tuple

            leaf vlan-ascii-tuple {
              type boolean;
            } //vlan-ascii-tuple

          } //container interface-id

          container remote-id {
            description
                "Configure the remote-id suboption of the DHCP6 Relay packet";
            leaf mac {
              type boolean;
            } //mac

            leaf string {
              type string {
                length "1..32";
              }
            } //string

          } //container remote-id

        } //container option

      } //container dhcp6

      container dynamic-services {
        description
            "Configure dynamic-services (capture SAP only)";
        container dynamic-services-policy {
          description
              "Configure the dynamic services policy associated with this capture SAP";
          leaf dynsvc-policy-name {
            type string;
          } //dynsvc-policy-name

        } //container dynamic-services-policy

        leaf shutdown {
          type boolean;
          description
              "Configure the dynamic services admin state of this capture SAP";
        }

      } //container dynamic-services

      container egress {
        description
            "Configure egress policies";
        container dest-mac-rewrite {
          description
              "Enables destination MAC overwrite for unicast";
          leaf ieee-address {
            type alu:ieee-address;
          } //ieee-address

        } //container dest-mac-rewrite

        container egress-remark-policy {
          description
              "Specify an egress-remark-policy";
          leaf egress-remark-policy-name {
            type string {
              length "1..64";
            }
          } //egress-remark-policy-name

        } //container egress-remark-policy

        container filter {
          description
              "Apply egress filter";
          leaf ip {
            type string;
            description
                "[1..65535]|<name:64 char max>";
          } //ip

          leaf mac {
            type string;
            description
                "[1..65535]|<name:64 char max>";
          } //mac

          leaf ipv6 {
            type string;
            description
                "[1..65535]|<name:64 char max>";
          } //ipv6

        } //container filter

        container multicast-group {
          status "obsolete";
          description
              "Apply egress multicast group";
          leaf group-name {
            type string {
              length "1..32";
            }
            description
                "32 chars max";
          } //group-name

        } //container multicast-group

        container policer-control-policy {
          description
              "Specify policer control policy";
          leaf policy-name {
            type string {
              length "1..32";
            }
          } //policy-name

        } //container policer-control-policy

        leaf qinq-mark-top-only {
          type boolean;
          description
              "Mark p-bits on top q-tag only";
        }

        list qos {
          key "policy-id";
          description
              "Apply egress qos policy";
          leaf policy-id {
            type string;
            description
                "[1..65535]|<name:64 char max>";
          } //policy-id

          leaf port-redirect-group {
            type string {
              length "1..32";
            }
          } //port-redirect-group

          leaf instance {
            type uint16 {
              range "1..65535";
            }
          } //instance

        } //list qos

        container scheduler-policy {
          description
              "Specify a scheduler-policy";
          leaf scheduler-policy-name {
            type string {
              length "1..32";
            }
          } //scheduler-policy-name

        } //container scheduler-policy

        container vlan-qos-policy {
          description
              "Specify a vlan-qos-policy";
          leaf vlan-qos-policy-name {
            type string;
          } //vlan-qos-policy-name

        } //container vlan-qos-policy

        container agg-rate {
          presence
              "Configure aggregate rate limit";
          leaf limit-unused-bandwidth {
            type boolean;
            description
                "Specify whether to enable limit unused bandwidth";
          }

          leaf queue-frame-based-accounting {
            type boolean;
            description
                "Specify whether to enable queue frame based accounting";
          }

          container rate {
            description
                "Specify rate limit for agg-rate";
            leaf kilobits-per-second {
              type string;
              description
                  "[1..6400000000|max] Kbps";
            } //kilobits-per-second

            leaf cir {
              type string;
              description
                  "[0..100000000|max] Kbps";
            } //cir

          } //container rate

        } //container agg-rate

        container encap-defined-qos {
          description
              "Configure egress encapsulation group";
          list encap-group {
            key "group-name";
            description
                "Configure the encapsulation group";
            leaf group-name {
              type string {
                length "1..32";
              }
            } //group-name

            leaf type {
              type enumeration {
                enum isid;
              }
            } //type

            leaf qos-per-member {
              type boolean;
            } //qos-per-member

            list member {
              key "member-id to";
              description
                  "Configure the ISID member";
              leaf member-id {
                type int32 {
                  range "0..16777215";
                }
                description
                    "encap-id";
              } //member-id

              leaf to {
                type int32 {
                  range "0..16777215";
                }
                description
                    "[0..16777215]";
              } //to

            } //list member

            container qos {
              description
                  "Configure the qos policy";
              leaf policy-id {
                type uint32 {
                  range "1..65535";
                }
              } //policy-id

            } //container qos

            container scheduler-policy {
              description
                  "Configure the scheduler-policy";
              leaf scheduler-policy-name {
                type string {
                  length "1..32";
                }
              } //scheduler-policy-name

            } //container scheduler-policy

            container agg-rate {
              presence
                  "Configure aggregate rate limit";
              leaf limit-unused-bandwidth {
                type boolean;
                description
                    "Specify whether to enable limit unused bandwidth";
              }

              leaf queue-frame-based-accounting {
                type boolean;
                description
                    "Specify whether to enable queue frame based accounting";
              }

              container rate {
                description
                    "Specify rate limit for agg-rate";
                leaf kilobits-per-second {
                  type string;
                  description
                      "[1..6400000000|max] Kbps";
                } //kilobits-per-second

              } //container rate

            } //container agg-rate

          } //list encap-group

        } //container encap-defined-qos

        container hsmda-queue-override {
          presence
              "Configure HSMDA egress queue overrides";
          container packet-byte-offset {
            description
                "Specify a packet offset for HSMDA queue accounting";
            leaf add {
              type uint32 {
                range "0..31";
              }
            } //add

            leaf subtract {
              type string;
              description
                  "Attribute sub-bytes for packet-byte-offset";
            } //subtract

          } //container packet-byte-offset

          container secondary-shaper {
            description
                "Configure a HSMDA egress secondary shaper";
            leaf secondary-shaper-name {
              type string {
                length "1..32";
              }
            } //secondary-shaper-name

          } //container secondary-shaper

          container wrr-policy {
            description
                "Configure a HSMDA egress wrr-policy";
            leaf policy-name {
              type string {
                length "1..32";
              }
            } //policy-name

          } //container wrr-policy

          list queue {
            key "queue-id";
            description
                "Configure overrides for a HSMDA egress queue";
            leaf queue-id {
              type int32 {
                range "1..8";
              }
            } //queue-id

            container mbs {
              description
                  "Specify MBS rate";
              leaf mbs-string {
                type string;
              } //mbs-string

              leaf mbs-id-2 {
                type enumeration {
                  enum bytes;
                  enum kilobytes;
                }
              } //mbs-id-2

            } //container mbs

            container rate {
              description
                  "Specify rate (PIR)";
              leaf pir-rate {
                type string;
                description
                    "[1..100000000|max] Kbps";
              } //pir-rate

            } //container rate

            container slope-policy {
              description
                  "Specify slope policy";
              leaf hsmda-slope-policy-name {
                type string {
                  length "1..32";
                }
              } //hsmda-slope-policy-name

            } //container slope-policy

            container wrr-weight {
              description
                  "Specify wrr-weight";
              leaf weight {
                type int32 {
                  range "1..32";
                }
                description
                    "Attribute weight for wrr-weight";
              } //weight

            } //container wrr-weight

          } //list queue

        } //container hsmda-queue-override

        container policer-control-override {
          description
              "Configure policer control overrides";
          container max-rate {
            description
                "Configure Max Rate override in kilobits-per-second";
            leaf rate {
              type string;
              description
                  "[1..6400000000|max] Kbps";
            } //rate

          } //container max-rate

          container priority-mbs-thresholds {
            description
                "Configure priority mbs thresholds overrides";
            container min-thresh-separation {
              description
                  "configure min threshold separation override";
              leaf size {
                type string;
                description
                    "[0..16777216 default]";
              } //size

              leaf min-thresh-separation-id {
                type enumeration {
                  enum bytes;
                  enum kilobytes;
                }
              } //min-thresh-separation-id

            } //container min-thresh-separation

            list priority {
              key "level";
              description
                  "Configure Priority Levels overrides";
              leaf level {
                type uint32 {
                  range "1..8";
                }
              } //level

              container mbs-contribution {
                description
                    "Configure mbs size override";
                leaf size {
                  type string;
                  description
                      "[0..16777216 default]";
                } //size

                leaf mbs-contribution-id {
                  type enumeration {
                    enum bytes;
                    enum kilobytes;
                  }
                } //mbs-contribution-id

              } //container mbs-contribution

            } //list priority

          } //container priority-mbs-thresholds

        } //container policer-control-override

        container policer-override {
          presence
              "Configure policer overrides";
          list policer {
            key "policer-id";
            description
                "Configure overrides for the policer";
            leaf policer-id {
              type uint32 {
                range "1..63";
              }
            } //policer-id

            container cbs {
              description
                  "Specify Cbs override";
              leaf size {
                type string;
                description
                    "[0..16777216 default]";
              } //size

              leaf cbs-id {
                type enumeration {
                  enum bytes;
                  enum kilobytes;
                }
              } //cbs-id

            } //container cbs

            container mbs {
              description
                  "Specify Mbs override";
              leaf size {
                type string;
                description
                    "[0..16777216 default]";
              } //size

              leaf mbs-id {
                type enumeration {
                  enum bytes;
                  enum kilobytes;
                }
              } //mbs-id

            } //container mbs

            container packet-byte-offset {
              description
                  "Specify packet byte offset";
              leaf add {
                type uint32 {
                  range "0..31";
                }
              } //add

              leaf subtract {
                type string;
                description
                    "Attribute sub-bytes for packet-byte-offset";
              } //subtract

            } //container packet-byte-offset

            container percent-rate {
              description
                  "Specify percent rates (CIR and PIR) override";
              leaf pir-percent {
                type string;
                description
                    "[0.01..100.00]";
              } //pir-percent

              leaf cir {
                type string;
                description
                    "[0.00..100.00]";
              } //cir

            } //container percent-rate

            container rate {
              description
                  "Specify rates (CIR and PIR) override";
              leaf pir-rate {
                type string;
                description
                    "[1..6400000000|max] Kbps";
              } //pir-rate

              leaf cir {
                type string;
                description
                    "[0..6400000000|max] Kbps";
              } //cir

            } //container rate

            container stat-mode {
              description
                  "Specify Stat Mode for the policer";
              leaf stat-mode {
                type enumeration {
                  enum no-stats;
                  enum minimal;
                  enum offered-profile-no-cir;
                  enum offered-profile-cir;
                  enum offered-total-cir;
                  enum offered-limited-capped-cir;
                  enum offered-profile-capped-cir;
                  enum offered-total-cir-exceed;
                  enum offered-four-profile-no-cir;
                  enum offered-total-cir-four-profile;
                }
              } //stat-mode

            } //container stat-mode

          } //list policer

        } //container policer-override

        container qtag-manipulation {
          status "obsolete";
          presence
              "Configure VLAN Tag Manipulation";
          leaf preserve {
            type boolean;
            status "obsolete";
            description
                "Preserve tags";
          }

          leaf push {
            type boolean;
            status "obsolete";
            description
                "Push tags";
          }

          container translate {
            status "obsolete";
            description
                "Replace or pop tags";
            leaf t1-to-1-1-to-2-2-to-2 {
              type enumeration {
                enum 1-to-1;
                enum 1-to-2;
                enum 2-to-2;
              }
              description
                  "keywords";
            } //t1-to-1-1-to-2-2-to-2

            leaf qtag1.qtag2 {
              type string;
              description
                  "null[.null]";
            } //qtag1.qtag2

          } //container translate

        } //container qtag-manipulation

        container queue-override {
          presence
              "Apply queue override";
          container hs-secondary-shaper {
            description
                "Specify HS Secondary Shaper";
            leaf policy-name {
              type string;
            } //policy-name

          } //container hs-secondary-shaper

          list hs-wrr-group {
            key "group-id";
            description
                "Configure HS WRR Group";
            leaf group-id {
              type uint16 {
                range "1..2";
              }
              description
                  "[1..2]";
            } //group-id

            container class-weight {
              description
                  "Specify class weight";
              leaf weight {
                type enumeration {
                  enum 1;
                  enum 2;
                  enum 4;
                  enum 8;
                }
              } //weight

            } //container class-weight

            container percent-rate {
              description
                  "Specify percent rate";
              leaf percent {
                type string;
                description
                    "[0.01..100.00]";
              } //percent

            } //container percent-rate

            container rate {
              description
                  "Specify rates (PIR)";
              leaf rate {
                type string;
                description
                    "Attribute rate for rate";
              } //rate

            } //container rate

          } //list hs-wrr-group

          list queue {
            key "queue-id";
            description
                "Configure a queue override";
            leaf queue-id {
              type int32 {
                range "1..8";
              }
            } //queue-id

            container adaptation-rule {
              description
                  "Specify the CIR and PIR adaptation rules";
              leaf pir {
                type enumeration {
                  enum max;
                  enum min;
                  enum closest;
                }
              } //pir

              leaf cir {
                type enumeration {
                  enum max;
                  enum min;
                  enum closest;
                }
              } //cir

            } //container adaptation-rule

            container avg-frame-overhead {
              description
                  "Specify the average frame overhead";
              leaf percentage {
                type string;
                description
                    "[0.00..100.00]";
              } //percentage

            } //container avg-frame-overhead

            container burst-limit {
              description
                  "Specify burst limit";
              leaf size {
                type string;
                description
                    "Attribute size for burst-limit";
              } //size

              leaf bytes-kilobytes {
                type enumeration {
                  enum bytes;
                  enum kilobytes;
                }
              } //bytes-kilobytes

            } //container burst-limit

            container cbs {
              description
                  "Specify CBS";
              leaf size-in-kbytes {
                type string;
                description
                    "Attribute size-in-kbytes for cbs";
              } //size-in-kbytes

            } //container cbs

            container high-prio-only {
              status "obsolete";
              description
                  "Specify high priority only burst size";
              leaf percent {
                type string;
                description
                    "[0..100 | default]";
              } //percent

            } //container high-prio-only

            container hs-class-weight {
              description
                  "Specify HS class weight";
              leaf weight {
                type enumeration {
                  enum 1;
                  enum 2;
                  enum 4;
                  enum 8;
                }
              } //weight

            } //container hs-class-weight

            container hs-wred-queue {
              description
                  "Configure HS WRED queue";
              leaf policy {
                type string {
                  length "1..32";
                }
              } //policy

            } //container hs-wred-queue

            container hs-wrr-weight {
              description
                  "Specify HS WRR weight";
              leaf weight {
                type uint16 {
                  range "1..127";
                }
                description
                    "[1..127]";
              } //weight

            } //container hs-wrr-weight

            container mbs {
              description
                  "Specify MBS";
              leaf size {
                type string;
                description
                    "Attribute size for mbs";
              } //size

              leaf bytes-kilobytes {
                type enumeration {
                  enum bytes;
                  enum kilobytes;
                }
              } //bytes-kilobytes

            } //container mbs

            leaf monitor-depth {
              type boolean;
              description
                  "Enable/Disable queue-depth monitoring";
            }

            container monitor-queue-depth {
              description
                  "Enable/Disable fast polling queue-depth monitoring";
              leaf fast-polling {
                type boolean;
              } //fast-polling

              leaf violation-threshold {
                type string;
                description
                    "[00.01..99.99]";
              } //violation-threshold

            } //container monitor-queue-depth

            container parent {
              description
                  "Specify the override weights for the queue within its parental scheduling 
                   context";
              leaf weight {
                type uint32 {
                  range "0..100";
                }
              } //weight

              leaf cir-weight {
                type uint32 {
                  range "0..100";
                }
              } //cir-weight

            } //container parent

            container percent-rate {
              description
                  "Specify percent rates (CIR and PIR)";
              leaf pir-percent {
                type string;
                description
                    "[0.01..100.00]";
              } //pir-percent

              leaf cir {
                type string;
                description
                    "[0.00..100.00]";
              } //cir

            } //container percent-rate

            container rate {
              description
                  "Specify rates (CIR and PIR)";
              leaf pir-rate {
                type string;
                description
                    "Attribute pir-rate for rate";
              } //pir-rate

              leaf cir {
                type string;
                description
                    "Attribute cir-rate for rate";
              } //cir

            } //container rate

            container drop-tail {
              description
                  "Specify drop tail";
              container low {
                description
                    "Specify low drop-tail";
                container percent-reduction-from-mbs {
                  description
                      "Specify low drop tail percent reduction from MBS";
                  leaf percent {
                    type string;
                    description
                        "[0..100|default]";
                  } //percent

                } //container percent-reduction-from-mbs

              } //container low

            } //container drop-tail

          } //list queue

        } //container queue-override

        container scheduler-override {
          presence
              "Apply a scheduler override";
          list scheduler {
            key "scheduler-name";
            description
                "Configure a scheduler override";
            leaf scheduler-name {
              type string {
                length "1..32";
              }
            } //scheduler-name

            container parent {
              description
                  "Specify the override weights for the scheduler";
              leaf weight {
                type uint32 {
                  range "0..100";
                }
              } //weight

              leaf cir-weight {
                type uint32 {
                  range "0..100";
                }
              } //cir-weight

            } //container parent

            container rate {
              description
                  "Specify rates (CIR and PIR)";
              leaf pir-rate {
                type string;
                description
                    "[1..6400000000|max] Kbps";
              } //pir-rate

              leaf cir {
                type string;
                description
                    "[0..6400000000|sum|max] Kbps";
              } //cir

            } //container rate

          } //list scheduler

        } //container scheduler-override

        container vlan-manipulation {
          presence
              "Configure VLAN Tag Manipulation";
          leaf preserve {
            type boolean;
            description
                "Preserve tags";
          }

          leaf push {
            type boolean;
            description
                "Push tags";
          }

          container translate {
            description
                "Replace or pop tags";
            leaf t1-to-1-1-to-2-2-to-2 {
              type enumeration {
                enum 1-to-1;
                enum 1-to-2;
                enum 2-to-2;
              }
              description
                  "keywords";
            } //t1-to-1-1-to-2-2-to-2

            leaf qtag1.qtag2 {
              type string;
              description
                  "null[.null]";
            } //qtag1.qtag2

          } //container translate

        } //container vlan-manipulation

      } //container egress

      container eth-cfm {
        description
            "Configure CFM parameters";
        leaf collect-lmm-stats {
          type boolean;
          description
              "Enable/Disable the collection of statistics for OAM-PM Loss Measurement 
               Message (LMM) tests";
        }

        list mip {
          key "primary-vlan-enable";
          description
              "Enable/Disable Maintenance Intermediate Points";
          leaf mac {
            type yang:mac-address;
          } //mac

          leaf default-mac {
            type boolean;
            description
                "keyword - Use the default MAC address for the MIP";
          } //default-mac

          leaf primary-vlan-enable {
            type uint32 {
              range "1..4094";
            }
          } //primary-vlan-enable

        } //list mip

        container squelch-ingress-levels {
          description
              "Configure the level(s) of the ETH-CFM PDUs that will be silently discarded";
          leaf t0 {
            type boolean;
            description
                "[0..7]";
          } //t0

          leaf t1 {
            type boolean;
          } //t1

          leaf t2 {
            type boolean;
          } //t2

          leaf t3 {
            type boolean;
          } //t3

          leaf t4 {
            type boolean;
          } //t4

          leaf t5 {
            type boolean;
          } //t5

          leaf t6 {
            type boolean;
          } //t6

          leaf t7 {
            type boolean;
          } //t7

        } //container squelch-ingress-levels

        container tunnel-fault {
          description
              "Accept/Ignore tunnel fault notification";
          leaf tunnel-fault-id {
            type enumeration {
              enum accept;
              enum ignore;
            }
          } //tunnel-fault-id

        } //container tunnel-fault

        leaf vmep-filter {
          type boolean;
          description
              "Suppress eth-cfm PDUs based on level lower than or equal to configured Virtual 
               MEP";
        }

        container collect-lmm-fc-stats {
          description
              "Configure the collection of Forwarding Class (FC) aware statistics for OAM-PM 
               Loss Measurement Message (LMM) tests";
          container fc {
            description
                "Configure Forwarding Class (FC) counters without regard for profile";
            leaf-list fc-name {
              type enumeration {
                enum be;
                enum l2;
                enum af;
                enum l1;
                enum h2;
                enum ef;
                enum h1;
                enum nc;
              }
              max-elements 8;
            } //fc-name

          } //container fc

          container fc-in-profile {
            description
                "Configure only in profile Forwarding Class (FC) counters";
            leaf-list fc-name {
              type enumeration {
                enum be;
                enum l2;
                enum af;
                enum l1;
                enum h2;
                enum ef;
                enum h1;
                enum nc;
              }
              max-elements 8;
            } //fc-name

          } //container fc-in-profile

        } //container collect-lmm-fc-stats

        list mep {
          key "mep-id domain association";
          description
              "Configure a CFM Maintenance Endpoint";
          leaf mep-id {
            type int16 {
              range "1..8191";
            }
            description
                "Attribute mep-id for mep";
          } //mep-id

          leaf domain {
            type uint32 {
              range "1..4294967295";
            }
          } //domain

          leaf association {
            type uint32 {
              range "1..4294967295";
            }
          } //association

          leaf direction {
            type enumeration {
              enum up;
              enum down;
            }
            description
                "keywords";
          } //direction

          leaf primary-vlan-enable {
            type boolean;
            description
                "keyword - Provision MEP using MA primary vlan-id";
          } //primary-vlan-enable

          leaf ccm-enable {
            type boolean;
            description
                "Enable/Disable Generation of CCM messages";
          }

          container ccm-ltm-priority {
            description
                "Configure the priority of CCM and LTM messages";
            leaf priority {
              type uint16 {
                range "0..7";
              }
              description
                  "[0..7] - Default highest priority on bridge-port";
            } //priority

          } //container ccm-ltm-priority

          container ccm-padding-size {
            description
                "Insert additional padding in the CCM packets";
            leaf ccm-padding {
              type uint32 {
                range "3..1500";
              }
              description
                  "3..1500 octets";
            } //ccm-padding

          } //container ccm-padding-size

          container description {
            description
                "Add/remove a text description for the MEP";
            leaf description-string {
              type string {
              }
              description
                  "[80 chars max]";
            } //description-string

          } //container description

          container fault-propagation-enable {
            description
                "Configure the Fault Propagation for the MEP";
            leaf use-if-tlv-suspend-ccm {
              type enumeration {
                enum use-if-tlv;
                enum suspend-ccm;
              }
              description
                  "keywords - use interface TLV, or suspend Continuity Check Messages";
            } //use-if-tlv-suspend-ccm

          } //container fault-propagation-enable

          leaf install-mep {
            type boolean;
            description
                "Enable/Disable Installation of the MEP in the forwarding plane";
          }

          leaf lbm-svc-act-responder {
            type boolean;
            description
                "Enable/Disable processing of service activation streams that may be 
                 encapsulated in the ETH-CFM request Loopback Message (LBM) on the MEP";
          }

          container low-priority-defect {
            description
                "Configure the Lowest Priority Defect for the MEP";
            leaf allDef-macRemErrXcon-remErrXcon-errXcon-xcon-noXcon {
              type enumeration {
                enum allDef;
                enum macRemErrXcon;
                enum remErrXcon;
                enum errXcon;
                enum xcon;
                enum noXcon;
              }
              description
                  "keywords";
            } //allDef-macRemErrXcon-remErrXcon-errXcon-xcon-noXcon

          } //container low-priority-defect

          container mac-address {
            description
                "Configure the MAC Address for the MEP";
            leaf mac-address {
              type yang:mac-address;
            } //mac-address

          } //container mac-address

          container one-way-delay-threshold {
            description
                "Configure the one-way-delay test threshold";
            leaf seconds {
              type uint32 {
                range "0..600";
              }
              default 3;
              description
                  "[0..600] Default: 3";
            } //seconds

          } //container one-way-delay-threshold

          leaf shutdown {
            type boolean;
            description
                "Administratively enable/disable the MEP";
          }

          container ais-enable {
            presence
                "Configure the generation and reception of Alarm Indication Signal (AIS) 
                 message parameters";
            container client-meg-level {
              description
                  "Configure the client meg level";
              leaf t1 {
                type boolean;
                description
                    "[1..7]";
              } //t1

              leaf t2 {
                type boolean;
              } //t2

              leaf t3 {
                type boolean;
              } //t3

              leaf t4 {
                type boolean;
              } //t4

              leaf t5 {
                type boolean;
              } //t5

              leaf t6 {
                type boolean;
              } //t6

              leaf t7 {
                type boolean;
              } //t7

            } //container client-meg-level

            leaf interface-support-enable {
              type boolean;
              description
                  "Enable/disable the generation of AIS PDUs based on the associated endpoint 
                   state";
            }

            container interval {
              description
                  "Configure the transmission interval of AIS messages";
              leaf t1-60 {
                type enumeration {
                  enum 1;
                  enum 60;
                }
                default 1;
                description
                    "seconds - Default: 1";
              } //t1-60

            } //container interval

            container low-priority-defect {
              description
                  "Configure the Lowest Priority Defect for the MEP AIS generation";
              leaf allDef---macRemErrXcon {
                type enumeration {
                  enum allDef;
                  enum macRemErrXcon;
                }
                description
                    "keywords";
              } //allDef---macRemErrXcon

            } //container low-priority-defect

            container priority {
              description
                  "Configure the priority of AIS messages originated by the node";
              leaf priority-value {
                type uint32 {
                  range "0..7";
                }
                default 7;
                description
                    "[0..7] - Default: 7";
              } //priority-value

            } //container priority

          } //container ais-enable

          container alarm-notification {
            description
                "Configure the MEP alarm notification parameters";
            container fng-alarm-time {
              description
                  "Configure the Fault Notification Generation (FNG) alarm time";
              leaf time {
                type enumeration {
                  enum 0;
                  enum 250;
                  enum 500;
                  enum 1000;
                }
                default 0;
                description
                    "[0,250,500,1000] centi-seconds - Default: 0";
              } //time

            } //container fng-alarm-time

            container fng-reset-time {
              description
                  "Configure the Fault Notification Generation (FNG) reset time";
              leaf time {
                type enumeration {
                  enum 0;
                  enum 250;
                  enum 500;
                  enum 1000;
                }
                default 0;
                description
                    "[0,250,500,1000] centi-seconds - Default: 0";
              } //time

            } //container fng-reset-time

          } //container alarm-notification

          container csf-enable {
            presence
                "Configure the reception of Client Signal Fail (CSF) message parameters";
            container multiplier {
              description
                  "Configure the multiplier used for timing out CSF";
              leaf multiplier-value {
                type string;
                description
                    "[0.0|2.0 .. 30.0] - Default: 3.5";
              } //multiplier-value

            } //container multiplier

          } //container csf-enable

          container eth-test-enable {
            presence
                "Enable/Disable eth-test functionality on MEP";
            container bit-error-threshold {
              description
                  "Configure the bit error trap threshold";
              leaf bit-errors {
                type uint32 {
                  range "0..11840";
                }
                default 1;
                description
                    "[0..11840] Default: 1";
              } //bit-errors

            } //container bit-error-threshold

            container test-pattern {
              description
                  "Configure the test pattern for eth-test frames";
              leaf all-zeros-all-ones {
                type enumeration {
                  enum all-zeros;
                  enum all-ones;
                }
                default "all-zeros";
                description
                    "keywords - Test pattern - default: all-zeros";
              } //all-zeros-all-ones

              leaf crc-enable {
                type boolean;
                description
                    "keyword - Generate CRC checksum";
              } //crc-enable

            } //container test-pattern

          } //container eth-test-enable

          container grace {
            description
                "Configure the generation and reception of grace period parameters";
            container eth-ed {
              description
                  "Configure the generation and reception of eth-ed grace period parameters";
              container max-rx-defect-window {
                description
                    "Configure/Disable an upper maximum defect window length; when disabled the 
                     advertised value from the peer will be used; when enabled the lower of the 
                     configured value or the advertised value from the peer will be used";
                leaf seconds {
                  type uint32 {
                    range "1..86400";
                  }
                  description
                      "[1..86400] - Default: no max-rx-defect-window";
                } //seconds

              } //container max-rx-defect-window

              container priority {
                description
                    "Configure/Disable the transmission priority value for ETH-ED PDUs; when 
                     disabled the priority value of ccm-ltm-priority associated with this MEP will 
                     be used";
                leaf priority {
                  type int32 {
                    range "0..7";
                  }
                  default 0;
                  description
                      "[0..7] - Default: no priority";
                } //priority

              } //container priority

              leaf rx-eth-ed {
                type boolean;
                description
                    "Enable/Disable the receiving and processing of ETH-ED PDUs";
              }

              leaf tx-eth-ed {
                type boolean;
                description
                    "Enable/Disable the transmission of ETH-ED PDUs";
              }

            } //container eth-ed

            container eth-vsm-grace {
              description
                  "Configure the generation and reception of sros vendor specific message (vsm) 
                   grace period parameters";
              leaf rx-eth-vsm-grace {
                type boolean;
                description
                    "Enable/Disable the receiving and processing of vendor specific message (vsm) 
                     grace period notifications";
              }

              leaf tx-eth-vsm-grace {
                type boolean;
                description
                    "Enable/Disable the transmission of vsm grace period notifications";
              }

            } //container eth-vsm-grace

          } //container grace

        } //list mep

      } //container eth-cfm

      container eth-tunnel {
        description
            "Configure Ethernet Tunnel SAP parameters";
        list path {
          key "path-index";
          description
              "Configure Ethernet Tunnel SAP Path parameters";
          leaf path-index {
            type string;
            description
                "Attribute path-index for path";
          } //path-index

          leaf tag {
            type string;
            description
                "[0..4094|*]";
          } //tag

        } //list path

      } //container eth-tunnel

      container frame-relay {
        description
            "Configure frame-relay parameters";
        container scheduling-class {
          description
              "Configure frf.12 scheduling class";
          leaf class-id {
            type uint32 {
              range "0..3";
            }
          } //class-id

        } //container scheduling-class

        container frf-12 {
          presence
              "Enable/Disable FRF12 Headers";
          container ete-fragment-threshold {
            description
                "Configure frf.12 fragmentation threshold";
            leaf threshold {
              type uint32 {
                range "128..512";
              }
            } //threshold

          } //container ete-fragment-threshold

          leaf interleave {
            type boolean;
            description
                "Enable/Disable frf-12 interleave";
          }

        } //container frf-12

      } //container frame-relay

      container igmp-host-tracking {
        description
            "Configure IGMP host tracking parameters";
        leaf disable-router-alert-check {
          type boolean;
          description
              "Enable/disable the IGMP router alert check option";
        }

        container expiry-time {
          description
              "Configure the time that the system continues to track inactive hosts";
          leaf expiry-time {
            type uint32 {
              range "1..65535";
            }
            description
                "[1..65535] seconds";
          } //expiry-time

        } //container expiry-time

        container import {
          description
              "Specify the import policy to filter IGMP packets";
          leaf policy-name {
            type string {
              length "1..32";
            }
          } //policy-name

        } //container import

        container max-num-groups {
          description
              "Configure the max number of multicast groups allowed to be tracked";
          leaf max-num-groups-id {
            type uint32 {
              range "1..16000";
            }
          } //max-num-groups-id

        } //container max-num-groups

        container max-num-grp-sources {
          description
              "Configure the max number of multicast group sources allowed to be tracked per 
               group";
          leaf max-num-grp-sources-id {
            type uint16 {
              range "1..32000";
            }
          } //max-num-grp-sources-id

        } //container max-num-grp-sources

        container max-num-sources {
          description
              "Configure the max number of multicast sources allowed to be tracked per group";
          leaf max-num-sources-id {
            type uint32 {
              range "1..1000";
            }
          } //max-num-sources-id

        } //container max-num-sources

      } //container igmp-host-tracking

      container igmp-snooping {
        description
            "Configure IGMP snooping parameters";
        leaf disable-router-alert-check {
          type boolean;
          description
              "Enable/disable the IGMP router alert check option";
        }

        leaf fast-leave {
          type boolean;
          description
              "Enable/disable IGMP fast-leave processing";
        }

        list import {
          key "policy-name";
          description
              "Import a policy to filter IGMP packets";
          leaf policy-name {
            type string {
              length "1..32";
            }
          } //policy-name

        } //list import

        container last-member-query-interval {
          description
              "Configure the IGMP Last Member Query Interval";
          leaf t1-10-seconds {
            type uint32 {
              range "1..50";
            }
          } //t1-10-seconds

        } //container last-member-query-interval

        container max-num-groups {
          description
              "Configure the max number of multicast groups allowed";
          leaf max-num-groups-id {
            type uint32 {
              range "1..16000";
            }
          } //max-num-groups-id

        } //container max-num-groups

        container max-num-grp-sources {
          description
              "Configure the max number of multicast group sources allowed per group";
          leaf max-num-grp-sources-id {
            type uint16 {
              range "1..32000";
            }
          } //max-num-grp-sources-id

        } //container max-num-grp-sources

        container max-num-sources {
          description
              "Configure the max number of multicast sources allowed per group";
          leaf max-num-sources-id {
            type uint32 {
              range "1..1000";
            }
          } //max-num-sources-id

        } //container max-num-sources

        leaf mrouter-port {
          type boolean;
          description
              "Configure the SAP as a multicast router port";
        }

        container query-interval {
          description
              "Configure the IGMP Query Interval";
          leaf seconds {
            type uint32 {
              range "2..1024";
            }
          } //seconds

        } //container query-interval

        container query-response-interval {
          description
              "Configure the IGMP Query Response Interval";
          leaf seconds {
            type uint32 {
              range "1..1023";
            }
          } //seconds

        } //container query-response-interval

        container robust-count {
          description
              "Configure the IGMP Robustness Variable";
          leaf robust-count {
            type uint32 {
              range "2..7";
            }
          } //robust-count

        } //container robust-count

        leaf send-queries {
          type boolean;
          description
              "Enable/disable generation of IGMP General Queries";
        }

        container version {
          description
              "Configure the version of IGMP";
          leaf version {
            type uint32 {
              range "1..3";
            }
            description
                "[1, 2 or 3]";
          } //version

        } //container version

        container mcac {
          description
              "Configure multicast CAC policy and constraints for this SAP";
          container if-policy {
            description
                "Configure multicast CAC if-policy";
            leaf if-policy-name {
              type string {
                length "1..32";
              }
            } //if-policy-name

          } //container if-policy

          container policy {
            description
                "Enable/disable multicast CAC policy";
            leaf policy-name {
              type string {
                length "1..32";
              }
              description
                  "max 32 chars";
            } //policy-name

          } //container policy

          container unconstrained-bw {
            description
                "Set/reset unconstrained-bw for multicast CAC policy on this SAP";
            leaf bandwidth {
              type int32 {
                range "0..2147483647";
              }
              description
                  "[0..2147483647] kbps";
            } //bandwidth

            leaf mandatory-bw {
              type int32 {
                range "0..2147483647";
              }
              description
                  "[0..2147483647] kbps";
            } //mandatory-bw

          } //container unconstrained-bw

          container mc-constraints {
            description
                "create context that allows for the configuration of the different levels and 
                 their associated bandwidth for multicast CAC policy on this SAP";
            list level {
              key "level-id";
              description
                  "Configure levels and their associated bandwidth for multicast CAC policy on 
                   this SAP";
              leaf level-id {
                type uint32 {
                  range "1..8";
                }
              } //level-id

              leaf bw {
                type uint32;
                description
                    "[0..2147483647] kbps";
              } //bw

            } //list level

            list number-down {
              key "number-lag-port-down";
              description
                  "Configure number of ports down along with level for multicast CAC policy on 
                   this SAP";
              leaf number-lag-port-down {
                type string;
                description
                    "Attribute number-lag-port-down for number-down";
              } //number-lag-port-down

              leaf level {
                type uint32 {
                  range "1..8";
                }
              } //level

            } //list number-down

            leaf shutdown {
              type boolean;
              description
                  "Administratively enable/disable constraint for multicast CAC policy";
            }

            leaf use-lag-port-weight {
              type boolean;
              description
                  "Enable/disable using the LAG port weight while calculating Multicast CAC 
                   constraints";
            }

          } //container mc-constraints

        } //container mcac

        container mvr {
          description
              "Configure Multicast VPLS Registration parameters";
          container from-vpls {
            description
                "The MVR VPLS from which the multicast channels are taken";
            leaf service-id {
              type string;
              description
                  "Attribute service-id for from-vpls";
            } //service-id

          } //container from-vpls

          container to-sap {
            description
                "The SAP to which the multicast channels are copied";
            leaf sap-id {
              type string;
              description
                  "Attribute sap-id for to-sap";
            } //sap-id

          } //container to-sap

        } //container mvr

        container static {
          description
              "Add/remove IGMP static group membership";
          list group {
            key "grp-ip-address";
            description
                "Add/remove a static multicast group";
            leaf grp-ip-address {
              type inet:ip-address;
              description
                  "a.b.c.d - multicast group address";
            } //grp-ip-address

            list source {
              key "ip-address";
              description
                  "Add/remove a static multicast source";
              leaf ip-address {
                type inet:ip-address;
              } //ip-address

            } //list source

            leaf starg {
              type boolean;
              description
                  "Add/remove a static starg entry";
            }

          } //list group

        } //container static

      } //container igmp-snooping

      container ingress {
        description
            "Configure ingress policies";
        container aggregate-policer-rate {
          description
              "Specify aggregate policer rate and burst";
          leaf rate-in-kbps {
            type string;
            description
                "Attribute rate-in-kbps for aggregate-policer-rate";
          } //rate-in-kbps

          leaf burst {
            type string;
            description
                "[1..33292 | default]";
          } //burst

          leaf cir {
            type string;
            description
                "Attribute cir-in-kbps for aggregate-policer-rate";
          } //cir

          leaf cbs {
            type string;
            description
                "[1..33292 | default]";
          } //cbs

        } //container aggregate-policer-rate

        container filter {
          description
              "Apply ingress filter";
          leaf ip {
            type string;
            description
                "[1..65535]|<name:64 char max>";
          } //ip

          leaf mac {
            type string;
            description
                "[1..65535]|<name:64 char max>";
          } //mac

          leaf ipv6 {
            type string;
            description
                "[1..65535]|<name:64 char max>";
          } //ipv6

        } //container filter

        container match-qinq-dot1p {
          description
              "Define 802.1P bits to match in QinQ SAP's";
          leaf top-bottom {
            type enumeration {
              enum top;
              enum bottom;
            }
          } //top-bottom

        } //container match-qinq-dot1p

        container policer-control-policy {
          description
              "Specify policer control policy";
          leaf policy-name {
            type string {
              length "1..32";
            }
          } //policy-name

        } //container policer-control-policy

        list qos {
          key "policy-id";
          description
              "Apply ingress qos policy";
          leaf policy-id {
            type string;
            description
                "[1..65535]|<name:64 char max>";
          } //policy-id

          leaf shared-queuing-multipoint-shared {
            type enumeration {
              enum shared-queuing;
              enum multipoint-shared;
            }
            description
                "keywords";
          } //shared-queuing-multipoint-shared

          leaf fp-redirect-group {
            type string {
              length "1..32";
            }
          } //fp-redirect-group

          leaf instance {
            type uint16 {
              range "1..65535";
            }
          } //instance

        } //list qos

        container scheduler-policy {
          description
              "Specify a scheduler-policy";
          leaf scheduler-policy-name {
            type string {
              length "1..32";
            }
          } //scheduler-policy-name

        } //container scheduler-policy

        container vlan-translation {
          description
              "Apply Ingress Vlan Translation";
          leaf t0..4094 {
            type uint32 {
              range "0..4094";
            }
          } //t0..4094

          leaf copy-outer {
            type boolean;
            description
                "Keyword - Use outer vlan-id";
          } //copy-outer

        } //container vlan-translation

        container criteria-overrides {
          description
              "Configure sap ingress criteria overrides";
          container ip-criteria {
            presence
                "Configure sap ingress ip criteria override";
            container activate-entry-tag {
              description
                  "Configure activate entry-tag id";
              leaf activate-entry-tag {
                type uint32 {
                  range "1..255";
                }
              } //activate-entry-tag

            } //container activate-entry-tag

          } //container ip-criteria

          container ipv6-criteria {
            presence
                "Configure sap ingress ipv6 criteria override";
            container activate-entry-tag {
              description
                  "Configure activate entry-tag-id";
              leaf activate-entry-tag {
                type uint32 {
                  range "1..255";
                }
              } //activate-entry-tag

            } //container activate-entry-tag

          } //container ipv6-criteria

        } //container criteria-overrides

        container policer-control-override {
          description
              "Configure policer control overrides";
          container max-rate {
            description
                "Configure Max Rate override in kilobits-per-second";
            leaf rate {
              type string;
              description
                  "[1..6400000000|max] Kbps";
            } //rate

          } //container max-rate

          container priority-mbs-thresholds {
            description
                "Configure priority mbs thresholds overrides";
            container min-thresh-separation {
              description
                  "configure min threshold separation override";
              leaf size {
                type string;
                description
                    "[0..16777216 default]";
              } //size

              leaf min-thresh-separation-id {
                type enumeration {
                  enum bytes;
                  enum kilobytes;
                }
              } //min-thresh-separation-id

            } //container min-thresh-separation

            list priority {
              key "level";
              description
                  "Configure Priority Levels overrides";
              leaf level {
                type uint32 {
                  range "1..8";
                }
              } //level

              container mbs-contribution {
                description
                    "Configure mbs size override";
                leaf size {
                  type string;
                  description
                      "[0..16777216 default]";
                } //size

                leaf mbs-contribution-id {
                  type enumeration {
                    enum bytes;
                    enum kilobytes;
                  }
                } //mbs-contribution-id

              } //container mbs-contribution

            } //list priority

          } //container priority-mbs-thresholds

        } //container policer-control-override

        container policer-override {
          presence
              "Configure policer overrides";
          list policer {
            key "policer-id";
            description
                "Configure overrides for the policer";
            leaf policer-id {
              type uint32 {
                range "1..63";
              }
            } //policer-id

            container cbs {
              description
                  "Specify Cbs override";
              leaf size {
                type string;
                description
                    "[0..16777216 default]";
              } //size

              leaf cbs-id {
                type enumeration {
                  enum bytes;
                  enum kilobytes;
                }
              } //cbs-id

            } //container cbs

            container mbs {
              description
                  "Specify Mbs override";
              leaf size {
                type string;
                description
                    "[0..16777216 default]";
              } //size

              leaf mbs-id {
                type enumeration {
                  enum bytes;
                  enum kilobytes;
                }
              } //mbs-id

            } //container mbs

            container packet-byte-offset {
              description
                  "specify packet byte offset";
              leaf add {
                type uint32 {
                  range "0..31";
                }
              } //add

              leaf subtract {
                type uint32 {
                  range "1..32";
                }
              } //subtract

            } //container packet-byte-offset

            container percent-rate {
              description
                  "Specify percent rates (CIR and PIR) override";
              leaf pir-percent {
                type string;
                description
                    "[0.01..100.00]";
              } //pir-percent

              leaf cir {
                type string;
                description
                    "[0.00..100.00]";
              } //cir

            } //container percent-rate

            container rate {
              description
                  "Specify rates (CIR and PIR) override";
              leaf pir-rate {
                type string;
                description
                    "[1..6400000000|max] Kbps";
              } //pir-rate

              leaf cir {
                type string;
                description
                    "[0..6400000000|max] Kbps";
              } //cir

            } //container rate

            container stat-mode {
              description
                  "Specify Stat Mode for the policer";
              leaf stat-mode {
                type enumeration {
                  enum no-stats;
                  enum minimal;
                  enum offered-profile-no-cir;
                  enum offered-priority-no-cir;
                  enum offered-profile-cir;
                  enum offered-priority-cir;
                  enum offered-total-cir;
                  enum offered-limited-profile-cir;
                  enum offered-profile-capped-cir;
                  enum offered-limited-capped-cir;
                }
              } //stat-mode

            } //container stat-mode

          } //list policer

        } //container policer-override

        container qtag-manipulation {
          status "obsolete";
          presence
              "Configure VLAN Tag Manipulation";
          leaf preserve {
            type boolean;
            status "obsolete";
            description
                "Preserve tags";
          }

          container push {
            status "obsolete";
            description
                "Push tags";
            leaf qtag1.qtag2 {
              type string;
              description
                  "Attribute qtag1[.qtag2] for push";
            } //qtag1.qtag2

          } //container push

          container translate {
            status "obsolete";
            description
                "Replace or pop tags";
            leaf t1-to-1-2-to-1-2-to-2 {
              type enumeration {
                enum 1-to-1;
                enum 2-to-1;
                enum 2-to-2;
              }
              description
                  "keywords";
            } //t1-to-1-2-to-1-2-to-2

            leaf qtag1.qtag2 {
              type string;
              description
                  "Attribute qtag1[.qtag2] for translate";
            } //qtag1.qtag2

          } //container translate

        } //container qtag-manipulation

        container queue-override {
          presence
              "Apply queue override";
          list queue {
            key "queue-id";
            description
                "Configure a queue override";
            leaf queue-id {
              type int32 {
                range "1..32";
              }
            } //queue-id

            container adaptation-rule {
              description
                  "Specify the CIR and PIR adaptation rules";
              leaf pir {
                type enumeration {
                  enum max;
                  enum min;
                  enum closest;
                }
              } //pir

              leaf cir {
                type enumeration {
                  enum max;
                  enum min;
                  enum closest;
                }
              } //cir

            } //container adaptation-rule

            container cbs {
              description
                  "Specify CBS";
              leaf size-in-kbytes {
                type string;
                description
                    "Attribute size-in-kbytes for cbs";
              } //size-in-kbytes

            } //container cbs

            container high-prio-only {
              status "obsolete";
              description
                  "Specify high priority only burst size";
              leaf percent {
                type string;
                description
                    "[0..100 | default]";
              } //percent

            } //container high-prio-only

            container mbs {
              description
                  "Specify MBS";
              leaf size {
                type string;
                description
                    "Attribute size for mbs";
              } //size

              leaf bytes-kilobytes {
                type enumeration {
                  enum bytes;
                  enum kilobytes;
                }
              } //bytes-kilobytes

            } //container mbs

            leaf monitor-depth {
              type boolean;
              description
                  "Enable/Disable queue-depth monitoring";
            }

            container parent {
              description
                  "Specify the override weights for the queue within its parental scheduling 
                   context";
              leaf weight {
                type uint32 {
                  range "0..100";
                }
              } //weight

              leaf cir-weight {
                type uint32 {
                  range "0..100";
                }
              } //cir-weight

            } //container parent

            container percent-rate {
              description
                  "Specify percent rates (CIR and PIR)";
              leaf pir-percent {
                type string;
                description
                    "[0.01..100.00]";
              } //pir-percent

              leaf cir {
                type string;
                description
                    "[0.00..100.00]";
              } //cir

            } //container percent-rate

            container rate {
              description
                  "Specify rates (CIR and PIR)";
              leaf pir-rate {
                type string;
                description
                    "Attribute pir-rate for rate";
              } //pir-rate

              leaf cir {
                type string;
                description
                    "Attribute cir-rate for rate";
              } //cir

            } //container rate

            container drop-tail {
              description
                  "Specify drop tail";
              container low {
                description
                    "Specify low drop-tail";
                container percent-reduction-from-mbs {
                  description
                      "Specify low drop tail percent reduction from MBS";
                  leaf percent {
                    type string;
                    description
                        "[0..100|default]";
                  } //percent

                } //container percent-reduction-from-mbs

              } //container low

            } //container drop-tail

          } //list queue

        } //container queue-override

        container scheduler-override {
          presence
              "Apply a scheduler override";
          list scheduler {
            key "scheduler-name";
            description
                "Configure a scheduler override";
            leaf scheduler-name {
              type string {
                length "1..32";
              }
            } //scheduler-name

            container parent {
              description
                  "Specify the override weights for the scheduler";
              leaf weight {
                type uint32 {
                  range "0..100";
                }
              } //weight

              leaf cir-weight {
                type uint32 {
                  range "0..100";
                }
              } //cir-weight

            } //container parent

            container rate {
              description
                  "Specify rates (CIR and PIR)";
              leaf pir-rate {
                type string;
                description
                    "[1..6400000000|max] Kbps";
              } //pir-rate

              leaf cir {
                type string;
                description
                    "[0..6400000000|sum|max] Kbps";
              } //cir

            } //container rate

          } //list scheduler

        } //container scheduler-override

        container vlan-manipulation {
          presence
              "Configure VLAN Tag Manipulation";
          leaf preserve {
            type boolean;
            description
                "Preserve tags";
          }

          container push {
            description
                "Push tags";
            leaf qtag1.qtag2 {
              type string;
              description
                  "Attribute qtag1[.qtag2] for push";
            } //qtag1.qtag2

          } //container push

          container translate {
            description
                "Replace or pop tags";
            leaf t1-to-1-2-to-1-2-to-2 {
              type enumeration {
                enum 1-to-1;
                enum 2-to-1;
                enum 2-to-2;
              }
              description
                  "keywords";
            } //t1-to-1-2-to-1-2-to-2

            leaf qtag1.qtag2 {
              type string;
              description
                  "Attribute qtag1[.qtag2] for translate";
            } //qtag1.qtag2

          } //container translate

        } //container vlan-manipulation

      } //container ingress

      container ipoe-session {
        description
            "Configure IPoE session parameters for capture SAP";
        container description {
          description
              "Description for the IPoE session";
          leaf description-string {
            type string {
              length "1..80";
            }
          } //description-string

        } //container description

        container ipoe-session-policy {
          description
              "Assign an IPoE session policy";
          leaf policy-name {
            type string {
              length "1..32";
            }
          } //policy-name

        } //container ipoe-session-policy

        leaf shutdown {
          type boolean;
          description
              "Administratively enable/disable IPoE Session";
        }

        container user-db {
          description
              "Assign a local user database";
          leaf local-user-db-name {
            type string {
              length "1..32";
            }
          } //local-user-db-name

        } //container user-db

      } //container ipoe-session

      container l2tpv3-session {
        description
            "Configure L2TPv3 session parameters";
        container pw-type {
          description
              "Configure pseudo-wire type";
          leaf ethernet {
            type boolean;
          } //ethernet

          leaf ethernet-vlan {
            type int32 {
              range "0..4095";
            }
          } //ethernet-vlan

        } //container pw-type

        container router {
          description
              "Configure L2TPv3 session router information";
          leaf router-instance {
            type string {
              length "1..32";
            }
            default "Base";
            description
                "Attribute router-instance for router";
          } //router-instance

          leaf group {
            type string {
              length "1..32";
            }
          } //group

          leaf service-name {
            type string;
          } //service-name

        } //container router

        leaf shutdown {
          type boolean;
          description
              "Configure adminstrative state of the entry";
        }

        container vc-id {
          description
              "Configure VC identifier";
          leaf vc-id {
            type uint32 {
              range "1..4294967295";
            }
          } //vc-id

        } //container vc-id

      } //container l2tpv3-session

      container managed-vlan-list {
        description
            "Provision VLAN list for this mVPLS SAP";
        leaf default-sap {
          type boolean;
          description
              "add default SAP to the managed vlan list";
        }

        list range {
          key "vlan-range";
          description
              "Configure range of VLANs managed by this SAP";
          leaf vlan-range {
            type string {
              length "1..64";
            }
            description
                "[0..4094] - [0..4094]";
          } //vlan-range

        } //list range

      } //container managed-vlan-list

      container mld-snooping {
        description
            "Configure MLD snooping parameters";
        leaf disable-router-alert-check {
          type boolean;
          description
              "Enable/disable the MLD router alert check option";
        }

        leaf fast-leave {
          type boolean;
          description
              "Enable/disable MLD fast-leave processing";
        }

        list import {
          key "policy-name";
          description
              "Import a policy to filter MLD packets";
          leaf policy-name {
            type string {
              length "1..32";
            }
          } //policy-name

        } //list import

        container last-member-query-interval {
          description
              "Configure the MLD Last Member Query Interval";
          leaf t1-10-seconds {
            type uint32 {
              range "1..50";
            }
          } //t1-10-seconds

        } //container last-member-query-interval

        container max-num-groups {
          description
              "Configure the max number of multicast groups allowed";
          leaf max-num-groups-id {
            type uint32 {
              range "1..16000";
            }
          } //max-num-groups-id

        } //container max-num-groups

        leaf mrouter-port {
          type boolean;
          description
              "Configure the SAP as a multicast router port";
        }

        container query-interval {
          description
              "Configure the MLD Query Interval";
          leaf seconds {
            type uint32 {
              range "2..1024";
            }
          } //seconds

        } //container query-interval

        container query-response-interval {
          description
              "Configure the MLD Query Response Interval";
          leaf seconds {
            type uint32 {
              range "1..1023";
            }
          } //seconds

        } //container query-response-interval

        container robust-count {
          description
              "Configure the MLD Robustness Variable";
          leaf robust-count {
            type uint32 {
              range "2..7";
            }
          } //robust-count

        } //container robust-count

        leaf send-queries {
          type boolean;
          description
              "Enable/disable generation of MLD General Queries";
        }

        container version {
          description
              "Configure the version of MLD";
          leaf version {
            type uint32 {
              range "1..2";
            }
            description
                "[1 or 2]";
          } //version

        } //container version

        container mcac {
          description
              "Configure multicast CAC policy and constraints for this SAP";
          container if-policy {
            description
                "Configure multicast CAC if-policy";
            leaf if-policy-name {
              type string {
                length "1..32";
              }
            } //if-policy-name

          } //container if-policy

          container policy {
            description
                "Enable/disable multicast CAC policy";
            leaf policy-name {
              type string {
                length "1..32";
              }
              description
                  "max 32 chars";
            } //policy-name

          } //container policy

          container unconstrained-bw {
            description
                "Set/reset unconstrained-bw for multicast CAC policy on this SAP";
            leaf bandwidth {
              type int32 {
                range "0..2147483647";
              }
              description
                  "[0..2147483647] kbps";
            } //bandwidth

            leaf mandatory-bw {
              type int32 {
                range "0..2147483647";
              }
              description
                  "[0..2147483647] kbps";
            } //mandatory-bw

          } //container unconstrained-bw

          container mc-constraints {
            description
                "create context that allows for the configuration of the different levels and 
                 their associated bandwidth for multicast CAC policy on this SAP";
            list level {
              key "level-id";
              description
                  "Configure levels and their associated bandwidth for multicast CAC policy on 
                   this SAP";
              leaf level-id {
                type uint32 {
                  range "1..8";
                }
              } //level-id

              leaf bw {
                type uint32;
                description
                    "[0..2147483647] kbps";
              } //bw

            } //list level

            list number-down {
              key "number-lag-port-down";
              description
                  "Configure number of ports down along with level for multicast CAC policy on 
                   this SAP";
              leaf number-lag-port-down {
                type string;
                description
                    "Attribute number-lag-port-down for number-down";
              } //number-lag-port-down

              leaf level {
                type uint32 {
                  range "1..8";
                }
              } //level

            } //list number-down

            leaf shutdown {
              type boolean;
              description
                  "Administratively enable/disable constraint for multicast CAC policy";
            }

            leaf use-lag-port-weight {
              type boolean;
              description
                  "Enable/disable using the LAG port weight while calculating Multicast CAC 
                   constraints";
            }

          } //container mc-constraints

        } //container mcac

        container mvr {
          description
              "Configure Multicast VPLS Registration parameters";
          container from-vpls {
            description
                "The MVR VPLS from which the multicast channels are taken";
            leaf service-id {
              type string;
              description
                  "Attribute service-id for from-vpls";
            } //service-id

          } //container from-vpls

          container to-sap {
            description
                "The SAP to which the multicast channels are copied";
            leaf sap-id {
              type string;
              description
                  "Attribute sap-id for to-sap";
            } //sap-id

          } //container to-sap

        } //container mvr

        container static {
          description
              "Add/remove MLD static group membership";
          list group {
            key "grp-ipv6-address";
            description
                "Add/remove a static multicast group";
            leaf grp-ipv6-address {
              type inet:ipv6-address;
              description
                  "Attribute grp-ipv6-address for group";
            } //grp-ipv6-address

            list source {
              key "src-ipv6-address";
              description
                  "Add/remove a static multicast source";
              leaf src-ipv6-address {
                type inet:ipv6-address;
                description
                    "Attribute src-ipv6-address for source";
              } //src-ipv6-address

            } //list source

            leaf starg {
              type boolean;
              description
                  "Add/remove a static starg entry";
            }

          } //list group

        } //container static

      } //container mld-snooping

      container mrp {
        description
            "Configure MRP attributes";
        container join-time {
          description
              "Configure timer value in 10th of seconds for sending join-messages";
          leaf join-time {
            type int32 {
              range "1..10";
            }
            description
                "[1-10] tenths of a second";
          } //join-time

        } //container join-time

        container leave-all-time {
          description
              "Configure timer value in 10th of seconds for refreshing all attributes";
          leaf leave-all-time {
            type int32 {
              range "60..300";
            }
            description
                "[60..300] tenths of a second";
          } //leave-all-time

        } //container leave-all-time

        container leave-time {
          description
              "Configure timer value in 10th of seconds to hold attribute in leave-state";
          leaf leave-time {
            type int32 {
              range "30..60";
            }
            description
                "[30..60] tenths of a second";
          } //leave-time

        } //container leave-time

        container mrp-policy {
          description
              "Configure mrp-policy";
          leaf policy-name {
            type string {
              length "1..32";
            }
          } //policy-name

        } //container mrp-policy

        container periodic-time {
          description
              "Configure timer value in 10th of seconds for re-transmission of attribute 
               declarations";
          leaf periodic-time {
            type int32 {
              range "10..100";
            }
            description
                "[10..100] tenths of a second";
          } //periodic-time

        } //container periodic-time

        leaf periodic-timer {
          type boolean;
          description
              "Control re-transmission of attribute declarations";
        }

        container mvrp {
          description
              "Configure MVRP attributes";
          list endstation-vid-group {
            key "vlan-group-id";
            description
                "Configure end-station vlan-id group";
            leaf vlan-group-id {
              type uint32 {
                range "1..4094";
              }
            } //vlan-group-id

            leaf vlan-range {
              type string;
              description
                  "<1..4094>-<1..4094>";
            } //vlan-range

          } //list endstation-vid-group

          leaf shutdown {
            type boolean;
            description
                "Administratively enable/disable MVRP on the SAP";
          }

        } //container mvrp

      } //container mrp

      container msap-defaults {
        description
            "Configure MSAP authentication defaults";
        container group-interface {
          description
              "Configure the group interface";
          leaf ip-int-name {
            type string {
              length "1..32";
            }
            description
                "[32 chars max] (must start with a letter)";
          } //ip-int-name

        } //container group-interface

        container policy {
          description
              "Configure the MSAP policy";
          leaf msap-policy-name {
            type string {
              length "1..32";
            }
            description
                "Managed SAP policy name";
          } //msap-policy-name

        } //container policy

        container service {
          description
              "Configure the service";
          leaf service-id {
            type string;
            description
                "Attribute service-id for service";
          } //service-id

        } //container service

      } //container msap-defaults

      container pfcp {
        description
            "Configure Packet Forwarding Control Plane (PFCP) parameters";
        container association {
          description
              "Configure the PFCP association used for PFCP messages on this capture SAP";
          leaf name {
            type string;
          } //name

        } //container association

      } //container pfcp

      container pim-snooping {
        description
            "Configure PIM snooping parameters on this SAP";
        container max-num-groups {
          description
              "Configure maximum group for PIM snooping";
          leaf max-num-groups-id {
            type uint32 {
              range "1..16000";
            }
          } //max-num-groups-id

        } //container max-num-groups

      } //container pim-snooping

      container spb {
        description
            "Configure Shortest Path Bridging";
        container lsp-pacing-interval {
          description
              "Configure the interval for sending LSPs from the interface";
          leaf milli-seconds {
            type uint32 {
              range "0..65535";
            }
          } //milli-seconds

        } //container lsp-pacing-interval

        container retransmit-interval {
          description
              "Configure the minimum interval between LSP packets retransmission for the 
               given interface";
          leaf seconds {
            type int32 {
              range "1..65535";
            }
          } //seconds

        } //container retransmit-interval

        leaf shutdown {
          type boolean;
          description
              "Administratively Enable/disable the interface";
        }

        container level {
          description
              "Configure SPB level information";
          leaf level-id {
            type uint32 {
            }
          } //level-id

          container hello-interval {
            description
                "Configure hello-interval for this interface";
            leaf seconds {
              type int32 {
                range "1..20000";
              }
            } //seconds

          } //container hello-interval

          container hello-multiplier {
            description
                "Configure hello-multiplier for this level";
            leaf multiplier {
              type int32 {
                range "2..100";
              }
            } //multiplier

          } //container hello-multiplier

          container metric {
            description
                "Configure IS-IS interface metric for IPv4 unicast";
            leaf ipv4-metric {
              type uint32 {
                range "1..16777215";
              }
            } //ipv4-metric

          } //container metric

        } //container level

      } //container spb

      container static-host {
        description
            "Configure a static host on this SAP";
        leaf ip {
          type inet:ip-address;
        } //ip

        leaf mac {
          type string;
          description
              "xx:xx:xx:xx:xx:xx or xx-xx-xx-xx-xx-xx (cannot be all zeros)";
        } //mac

        leaf all {
          type boolean;
        } //all

        leaf force {
          type boolean;
          description
              "keyword - force removal";
        } //force

        container ancp-string {
          description
              "Configure the ANCP string";
          leaf ancp-string {
            type string {
              length "1..63";
            }
          } //ancp-string

        } //container ancp-string

        container app-profile {
          description
              "Configure the application profile name";
          leaf app-profile-name {
            type string {
              length "1..32";
            }
          } //app-profile-name

        } //container app-profile

        container inter-dest-id {
          description
              "Configure the intermediate destination id";
          leaf intermediate-destination-id {
            type string {
              length "1..32";
            }
          } //intermediate-destination-id

        } //container inter-dest-id

        leaf shutdown {
          type boolean;
          description
              "Enable/disable the static host";
        }

        container sla-profile {
          description
              "Configure the SLA profile name";
          leaf sla-profile-name {
            type string {
              length "1..32";
            }
          } //sla-profile-name

        } //container sla-profile

        container sub-profile {
          description
              "Configure the sub-profile name";
          leaf sub-profile-name {
            type string {
              length "1..32";
            }
          } //sub-profile-name

        } //container sub-profile

        container subscriber {
          description
              "Configure the subscriber identification";
          leaf sub-ident-string {
            type string;
            description
                "Attribute sub-ident-string for subscriber";
          } //sub-ident-string

        } //container subscriber

        leaf subscriber-sap-id {
          type boolean;
          description
              "Enable/disable using the SAP id as subscriber id";
        }

      } //container static-host

      container static-isid {
        description
            "Configure static ISID ranges";
        list range {
          key "range-id";
          description
              "Configure static ISID range";
          leaf range-id {
            type uint32 {
              range "1..8191";
            }
          } //range-id

          leaf isid {
            type uint32 {
              range "1..16777215";
            }
          } //isid

          leaf to {
            type uint32 {
              range "1..16777215";
            }
            description
                "isid-value";
          } //to

        } //list range

      } //container static-isid

      container stp {
        description
            "Configure spanning tree protocol parameters";
        leaf auto-edge {
          type boolean;
          description
              "Enable/disable automatic detection of edge port";
        }

        leaf edge-port {
          type boolean;
          description
              "Configure sap as edge or non-edge port";
        }

        list link-type {
          key "pt-pt-shared";
          description
              "Configure link type of the sap";
          leaf pt-pt-shared {
            type enumeration {
              enum pt-pt;
              enum shared;
            }
            description
                "link type";
          } //pt-pt-shared

        } //list link-type

        list path-cost {
          key "sap-path-cost";
          description
              "Configure path-cost";
          leaf sap-path-cost {
            type uint32 {
              range "1..200000000";
            }
          } //sap-path-cost

        } //list path-cost

        list port-num {
          key "virtual-port-number";
          description
              "Configure virtual port number";
          leaf virtual-port-number {
            type uint64 {
              range "1..2047";
            }
            description
                "[1..2047]";
          } //virtual-port-number

        } //list port-num

        list priority {
          key "stp-priority";
          description
              "Configure stp priority";
          leaf stp-priority {
            type uint32 {
              range "0..255";
            }
          } //stp-priority

        } //list priority

        leaf root-guard {
          type boolean;
          description
              "Enable/disable STP root-guard";
        }

        leaf shutdown {
          type boolean;
          description
              "Enable/disable spanning tree protocol";
        }

        container mst-instance {
          description
              "Provision a Multiple Spanning Tree instance";
          leaf mst-inst-number {
            type uint32 {
              range "1..4094";
            }
          } //mst-inst-number

          container mst-path-cost {
            description
                "Configure path-cost";
            leaf inst-path-cost {
              type uint32 {
                range "1..200000000";
              }
            } //inst-path-cost

          } //container mst-path-cost

          container mst-port-priority {
            description
                "Configure MSTI port priority";
            leaf stp-priority {
              type uint32 {
                range "0..255";
              }
            } //stp-priority

          } //container mst-port-priority

        } //container mst-instance

      } //container stp

      container sub-sla-mgmt {
        presence
            "Configure subscriber management for this SAP";
        container def-app-profile {
          description
              "Configure a default application profile for this SAP";
          leaf default-app-profile-name {
            type string {
              length "1..32";
            }
          } //default-app-profile-name

        } //container def-app-profile

        container def-inter-dest-id {
          description
              "Configure default inter-dest-id";
          leaf string {
            type string {
              length "1..32";
            }
          } //string

          leaf use-top-q {
            type boolean;
          } //use-top-q

        } //container def-inter-dest-id

        container def-sla-profile {
          description
              "Configure a default SLA profile for this SAP";
          leaf default-sla-profile-name {
            type string {
              length "1..32";
            }
          } //default-sla-profile-name

        } //container def-sla-profile

        container def-sub-id {
          description
              "Configure a default subscriber identification string for this SAP";
          leaf use-sap-id {
            type boolean;
            description
                "keyword - use sap-id as subscriber-id";
          } //use-sap-id

          leaf string {
            type string;
            description
                "Attribute sub-ident-string for def-sub-id";
          } //string

          leaf use-auto-id {
            type boolean;
            description
                "keyword - use auto-generated subscriber-id";
          } //use-auto-id

        } //container def-sub-id

        container def-sub-profile {
          description
              "Configure a default subscriber profile for this SAP";
          leaf default-subscriber-profile-name {
            type string {
              length "1..32";
            }
          } //default-subscriber-profile-name

        } //container def-sub-profile

        leaf mac-da-hashing {
          type boolean;
          description
              "Enable/disable hashing on MAC DA iso subscriber id";
        }

        container multi-sub-sap {
          description
              "Configure maximum number of subscribers for this SAP";
          leaf subscriber-limit {
            type uint32 {
              range "2..131071";
            }
            description
                "Attribute subscriber-limit for multi-sub-sap";
          } //subscriber-limit

        } //container multi-sub-sap

        leaf shutdown {
          type boolean;
          description
              "Enable/disable subscriber management on this SAP";
        }

        container sub-ident-policy {
          description
              "Apply a subscriber identification policy on this SAP";
          leaf sub-ident-policy-name {
            type string {
              length "1..32";
            }
          } //sub-ident-policy-name

        } //container sub-ident-policy

        container single-sub-parameters {
          description
              "Configure the single-sub-parameters for this SAP";
          container non-sub-traffic {
            description
                "Configure non-subscriber-traffic profiles";
            leaf sub-profile {
              type string {
                length "1..32";
              }
            } //sub-profile

            leaf sla-profile {
              type string {
                length "1..32";
              }
            } //sla-profile

            leaf subscriber {
              type string;
              description
                  "Attribute sub-ident-string for non-sub-traffic";
            } //subscriber

            leaf app-profile {
              type string {
                length "1..32";
              }
            } //app-profile

          } //container non-sub-traffic

          leaf profiled-traffic-only {
            type boolean;
            description
                "Enable/disable profiled-traffic-only for this SAP";
          }

        } //container single-sub-parameters

      } //container sub-sla-mgmt

    } //list sap

  } //grouping alu-conf-svc-vpls-sap-r13

} //module  alu-conf-svc-vpls-sap-r13
