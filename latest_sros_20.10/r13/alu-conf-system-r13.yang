module alu-conf-system-r13 {
  yang-version "1";

  namespace "urn:alcatel-lucent.com:sros:ns:yang:conf-system-r13";

  prefix "conf-system-r13";

  import alu-conf-sys-cellular-r13 {
    prefix "conf-sys-cellular-r13";
  }
  import alu-conf-sys-ptp-r13 {
    prefix "conf-sys-ptp-r13";
  }
  import alu-conf-sys-pwrmgmt-r13 {
    prefix "conf-sys-pwrmgmt-r13";
  }
  import alu-conf-sys-sec-r13 {
    prefix "conf-sys-sec-r13";
  }
  import alu-types {
    prefix "alu";
  }
  import ietf-inet-types {
    prefix "inet";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure system parameters on SR OS based 
       routers. 
       
       Copyright 2014-2015 Alcatel-Lucent, 2016 Nokia. All rights reserved. 
       Reproduction of this document is authorized on the condition that the 
       foregoing copyright notice is included. 
       
       This alu-conf-system-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2021-11-03";

  grouping alu-conf-system-r13 {
    container system {
      description
          "Configure system parameters";
      container alarm-contact-in-power {
        description
            "Configure the alarm contact input's internal power source switch";
        leaf on-off {
          type enumeration {
            enum on;
            enum off;
          }
        } //on-off

      } //container alarm-contact-in-power

      leaf allow-boot-license-violations {
        type boolean;
        description
            "Accept boot configuration containing licensing violations";
      }

      container boot-bad-exec {
        description
            "Configure url for CLI script to exec following failure of boot-up 
             configuration";
        leaf file-url {
          type string {
            length "1..255";
          }
          description
              "Attribute file-url for boot-bad-exec";
        } //file-url

      } //container boot-bad-exec

      container boot-good-exec {
        description
            "Configure url for CLI script to exec following success of boot-up 
             configuration";
        leaf file-url {
          type string {
            length "1..255";
          }
          description
              "Attribute file-url for boot-good-exec";
        } //file-url

      } //container boot-good-exec

      container chassis-mode {
        description
            "Configure the chassis scaling and feature set";
        leaf chassis-mode {
          type string {
            length "1";
          }
          description
              "Attribute chassis-mode for chassis-mode";
        } //chassis-mode

        leaf force {
          type boolean;
          description
              "Attribute force for chassis-mode";
        } //force

      } //container chassis-mode

      container clli-code {
        description
            "Configure a Common Language Location Identifier Code (CLLI) code string";
        leaf clli-code {
          type string {
            length "1..11";
          }
        } //clli-code

      } //container clli-code

      container config-backup {
        description
            "Configure maximum number of backup revisions maintained for configuration 
             files and BOF";
        leaf count {
          type uint32 {
            range "1..200";
          }
        } //count

      } //container config-backup

      leaf congestion-management {
        type boolean;
        description
            "Configure VSR Congestion Management";
      }

      container contact {
        description
            "Configure system contact name";
        leaf contact-name {
          type string {
            length "1..80";
          }
        } //contact-name

      } //container contact

      container coordinates {
        description
            "Configure system coordinates";
        leaf coordinates {
          type string {
            length "1..80";
          }
        } //coordinates

      } //container coordinates

      leaf enable-icmp-vse {
        type boolean;
        description
            "Enable vendor specific extensions to ICMP";
      }

      container lacp-system-priority {
        description
            "Configure Link Aggregation Control Protocol system priority";
        leaf lacp-system-priority {
          type uint32 {
            range "1..65535";
          }
        } //lacp-system-priority

      } //container lacp-system-priority

      container location {
        description
            "Configure system location";
        leaf location {
          type string {
            length "1..80";
          }
        } //location

      } //container location

      leaf mixed-mode {
        type boolean;
        status "obsolete";
        description
            "Configure chassis to support features with a mixture of IOMs/IMMs";
      }

      list monitor-filter-door {
        key "chassis";
        description
            "Monitor filter door configuration";
        leaf chassis {
          type string;
        } //chassis

      } //list monitor-filter-door

      container name {
        description
            "Configure system name";
        leaf system-name {
          type string {
            length "1..64";
          }
        } //system-name

      } //container name

      leaf ospf-dynamic-hostnames {
        type boolean;
        description
            "Enable/disable OSPF dynamic hostnames";
      }

      container power-supply {
        description
            "Configure the type of power supply for the system";
        leaf power-supply-id {
          type uint32;
          description
              "Attribute power-supply-id for power-supply";
        } //power-supply-id

        leaf type {
          type enumeration {
            enum dc;
            enum none;
            enum default;
          }
          description
              "keywords - dc|ac {single|multiple}|default|none";
        } //type

        leaf ac {
          type enumeration {
            enum single;
            enum multiple;
          }
          description
              "keywords";
        } //ac

        leaf chassis {
          type string;
          description
              "Attribute chassis-id for power-supply";
        } //chassis

      } //container power-supply

      leaf reduce-fan-speed {
        type boolean;
        description
            "Enable/disable the reduced fan speed mode";
      }

      leaf selective-fib {
        type boolean;
        description
            "Configure system-wide selective FIB";
      }

      container switchover-exec {
        description
            "Configure url for CLI script to exec following redundancy switchover";
        leaf file-url {
          type string {
            length "1..255";
          }
          description
              "Attribute file-url for switchover-exec";
        } //file-url

      } //container switchover-exec

      container alarm-contact-input {
        description
            "Configuration for alarm contact input parameters";
        leaf input-pin-number {
          type string;
          description
              "Attribute input-pin-number for alarm-contact-input";
        } //input-pin-number

        container clear-alarm-msg {
          description
              "Configure the clear event text";
          leaf message-string {
            type string {
              length "1..80";
            }
          } //message-string

        } //container clear-alarm-msg

        container description {
          description
              "Configure the description of the alarm contact input pin";
          leaf description-string {
            type string {
              length "1..160";
            }
          } //description-string

        } //container description

        container normal-state {
          description
              "Configure the normal operational state of the alarm contact input (i.e. when 
               there is no alarm)";
          leaf pin-normal-state {
            type enumeration {
              enum open;
              enum closed;
            }
            default "open";
            description
                "open|closed - Default: open";
          } //pin-normal-state

        } //container normal-state

        leaf shutdown {
          type boolean;
          description
              "Enable or disable the alarm contact input";
        }

        container trigger-alarm-msg {
          description
              "Configure the trigger event text";
          leaf message-string {
            type string {
              length "1..80";
            }
          } //message-string

        } //container trigger-alarm-msg

      } //container alarm-contact-input

      container alarms {
        description
            "Configure alarm management parameters";
        container max-cleared {
          description
              "Configure the maximum number of cleared alarms";
          leaf maximum {
            type uint32 {
              range "0..500";
            }
            default 500;
            description
                "[0..500] - Default: 500";
          } //maximum

        } //container max-cleared

        leaf shutdown {
          type boolean;
          description
              "Shutdown alarm management";
        }

      } //container alarms

      container atm {
        description
            "Configure system-wide ATM parameters";
        container atm-location-id {
          description
              "Configure ATM Location ID";
          leaf location-id {
            type string {
            }
            description
                "[47 chars] - in the form xx:xx:xx....";
          } //location-id

        } //container atm-location-id

        container oam {
          description
              "Configure OAM settings";
          container loopback-period {
            description
                "Configure loopback period";
            leaf period {
              type int32 {
                range "1..40";
              }
              description
                  "[1..40] in seconds";
            } //period

          } //container loopback-period

          container retry-down {
            description
                "Configure the number of failed loopbacks before a VC is down";
            leaf retries {
              type int32 {
                range "0..10";
              }
            } //retries

          } //container retry-down

          container retry-up {
            description
                "Configure the number of successful loopbacks before a VC is up";
            leaf retries {
              type int32 {
                range "0..10";
              }
            } //retries

          } //container retry-up

        } //container oam

      } //container atm

      container bluetooth {
        description
            "Configure Bluetooth parameters.";
        container advertising-timeout {
          description
              "The time when the Bluetooth module will stop advertising after a button press.";
          leaf seconds {
            type uint32 {
              range "30..3600";
            }
            default 30;
            description
                "[30..3600] seconds - Default: 30";
          } //seconds

        } //container advertising-timeout

        container pairing-button {
          description
              "Enable/Disable the active Bluetooth module pairing button.";
          leaf Enable-Disable {
            type enumeration {
              enum enable;
              enum disable;
            }
          } //Enable-Disable

        } //container pairing-button

        container passkey {
          description
              "Configure the system-wide Bluetooth passcode.";
          leaf passkey {
            type string {
              length "1..6";
            }
            description
                "Attribute passkey for passkey";
          } //passkey

        } //container passkey

        container power {
          description
              "Configure the active Bluetooth module power state.";
          leaf power-state {
            type enumeration {
              enum off;
              enum enabled-manual;
              enum enabled-automatic;
            }
          } //power-state

        } //container power

        list device {
          key "ieee-address";
          description
              "Configure Bluetooth capable device to be whitelisted in the system.";
          leaf ieee-address {
            type alu:ieee-address;
          } //ieee-address

          container description {
            description
                "Configure the description of the Bluetooth capable device.";
            leaf description-string {
              type string {
                length "1..80";
              }
            } //description-string

          } //container description

        } //list device

        container module {
          description
              "Configure the Bluetooth module.";
          leaf cpm-slot {
            type string;
            description
                "Attribute cpm-slot for module";
          } //cpm-slot

          container identifier {
            description
                "Configure the identifier of a Bluetooth module.";
            leaf identifier {
              type string {
                length "1..32";
              }
            } //identifier

          } //container identifier

        } //container module

      } //container bluetooth

      container ccm {
        description
            "Configure a chassis control module";
        leaf ccm-slot {
          type uint32 {
          }
        } //ccm-slot

        leaf shutdown {
          type boolean;
          description
              "Administratively shut down a ccm";
        }

      } //container ccm

      uses "conf-sys-cellular-r13:alu-conf-sys-cellular-r13";
      container cpm-http-redirect {
        description
            "Configuration of CPM HTTP redirect";
        leaf optimized-mode {
          type boolean;
          description
              "Enable/disable optimized mode for CPM HTTP redirect";
        }

      } //container cpm-http-redirect

      container cron {
        description
            "Configure time dependent command scheduling (CRON)";
        list schedule {
          key "schedule-name owner";
          description
              "Configure CRON schedule";
          leaf schedule-name {
            type string {
              length "1..32";
            }
          } //schedule-name

          leaf owner {
            type string {
              length "1..32";
            }
            description
                "[32 chars max] Default - \"TiMOS CLI\"";
          } //owner

          container count {
            description
                "Number of times to repeat periodic schedule run";
            leaf number {
              type uint32 {
                range "1..65535";
              }
            } //number

          } //container count

          container day-of-month {
            description
                "Configure the days of the month for CRON schedule";
            leaf-list day-number {
              type int32 {
                range "-31..31";
              }
              max-elements 62;
              description
                  "[1..31]|[-31..-1] - maximum 62 day-numbers";
            } //day-number

            leaf all {
              type boolean;
              description
                  "all days of the month";
            } //all

          } //container day-of-month

          container description {
            description
                "Description for this CRON schedule";
            leaf description-string {
              type string {
                length "1..80";
              }
              description
                  "[80 chars max]";
            } //description-string

          } //container description

          container end-time {
            description
                "Configure time to stop CRON schedule";
            leaf date {
              type string;
              description
                  "YYYY/MM/DD";
            } //date

            leaf time {
              type string;
              description
                  "hh:mm";
            } //time

            leaf day-name {
              type enumeration {
                enum sunday;
                enum monday;
                enum tuesday;
                enum wednesday;
                enum thursday;
                enum friday;
                enum saturday;
              }
            } //day-name

          } //container end-time

          container hour {
            description
                "Configure hour for CRON schedule";
            leaf-list hour-number {
              type uint32 {
                range "0..23";
              }
              max-elements 24;
              description
                  "[0..23] - maximum 24 hour-numbers";
            } //hour-number

            leaf all {
              type boolean;
              description
                  "all hours";
            } //all

          } //container hour

          container interval {
            description
                "Interval between each periodic schedule run";
            leaf seconds {
              type uint32 {
                range "30..42949672";
              }
            } //seconds

          } //container interval

          container minute {
            description
                "Configure minute for CRON schedule";
            leaf-list minute-number {
              type uint32 {
                range "0..59";
              }
              max-elements 60;
              description
                  "[0..59] - maximum 60 minute-numbers";
            } //minute-number

            leaf all {
              type boolean;
              description
                  "all minutes";
            } //all

          } //container minute

          container month {
            description
                "Configure month for CRON schedule";
            leaf-list month-number {
              type uint32 {
                range "1..12";
              }
              max-elements 12;
              description
                  "[1..12] - maximum 12 month-numbers";
            } //month-number

            leaf-list month-name {
              type enumeration {
                enum january;
                enum february;
                enum march;
                enum april;
                enum may;
                enum june;
                enum july;
                enum august;
                enum september;
                enum october;
                enum november;
                enum december;
              }
              max-elements 12;
              description
                  "january|february|march|april|may|june|july|august|september|october|november|december 
                   
                   maximum 12 month names";
            } //month-name

            leaf all {
              type boolean;
              description
                  "all months";
            } //all

          } //container month

          container script-policy {
            description
                "Script-policy parameters for this schedule";
            leaf script-policy-name {
              type string {
                length "1..32";
              }
            } //script-policy-name

            leaf owner {
              type string {
                length "1..32";
              }
              default "TiMOS CLI";
              description
                  "[32 chars max] Default - \"TiMOS CLI\"";
            } //owner

          } //container script-policy

          leaf shutdown {
            type boolean;
            description
                "Administratively enable/disable the CRON schedule";
          }

          container type {
            description
                "Type of schedule";
            leaf schedule-type {
              type enumeration {
                enum periodic;
                enum calendar;
                enum oneshot;
              }
              default "periodic";
              description
                  "periodic|calendar|oneshot Default: periodic";
            } //schedule-type

          } //container type

          container weekday {
            description
                "Configure week day for CRON schedule";
            leaf-list weekday-number {
              type uint32 {
                range "1..7";
              }
              max-elements 7;
              description
                  "[1..7] - maximum 7 week-day-numbers";
            } //weekday-number

            leaf-list day-name {
              type enumeration {
                enum sunday;
                enum monday;
                enum tuesday;
                enum wednesday;
                enum thursday;
                enum friday;
                enum saturday;
              }
              max-elements 7;
              description
                  "sunday|monday|tuesday|wednesday|thursday|friday|saturday 
                   maximum 7 weekday names";
            } //day-name

            leaf all {
              type boolean;
              description
                  "all days of the week";
            } //all

          } //container weekday

        } //list schedule

        list time-range {
          key "name";
          status "obsolete";
          description
              "Configure a time range";
          leaf name {
            type string {
              length "1..32";
            }
          } //name

          list absolute {
            key "start";
            status "obsolete";
            description
                "Configure an absolute time interval in the time-range";
            leaf start {
              type string {
                length "1..32";
              }
              description
                  "Attribute start-absolute-time for absolute";
            } //start

            leaf end {
              type string {
                length "1..32";
              }
              description
                  "Attribute end-absolute-time for absolute";
            } //end

          } //list absolute

          list daily {
            key "start";
            status "obsolete";
            description
                "Configure a daily time interval in the time-range";
            leaf start {
              type string {
              }
              description
                  "hh:mm 
                   hh : 0..23 
                   mm : 0..59";
            } //start

            leaf end {
              type string {
              }
              description
                  "hh:mm 
                   hh : 0..24 
                   mm : 0..59";
            } //end

          } //list daily

          container description {
            status "obsolete";
            description
                "Specify a description for this time-range";
            leaf description-string {
              type string {
                length "1..80";
              }
            } //description-string

          } //container description

          list weekdays {
            key "start";
            status "obsolete";
            description
                "Configure a time interval for weekdays in the time-range";
            leaf start {
              type string {
              }
              description
                  "hh:mm 
                   hh : 0..23 
                   mm : 0..59";
            } //start

            leaf end {
              type string {
              }
              description
                  "hh:mm 
                   hh : 0..24 
                   mm : 0..59";
            } //end

          } //list weekdays

          list weekend {
            key "start";
            status "obsolete";
            description
                "Configure a time interval for every weekend day in the time-range";
            leaf start {
              type string {
              }
              description
                  "hh:mm 
                   hh : 0..23 
                   mm : 0..59";
            } //start

            leaf end {
              type string {
              }
              description
                  "hh:mm 
                   hh : 0..24 
                   mm : 0..59";
            } //end

          } //list weekend

          list weekly {
            key "start";
            status "obsolete";
            description
                "Configure a weekly periodic interval in the time-range";
            leaf start {
              type string {
                length "1..32";
              }
              description
                  "Attribute start-time-in-week for weekly";
            } //start

            leaf end {
              type string {
                length "1..32";
              }
              description
                  "Attribute end-time-in-week for weekly";
            } //end

          } //list weekly

        } //list time-range

        list tod-suite {
          key "tod-suite-name";
          status "obsolete";
          description
              "Configure a time-of-day Suite";
          leaf tod-suite-name {
            type string {
              length "1..32";
            }
          } //tod-suite-name

          container description {
            status "obsolete";
            description
                "Specify a description for this tod-suite";
            leaf description-string {
              type string {
                length "1..80";
              }
            } //description-string

          } //container description

          container egress {
            status "obsolete";
            description
                "Configure tod suite egress parameters";
            list filter {
              key "time-range";
              status "obsolete";
              description
                  "Specify an egress filter for this tod-suite";
              leaf ip {
                type string;
                description
                    "[1..65535]|<name:64 char max>";
              } //ip

              leaf ipv6 {
                type string;
                description
                    "[1..65535]|<name:64 char max>";
              } //ipv6

              leaf mac {
                type string;
                description
                    "[1..65535]|<name:64 char max>";
              } //mac

              leaf time-range {
                type string {
                  length "1..32";
                }
              } //time-range

              leaf priority {
                type uint16 {
                  range "1..10";
                }
              } //priority

            } //list filter

            list qos {
              key "policy-id time-range";
              status "obsolete";
              description
                  "Specify an egress qos policy for this tod-suite";
              leaf policy-id {
                type string;
                description
                    "[1..65535]|<name:64 char max>";
              } //policy-id

              leaf time-range {
                type string {
                  length "1..32";
                }
              } //time-range

              leaf priority {
                type uint16 {
                  range "1..10";
                }
              } //priority

            } //list qos

            list scheduler-policy {
              key "Scheduler-policy-name time-range";
              status "obsolete";
              description
                  "Specify an egress scheduler policy for this tod-suite";
              leaf Scheduler-policy-name {
                type string {
                  length "1..32";
                }
              } //Scheduler-policy-name

              leaf time-range {
                type string {
                  length "1..32";
                }
              } //time-range

              leaf priority {
                type uint16 {
                  range "1..10";
                }
              } //priority

            } //list scheduler-policy

          } //container egress

          container ingress {
            status "obsolete";
            description
                "Configure tod suite ingress parameters";
            list filter {
              key "time-range";
              status "obsolete";
              description
                  "Specify an ingress filter for this tod-suite";
              leaf ip {
                type string;
                description
                    "[1..65535]|<name:64 char max>";
              } //ip

              leaf ipv6 {
                type string;
                description
                    "[1..65535]|<name:64 char max>";
              } //ipv6

              leaf mac {
                type string;
                description
                    "[1..65535]|<name:64 char max>";
              } //mac

              leaf time-range {
                type string {
                  length "1..32";
                }
              } //time-range

              leaf priority {
                type uint16 {
                  range "1..10";
                }
              } //priority

            } //list filter

            list qos {
              key "policy-id time-range";
              status "obsolete";
              description
                  "Specify an ingress qos policy for this tod-suite";
              leaf policy-id {
                type string;
                description
                    "[1..65535]|<name:64 char max>";
              } //policy-id

              leaf time-range {
                type string {
                  length "1..32";
                }
              } //time-range

              leaf priority {
                type uint16 {
                  range "1..10";
                }
              } //priority

            } //list qos

            list scheduler-policy {
              key "Scheduler-policy-name time-range";
              status "obsolete";
              description
                  "Specify an ingress scheduler policy for this tod-suite";
              leaf Scheduler-policy-name {
                type string {
                  length "1..32";
                }
              } //Scheduler-policy-name

              leaf time-range {
                type string {
                  length "1..32";
                }
              } //time-range

              leaf priority {
                type uint16 {
                  range "1..10";
                }
              } //priority

            } //list scheduler-policy

          } //container ingress

        } //list tod-suite

      } //container cron

      container dhcp6 {
        description
            "Configure system-wide DHCPv6 parameters";
        container adv-noaddrs-global {
          description
              "Configure the placement (global or in the IA_NA) of a NoAddrsAvail status code 
               in Advertisement messages for various DHCPv6 applications. Default: within 
               IA_NA";
          leaf esm-proxy {
            type boolean;
          } //esm-proxy

          leaf esm-relay {
            type boolean;
          } //esm-relay

          leaf relay {
            type boolean;
          } //relay

          leaf server {
            type boolean;
          } //server

        } //container adv-noaddrs-global

      } //container dhcp6

      container dns {
        description
            "Configure system DNS settings";
        container address-pref {
          description
              "Configure the DNS address resolving order preference";
          leaf address-pref-id {
            type enumeration {
              enum ipv4-only;
              enum ipv6-first;
            }
          } //address-pref-id

        } //container address-pref

        container dnssec {
          description
              "Configure system Domain Name System Security Extensions (DNSSEC) settings";
          container ad-validation {
            description
                "Enable/Disable whether the presence of the AD-bit in responses from the DNS 
                 servers is validated";
            leaf fall-through-drop {
              type enumeration {
                enum fall-through;
                enum drop;
              }
              description
                  "fall-through - Permit DNS responses that do not pass DNSSEC validation 
                   drop - Reject DNS Responses that do not pass DNSSEC validation";
            } //fall-through-drop

          } //container ad-validation

        } //container dnssec

      } //container dns

      container ethernet {
        description
            "Configure system-wide Ethernet parameters";
        leaf new-qinq-untagged-sap {
          type boolean;
          description
              "Configure Q-IN-Q behavior";
        }

        container efm-oam {
          description
              "Configure System EFM OAM attributes";
          leaf dying-gasp-tx-on-reset {
            type boolean;
            description
                "Enable/Disable EFM OAM dying gasp messages on reset";
          }

          leaf grace-tx-enable {
            type boolean;
            description
                "Enable/Disable EFM OAM grace period messages";
          }

        } //container efm-oam

      } //container ethernet

      list file-transmission-profile {
        key "name";
        description
            "Configure file transmission profile parameters";
        leaf name {
          type string;
        } //name

        container ipv4-source-address {
          description
              "Configure the IPv4 source address of the file transmission connections";
          leaf ip-address {
            type inet:ip-address;
            description
                "a.b.c.d";
          } //ip-address

        } //container ipv4-source-address

        container ipv6-source-address {
          description
              "Configure the IPv6 source address of the file transmission connections";
          leaf ipv6-address {
            type inet:ipv6-address;
            description
                "x:x:x:x:x:x:x:x (eight 16-bit pieces)";
          } //ipv6-address

        } //container ipv6-source-address

        container redirection {
          description
              "Configure the maximum level of redirection";
          leaf redirection-id {
            type uint32 {
              range "1..8";
            }
          } //redirection-id

        } //container redirection

        container retry {
          description
              "Configure the number of attempts to retry connecting the server";
          leaf count {
            type uint32 {
              range "1..256";
            }
          } //count

        } //container retry

        container router {
          description
              "Configure the router instance which the file transmission connection will be 
               established on";
          leaf router-instance {
            type string {
              length "1..32";
            }
            default "Base";
            description
                "Attribute router-instance for router";
          } //router-instance

          leaf service {
            type string;
          } //service

        } //container router

        container timeout {
          description
              "Configure the timeout for a response from the server";
          leaf seconds {
            type uint32 {
              range "1..3600";
            }
            default 60;
            description
                "[1..3600] - Default: 60";
          } //seconds

        } //container timeout

      } //list file-transmission-profile

      container forwarding-path-options {
        status "obsolete";
        description
            "Configure system forwarding path options";
        container dscp-transparency {
          description
              "Configure DSCP transparency parameters";
          leaf shutdown {
            type boolean;
            description
                "Administratively enable/disable DSCP transparencyl option";
          }

        } //container dscp-transparency

        container entropy-label {
          description
              "Configure entropy label parameters";
          leaf shutdown {
            type boolean;
            description
                "Administratively enable/disable entropy label option";
          }

        } //container entropy-label

        container fc-4-profile {
          description
              "Configure fc 4 profile parameters";
          leaf shutdown {
            type boolean;
            description
                "Administratively enable/disable 4 color mode";
          }

        } //container fc-4-profile

        container mac-filter {
          description
              "Configure MAC filter parameters";
          container outer-vlan-priority {
            description
                "Configure outer VLAN priority parameters";
            leaf shutdown {
              type boolean;
              description
                  "Administratively enable/disable MAC filter outer VLAN priority option";
            }

          } //container outer-vlan-priority

        } //container mac-filter

        container vpls-evpn-mpls {
          description
              "Configure VPLS-EVPN-MPLS parameters";
          leaf shutdown {
            type boolean;
            description
                "Administratively enable/disable VPLS-EVPN-MPLS option";
          }

        } //container vpls-evpn-mpls

      } //container forwarding-path-options

      container fp {
        description
            "Configure system forwarding path parameters";
        container cam-allocation {
          description
              "Configure cam bank allocation parameters";
          container v6-multicast {
            description
                "Configure v6 multicast parameter";
            leaf number-of-entries {
              type uint32 {
                range "1..10240";
              }
              description
                  "Attribute number-of-entries for v6-multicast";
            } //number-of-entries

          } //container v6-multicast

        } //container cam-allocation

        container options {
          description
              "Configure system forwarding path options";
          container mac-filter {
            description
                "Configure MAC filter parameters";
            container outer-vlan-priority {
              description
                  "Configure outer VLAN priority parameters";
              leaf shutdown {
                type boolean;
                description
                    "Administratively enable/disable MAC filter outer VLAN priority option";
              }

            } //container outer-vlan-priority

          } //container mac-filter

          container mpls {
            description
                "Configure system forwarding path mpls options";
            container entropy-label {
              description
                  "Configure entropy label parameters";
              leaf shutdown {
                type boolean;
                description
                    "Administratively enable/disable entropy label option";
              }

            } //container entropy-label

            container fast-switchover {
              description
                  "Configure MPLS fast switchover parameters";
              leaf shutdown {
                type boolean;
                description
                    "Administratively enable/disable MPLS fast switchover option";
              }

            } //container fast-switchover

          } //container mpls

          container qos {
            description
                "Configure system forwarding path qos options";
            container bum-policers {
              description
                  "Configure BUM policers";
              leaf shutdown {
                type boolean;
                description
                    "Administrative enable/disable BUM policers";
              }

            } //container bum-policers

            container dscp-transparency {
              description
                  "Configure DSCP transparency parameters";
              leaf shutdown {
                type boolean;
                description
                    "Administratively enable/disable DSCP transparencyl option";
              }

            } //container dscp-transparency

            container fc-4-profile {
              description
                  "Configure FC 4 profile parameters";
              leaf shutdown {
                type boolean;
                description
                    "Administratively enable/disable 4 color mode";
              }

            } //container fc-4-profile

            container ipv6-classification-criteria {
              description
                  "Configure IPv6 classification criteria";
              leaf shutdown {
                type boolean;
                description
                    "Administrative enable/disable IPv6 classification criteria";
              }

            } //container ipv6-classification-criteria

            container mac-classification-criteria {
              description
                  "Configure MAC classification criteria";
              leaf shutdown {
                type boolean;
                description
                    "Administrative enable/disable MAC classification criteria";
              }

            } //container mac-classification-criteria

          } //container qos

          container router {
            description
                "Configure system forwarding path router options";
            container ecmp {
              description
                  "Configure ECMP parameters";
              leaf shutdown {
                type boolean;
                description
                    "Administratively enable/disable ECMP option";
              }

            } //container ecmp

          } //container router

          container services {
            description
                "Configure system forwarding path services options";
            container vpls-evpn-mpls {
              description
                  "Configure VPLS-EVPN-MPLS parameters";
              leaf shutdown {
                type boolean;
                description
                    "Administratively enable/disable VPLS-EVPN-MPLS option";
              }

            } //container vpls-evpn-mpls

          } //container services

        } //container options

        container resource-allocation {
          description
              "Configure resource-allocation parameters";
          container g8032-sap {
            description
                "Configure max number of SAP resource-allocated";
            leaf number-of-entries {
              type uint32 {
                range "0..4096";
              }
              description
                  "Attribute number-of-entries for g8032-sap";
            } //number-of-entries

          } //container g8032-sap

        } //container resource-allocation

      } //container fp

      container grpc {
        description
            "Configure gRPC parameters";
        leaf allow-unsecure-connection {
          type boolean;
          description
              "Enable/disable gRPC server encryption";
        }

        leaf auto-config-save {
          type boolean;
          status "obsolete";
          description
              "Enable / disable automatic save of configuration as part of a commit operation";
        }

        container max-msg-size {
          description
              "Configure max rx message size";
          leaf number {
            type uint32 {
              range "1..1024";
            }
            default 512;
            description
                "[1..1024] MB - Default: 512 MB";
          } //number

        } //container max-msg-size

        leaf shutdown {
          type boolean;
          description
              "start/stop gRPC server";
        }

        container tls-server-profile {
          description
              "TLS profile for gRPC server";
          leaf name {
            type string;
          } //name

        } //container tls-server-profile

        container gnmi {
          description
              "Configure gNMI service parameters";
          leaf auto-config-save {
            type boolean;
            description
                "Enable / disable automatic save of configuration as part of a commit operation";
          }

          leaf shutdown {
            type boolean;
            description
                "start/stop gNMI service";
          }

        } //container gnmi

        container gnoi {
          description
              "Configure gNOI services parameters";
          container cert-mgmt {
            description
                "Configure gNOI CertificateManagement service parameters";
            leaf shutdown {
              type boolean;
              description
                  "start/stop gNOI CertificateManagement service";
            }

          } //container cert-mgmt

          container system {
            description
                "Configure gNOI System service parameters";
            leaf shutdown {
              type boolean;
              description
                  "start/stop gNOI System service";
            }

          } //container system

        } //container gnoi

        container md-cli {
          description
              "Configure MD-CLI service parameters";
          leaf shutdown {
            type boolean;
            description
                "start/stop MD-CLI service";
          }

        } //container md-cli

        container rib-api {
          description
              "Configure RibApi service parameters";
          container purge-timeout {
            description
                "Number of seconds until stale entries are purged";
            leaf seconds {
              type uint32 {
                range "1..100000";
              }
            } //seconds

          } //container purge-timeout

          leaf shutdown {
            type boolean;
            description
                "start/stop RibApi service";
          }

        } //container rib-api

        container tcp-keepalive {
          description
              "Parameters for TCP keep-alives";
          container idle-time {
            description
                "Number of seconds until the first TCP keep-alive is sent";
            leaf idle {
              type uint32 {
                range "1..100000";
              }
              default 600;
            } //idle

          } //container idle-time

          container interval {
            description
                "Number of seconds between two TCP keep-alives";
            leaf interval {
              type uint32 {
                range "1..100000";
              }
              default 15;
            } //interval

          } //container interval

          container retries {
            description
                "Number of missed keep-alives before the TCP connection is declared down";
            leaf count {
              type uint32 {
                range "3..100";
              }
              default 4;
            } //count

          } //container retries

          leaf shutdown {
            type boolean;
            description
                "Enable/disable TCP keep-alives";
          }

        } //container tcp-keepalive

      } //container grpc

      list icl {
        key "icl-id";
        status "obsolete";
        description
            "Configure the Inter-chassis Link parameters";
        leaf icl-id {
          type uint32 {
            range "1..8";
          }
        } //icl-id

        container primary {
          status "obsolete";
          description
              "Configure the Inter-chassis Link primary chassis port-id";
          leaf port-id {
            type string {
              length "1..17";
            }
            description
                "Attribute port-id for primary";
          } //port-id

        } //container primary

        container secondary {
          status "obsolete";
          description
              "Configure the Inter-chassis Link secondary chassis port-id";
          leaf port-id {
            type string {
              length "1..17";
            }
            description
                "Attribute port-id for secondary";
          } //port-id

        } //container secondary

        leaf shutdown {
          type boolean;
          status "obsolete";
          description
              "Administratively enable/disable the Inter-chassis Link";
        }

      } //list icl

      container ip {
        description
            "Configure system-wide IP router parameters";
        leaf allow-cpu-fragmentation {
          type boolean;
          description
              "Enables IP fragmentation for packets exceeding IP MTU via system CPU";
        }

        leaf allow-icmp-redirect {
          type boolean;
          description
              "Enables/Disables ICMP redirection";
        }

        leaf allow-qinq-network-interface {
          type boolean;
          description
              "Allow QinQ encapsulation for network interfaces";
        }

        leaf enforce-unique-if-index {
          type boolean;
          description
              "Enforce system-level unique if-index values while creating IP interfaces using 
               SNMP";
        }

        leaf forward-6in4 {
          type boolean;
          description
              "Enables the 6in4 forwarding of traffic sent to the system IP address";
        }

        leaf forward-ip-over-gre {
          type boolean;
          description
              "Enables the forwarding of IP traffic encapsulated in GRE transport sent to the 
               system IP address.";
        }

        container ipv6-eh {
          description
              "Limit the IPv6 headers processed ingress/egress";
          leaf ipv6-eh-id {
            type enumeration {
              enum max;
              enum limited;
            }
          } //ipv6-eh-id

        } //container ipv6-eh

        container mpls-tunnel-mode {
          description
              "Configure Mpls tunnel mode";
          leaf tunnel-mode {
            type enumeration {
              enum uniform;
              enum pipe;
            }
          } //tunnel-mode

        } //container mpls-tunnel-mode

        container mpls {
          description
              "Configure system-wide MPLS parameters";
          container label-stack-statistics-count {
            description
                "Configure Mpls label stack statistics count";
            leaf label-stack-statistics-count-id {
              type uint16 {
                range "1..2";
              }
            } //label-stack-statistics-count-id

          } //container label-stack-statistics-count

        } //container mpls

      } //container ip

      container l2tp {
        description
            "Configure system-wide L2TP parameters";
        container non-multi-chassis-tunnel-id-range {
          description
              "Configure the range of L2TP tunnel identifiers to be excluded from 
               multi-chassis redundancy synchronization";
          leaf start {
            type uint32 {
              range "0..16383";
            }
          } //start

          leaf end {
            type uint32 {
              range "0..16383";
            }
            description
                "l2tp-tunnel-id";
          } //end

          leaf default {
            type boolean;
          } //default

        } //container non-multi-chassis-tunnel-id-range

      } //container l2tp

      container lldp {
        description
            "Configure system-wide Link Layer Discovery Protocol parameters";
        container message-fast-tx {
          description
              "Configure duration of the fast transmission period";
          leaf time {
            type int32 {
              range "1..3600";
            }
            default 1;
            description
                "[1..3600] in seconds - Default: 1";
          } //time

        } //container message-fast-tx

        container message-fast-tx-init {
          description
              "Configure the number of LLDPDUs to send during the fast transmission period.";
          leaf count {
            type int32 {
              range "1..8";
            }
            default 4;
            description
                "[1..8] - Default: 4";
          } //count

        } //container message-fast-tx-init

        container notification-interval {
          description
              "Configure the minimum time between change notifications.";
          leaf time {
            type int32 {
              range "5..3600";
            }
            default 5;
            description
                "[5..3600] in seconds - Default: 5";
          } //time

        } //container notification-interval

        container reinit-delay {
          description
              "Configure time before re-initializing LLDP on a port.";
          leaf time {
            type int32 {
              range "1..10";
            }
            default 2;
            description
                "[1..10] in seconds - Default: 2";
          } //time

        } //container reinit-delay

        leaf shutdown {
          type boolean;
          description
              "Enable/disable LLDP on a system wide level";
        }

        container tx-credit-max {
          description
              "Configure the maximum consecutive LLDPDUs transmitted.";
          leaf count {
            type int32 {
              range "1..100";
            }
            default 5;
            description
                "[1..100] - Default: 5";
          } //count

        } //container tx-credit-max

        container tx-hold-multiplier {
          description
              "Configure multiplier of tx-interval";
          leaf multiplier {
            type int32 {
              range "2..10";
            }
            default 4;
            description
                "[2..10] - Default: 4";
          } //multiplier

        } //container tx-hold-multiplier

        container tx-interval {
          description
              "Configure LLDP transmit interval time.";
          leaf interval {
            type int32 {
              range "5..32768";
            }
            default 30;
            description
                "[5..32768] - default: 30";
          } //interval

        } //container tx-interval

      } //container lldp

      container load-balancing {
        description
            "Context to configure hashing commands at system level";
        container hash-poly {
          description
              "Configure polynomials for ECMP and LAG hashing";
          leaf ecmp {
            type enumeration {
              enum poly1;
              enum poly2;
              enum poly3;
              enum poly4;
              enum poly5;
              enum poly6;
            }
            description
                "Attribute polynomial-value for hash-poly";
          } //ecmp

          leaf lag {
            type enumeration {
              enum poly1;
              enum poly2;
              enum poly3;
              enum poly4;
              enum poly5;
              enum poly6;
            }
          } //lag

        } //container hash-poly

        leaf l2tp-load-balancing {
          type boolean;
          description
              "Enable/disable use of the L2TP header in the load-balancing hash algorithm";
        }

        leaf l4-load-balancing {
          type boolean;
          description
              "Configure system-wide L4 load balancing";
        }

        container lsr-load-balancing {
          description
              "Configure system wide LSR load balancing";
          leaf hashing-algorithm {
            type enumeration {
              enum lbl-only;
              enum lbl-ip;
              enum ip-only;
              enum eth-encap-ip;
              enum lbl-ip-l4-teid;
            }
            description
                "lbl-only | lbl-ip | ip-only | eth-encap-ip | lbl-ip-l4-teid";
          } //hashing-algorithm

        } //container lsr-load-balancing

        leaf mc-enh-load-balancing {
          type boolean;
          description
              "Configure system wide multicast enhanced load balancing";
        }

        leaf service-id-lag-hashing {
          type boolean;
          description
              "Enable/Disable enhanced VLL LAG service id hashing";
        }

        leaf system-ip-load-balancing {
          type boolean;
          description
              "Configure the inclusion of the system IP address in the ECMP and LAG load 
               balancing calculation";
        }

      } //container load-balancing

      container login-control {
        description
            "Configure login control parameters for console telnet and FTP sessions";
        leaf exponential-backoff {
          type boolean;
          description
              "Configure login exponential-backoff to deter brute force attack";
        }

        container idle-timeout {
          description
              "Configure idle-timeout for console, telnet, SSH and FTP sessions";
          leaf minutes {
            type uint32 {
              range "1..1440";
            }
          } //minutes

          leaf disable {
            type boolean;
          } //disable

        } //container idle-timeout

        leaf login-banner {
          type boolean;
          description
              "Enable/disable display of login banner";
        }

        container motd {
          description
              "Configure message of the day printed after a successful login";
          leaf url {
            type string {
              length "1..180";
            }
            description
                "[180 chars max]";
          } //url

          leaf text {
            type string {
              length "1..900";
            }
          } //text

        } //container motd

        container pre-login-message {
          description
              "Configure message prior to login";
          leaf name {
            type boolean;
          } //name

          leaf login-text-string {
            type string {
              length "1..900";
            }
          } //login-text-string

        } //container pre-login-message

        container ftp {
          description
              "Configure FTP login control parameters";
          container inbound-max-sessions {
            description
                "Configure max number of concurrent inbound FTP sessions";
            leaf value {
              type uint64 {
                range "0..5";
              }
              description
                  "[0..5] default = 3";
            } //value

          } //container inbound-max-sessions

        } //container ftp

        container login-scripts {
          description
              "Configure login scripts";
          container global {
            description
                "Configure a global login script";
            leaf file-url {
              type string {
                length "1..180";
              }
              description
                  "Attribute file-url for global";
            } //file-url

          } //container global

          container per-user {
            description
                "Configure the per-user login script";
            leaf user-directory {
              type string {
                length "1..255";
              }
              description
                  "Attribute dir-url for per-user";
            } //user-directory

            leaf file-name {
              type string {
                length "1..180";
              }
            } //file-name

          } //container per-user

        } //container login-scripts

        container ssh {
          description
              "Configure SSH login control parameters";
          leaf disable-graceful-shutdown {
            type boolean;
            description
                "Disable/Enable graceful shutdown of SSH sessions";
          }

          container inbound-max-sessions {
            description
                "Configure max number of inbound SSH sessions from the combined SSH/Telnet 
                 session limit";
            leaf value {
              type string;
              description
                  "Attribute number-of-sessions for inbound-max-sessions";
            } //value

          } //container inbound-max-sessions

          container outbound-max-sessions {
            description
                "Configure max number of concurrent outbound SSH sessions";
            leaf time {
              type uint32 {
                range "0..15";
              }
              description
                  "[0..15] default = 5";
            } //time

          } //container outbound-max-sessions

          container ttl-security {
            description
                "Configure TTL security parameters for incoming packets";
            leaf min-ttl-value {
              type int32 {
                range "1..255";
              }
            } //min-ttl-value

          } //container ttl-security

        } //container ssh

        container telnet {
          description
              "Configure telnet login control parameters";
          leaf enable-graceful-shutdown {
            type boolean;
            description
                "Enable/disable graceful shutdown of telnet sessions";
          }

          container inbound-max-sessions {
            description
                "Configure max number of inbound Telnet sessions from the combined SSH/Telnet 
                 session limit";
            leaf value {
              type string;
              description
                  "Attribute number-of-sessions for inbound-max-sessions";
            } //value

          } //container inbound-max-sessions

          container outbound-max-sessions {
            description
                "Configure max number of concurrent outbound telnet sessions";
            leaf time {
              type uint64 {
                range "0..15";
              }
              description
                  "[0..15] default = 5";
            } //time

          } //container outbound-max-sessions

          container ttl-security {
            description
                "Configure TTL security parameters for incoming packets";
            leaf min-ttl-value {
              type int32 {
                range "1..255";
              }
            } //min-ttl-value

          } //container ttl-security

        } //container telnet

      } //container login-control

      container management {
        status "obsolete";
        description
            "Configure network management protocol capabilities";
        leaf cli {
          type boolean;
          description
              "keyword - the management protocol";
        } //cli

        container configuration {
          status "obsolete";
          description
              "Configure network management protocol configuration";
          leaf immediate {
            type boolean;
            status "obsolete";
            description
                "Enable/disable CLI commands in the 'configure' branch from making changes to 
                 the running configuration";
          }

        } //container configuration

      } //container management

      container management-interface {
        description
            "Configure network management interface capabilities";
        container configuration-mode {
          description
              "Provision the management interface configuration mode of the system";
          leaf configuration-mode-id {
            type enumeration {
              enum classic;
              enum mixed;
              enum model-driven;
            }
          } //configuration-mode-id

        } //container configuration-mode

        container schema-path {
          description
              "Location of schema files used by the system";
          leaf url-string {
            type string {
              length "1..180";
            }
          } //url-string

        } //container schema-path

        container cli {
          description
              "Configure CLI capabilities";
          container cli-engine {
            description
                "System-wide CLI engine access configuration";
            leaf-list cli-engine-id {
              type enumeration {
                enum classic-cli;
                enum md-cli;
              }
              max-elements 2;
            } //cli-engine-id

            leaf cli-engine-id-2 {
              type enumeration {
                enum classic-cli;
                enum classic-cli-exclusive;
                enum md-cli;
              }
              status "obsolete";
            } //cli-engine-id-2

          } //container cli-engine

          container classic-cli {
            description
                "Configure classic CLI capabilities";
            leaf allow-immediate {
              type boolean;
              description
                  "Enable/disable CLI commands in the 'configure' branch from making changes to 
                   the running configuration";
            }

          } //container classic-cli

          container md-cli {
            description
                "Configure MD CLI capabilities";
            leaf auto-config-save {
              type boolean;
              description
                  "Enable / disable automatic save of configuration as part of a commit operation";
            }

            leaf command-accounting-during-load {
              type boolean;
              description
                  "Perform remote command accounting during a load or rollback operation";
            }

            container environment {
              description
                  "Configure MD CLI session environment default configuration";
              leaf more {
                type boolean;
                description
                    "Configure paging of the output text";
              }

              container time-display {
                description
                    "Specify whether timestamp should be displayed in UTC or local time";
                leaf time-display-id {
                  type enumeration {
                    enum local;
                    enum utc;
                  }
                  default "local";
                } //time-display-id

              } //container time-display

              container time-format {
                description
                    "Time format to display date and time";
                leaf time-format-id {
                  type enumeration {
                    enum iso-8601;
                    enum rfc-1123;
                    enum rfc-3339;
                  }
                  default "rfc-3339";
                } //time-format-id

              } //container time-format

              container command-completion {
                description
                    "Configure keystrokes to trigger command completion";
                leaf enter {
                  type boolean;
                  description
                      "Enable/Disable completion on enter character";
                }

                leaf space {
                  type boolean;
                  description
                      "Enable/Disable completion on space character";
                }

                leaf tab {
                  type boolean;
                  description
                      "Enable/Disable completion on tab character";
                }

              } //container command-completion

              container console {
                description
                    "Configure console parameters";
                container length {
                  description
                      "Set number of lines displayed on the screen";
                  leaf lines {
                    type uint32 {
                      range "24..512";
                    }
                    default 24;
                  } //lines

                } //container length

                container width {
                  description
                      "Set number of columns displayed on the screen";
                  leaf width {
                    type uint32 {
                      range "80..512";
                    }
                    default 80;
                  } //width

                } //container width

              } //container console

              container message-severity-level {
                description
                    "Configure messages severity";
                container cli {
                  description
                      "Specifies the threshold for CLI messages";
                  leaf cli-id {
                    type enumeration {
                      enum warning;
                      enum info;
                    }
                    default "info";
                  } //cli-id

                } //container cli

              } //container message-severity-level

              container progress-indicator {
                description
                    "Settings for progress indicator during command execution";
                container delay {
                  description
                      "Delay before progress indicator is displayed in MD-CLI.";
                  leaf interval {
                    type uint32 {
                      range "0..10000";
                    }
                    default 1000;
                  } //interval

                } //container delay

                leaf shutdown {
                  type boolean;
                  description
                      "Controls whether progress indicator during command execution is active.";
                }

                container type {
                  description
                      "Type of the progress indicator used in the MD-CLI.";
                  leaf indicator-type {
                    type enumeration {
                      enum dots;
                    }
                    default "dots";
                  } //indicator-type

                } //container type

              } //container progress-indicator

              container prompt {
                description
                    "Configure content of displayed prompt";
                leaf context {
                  type boolean;
                  description
                      "Enable/Disable displaying of the current command context";
                }

                leaf newline {
                  type boolean;
                  description
                      "Enable/Disable displaying of a newline before the first prompt line";
                }

                leaf timestamp {
                  type boolean;
                  description
                      "Enable/Disable displaying of a timestamp before the first prompt line";
                }

                leaf uncommitted-changes-indicator {
                  type boolean;
                  description
                      "Enable/Disable displaying of the indicator of uncommitted changes";
                }

              } //container prompt

            } //container environment

          } //container md-cli

        } //container cli

        container remote-management {
          description
              "Configure remote-management parameters";
          leaf allow-unsecure-connection {
            type boolean;
            description
                "Enable/disable manager encryption";
          }

          container client-tls-profile {
            description
                "TLS profile used by manager";
            leaf name {
              type string;
            } //name

          } //container client-tls-profile

          container connection-timeout {
            description
                "The amount of time a manager cannot be reached before it is declared down.";
            leaf connection-timeout-id {
              type uint32 {
                range "1..3600";
              }
              default 60;
            } //connection-timeout-id

          } //container connection-timeout

          container device-label {
            description
                "Provide a label for this device to the manager. Used to mark nodes common in 
                 nature.";
            leaf name {
              type string;
            } //name

          } //container device-label

          container device-name {
            description
                "Unique identifier of this device. If not configured default system name is 
                 used.";
            leaf name {
              type string;
            } //name

          } //container device-name

          container hello-interval {
            description
                "Number of minutes between hellos.";
            leaf hello-interval-id {
              type uint32 {
                range "10..3600";
              }
              default 10;
            } //hello-interval-id

          } //container hello-interval

          container router {
            description
                "router-instance or vprn service-name to source connections to managers from";
            leaf router-instance {
              type string {
                length "1..32";
              }
              default "management";
            } //router-instance

            leaf service {
              type string;
            } //service

          } //container router

          leaf shutdown {
            type boolean;
            description
                "enable/disable remote-management";
          }

          container source-address {
            description
                "IP address used to access this device.";
            leaf ip-address {
              type inet:ip-address;
              description
                  "Attribute ip-address for source-address";
            } //ip-address

          } //container source-address

          container source-port {
            description
                "TCP port used to access this device.";
            leaf grpc {
              type boolean;
            } //grpc

            leaf port {
              type int32 {
                range "1..65535";
              }
            } //port

          } //container source-port

          list manager {
            key "manager-name";
            description
                "Configure manager";
            leaf manager-name {
              type string;
            } //manager-name

            leaf allow-unsecure-connection {
              type boolean;
              description
                  "Enable/disable manager encryption";
            }

            container client-tls-profile {
              description
                  "TLS profile used by manager";
              leaf name {
                type string;
              } //name

            } //container client-tls-profile

            container connection-timeout {
              description
                  "The amount of time a manager cannot be reached before it is declared down.";
              leaf connection-timeout-id {
                type uint32 {
                  range "1..3600";
                }
              } //connection-timeout-id

            } //container connection-timeout

            container description {
              description
                  "Description of the manager";
              leaf description-string {
                type string {
                  length "1..80";
                }
              } //description-string

            } //container description

            container device-label {
              description
                  "Provide a label for this device to the manager. Used to mark nodes common in 
                   nature.";
              leaf name {
                type string;
              } //name

            } //container device-label

            container device-name {
              description
                  "Unique identifier of this device. If not configured default system name is 
                   used.";
              leaf name {
                type string;
              } //name

            } //container device-name

            container manager-address {
              description
                  "Configure manager-address";
              leaf ip-address-fqdn {
                type string {
                  length "1..255";
                }
                description
                    "Attribute ip-address|fqdn for manager-address";
              } //ip-address-fqdn

            } //container manager-address

            container manager-port {
              description
                  "Configure manager port";
              leaf port {
                type int32 {
                  range "1..65535";
                }
                default 57400;
              } //port

            } //container manager-port

            container router {
              description
                  "router-instance or vprn service-name to source connections to managers from";
              leaf router-instance {
                type string {
                  length "1..32";
                }
              } //router-instance

              leaf service {
                type string;
              } //service

            } //container router

            leaf shutdown {
              type boolean;
              description
                  "Enable/disable remote-management manager";
            }

            container source-address {
              description
                  "IP address used to access this device.";
              leaf ip-address {
                type inet:ip-address;
                description
                    "Attribute ip-address for source-address";
              } //ip-address

            } //container source-address

            container source-port {
              description
                  "TCP port used to access this device.";
              leaf grpc {
                type boolean;
              } //grpc

              leaf port {
                type int32 {
                  range "0..65535";
                }
              } //port

            } //container source-port

          } //list manager

        } //container remote-management

        container yang-modules {
          description
              "Configure yang module parameters";
          leaf base-r13-modules {
            type boolean;
            description
                "enable or disable publishing base release 13 yang modules";
          }

          leaf nokia-combined-modules {
            type boolean;
            description
                "enable or disable publishing combined Nokia yang modules";
          }

          leaf nokia-modules {
            type boolean;
            description
                "enable or disable publishing Nokia yang modules";
          }

          container nmda {
            description
                "Configure Network Management Datastores Architecture support";
            leaf nmda-support {
              type boolean;
              description
                  "Enable or Disable Network Management Datastores Architecture support";
            }

          } //container nmda

        } //container yang-modules

      } //container management-interface

      container netconf {
        description
            "Configure Netconf parameters";
        leaf auto-config-save {
          type boolean;
          description
              "Enable / disable automatic save of configuration as part of a commit operation";
        }

        container port {
          description
              "Configure port on which the server is listening for connections";
          leaf port {
            type enumeration {
              enum 22;
              enum 830;
            }
            default 830;
          } //port

        } //container port

        leaf shutdown {
          type boolean;
          description
              "start/stop NETCONF server";
        }

        container capabilities {
          description
              "Configure netconf capabilities parameters";
          leaf candidate {
            type boolean;
            description
                "enable or disable publishing netconf candidate capability";
          }

          leaf writable-running {
            type boolean;
            description
                "enable or disable publishing netconf writable-running capability";
          }

        } //container capabilities

        container yang-modules {
          status "obsolete";
          description
              "Configure netconf yang-module parameters";
          leaf base-r13-modules {
            type boolean;
            status "obsolete";
            description
                "enable or disable publishing netconf base release 13 yang modules";
          }

          leaf nokia-modules {
            type boolean;
            status "obsolete";
            description
                "enable or disable publishing netconf nokia yang modules";
          }

        } //container yang-modules

      } //container netconf

      container network-element-discovery {
        description
            "Configure network element discovery parameters";
        leaf generate-traps {
          type boolean;
          description
              "Enable/disable generation of NE discovery traps";
        }

        list profile {
          key "name";
          description
              "Configure NE profile parameters";
          leaf name {
            type string;
          } //name

          container neid {
            description
                "Configure the network element identifier of the advertised node";
            leaf hex-string {
              type string;
              description
                  "[0x10001..0xFEFFFE]";
            } //hex-string

          } //container neid

          container platform-type {
            description
                "Configure the platform name and chassis type to be advertised";
            leaf platform-type-string {
              type string {
                length "1..255";
              }
            } //platform-type-string

          } //container platform-type

          container system-mac {
            description
                "Configure the MAC address of the advertised node";
            leaf mac-address {
              type alu:ieee-address;
              description
                  "xx:xx:xx:xx:xx:xx or xx-xx-xx-xx-xx-xx";
            } //mac-address

          } //container system-mac

          container vendor-id {
            description
                "Configure the vendor identifier to be advertised";
            leaf vendor-id-string {
              type string {
                length "1..255";
              }
            } //vendor-id-string

          } //container vendor-id

          container neip {
            description
                "Configure network element IP address parameters";
            container ipv4 {
              description
                  "Configure the neip IPv4 address of the advertised node";
              leaf ip-address {
                type inet:ip-address;
              } //ip-address

            } //container ipv4

            container ipv6 {
              description
                  "Configure the neip IPv6 address of the advertised node";
              leaf ipv6-address {
                type inet:ipv6-address;
                description
                    "x:x:x:x:x:x:x:x (eight 16-bit pieces) 
                     x:x:x:x:x:x:d.d.d.d 
                     x [0..FFFF]H 
                     d [0..255]D";
              } //ipv6-address

            } //container ipv6

          } //container neip

        } //list profile

      } //container network-element-discovery

      container oes {
        status "obsolete";
        description
            "Configure Optical Extension Shelf capabilities";
        container cf-cache {
          description
              "Configure the compact flash (cf) location that contains the OES cache";
          leaf cflash-id {
            type enumeration {
              enum cf1;
              enum cf2;
              enum cf3;
            }
            default "cf3";
            description
                "cf1|cf2|cf3 - Default:cf3";
          } //cflash-id

        } //container cf-cache

        container software-repository {
          description
              "Configure which software repository is used for the OES";
          leaf repository-name {
            type string {
              length "1..32";
            }
          } //repository-name

        } //container software-repository

        container control-communications {
          description
              "Configure OES control communications";
          container oes-address {
            description
                "Configure the IP address of the OES master shelf";
            leaf ip-address {
              type inet:ip-address;
            } //ip-address

          } //container oes-address

          container retry-limit {
            description
                "Configure the retry limit for establishing communications with the OES chassis";
            leaf limit {
              type uint32 {
                range "0..7";
              }
              default 2;
              description
                  "[0..7] - Default: 2";
            } //limit

          } //container retry-limit

          container router {
            description
                "Configure the router instance used for OES control communications";
            leaf cpm-vr-name {
              type string {
                length "1..32";
              }
            } //cpm-vr-name

          } //container router

          container timeout {
            description
                "Configure the timeout for communications with OES chassis";
            leaf seconds {
              type uint32 {
                range "5..3600";
              }
              default 20;
              description
                  "[5..3600] - Default: 20";
            } //seconds

          } //container timeout

        } //container control-communications

      } //container oes

      container persistence {
        description
            "Configure persistence applications";
        container ancp {
          description
              "Configure ANCP persistence parameters";
          container description {
            description
                "Configures a description related to ANCP persistence";
            leaf description-string {
              type string {
                length "1..80";
              }
            } //description-string

          } //container description

          container location {
            description
                "Configures the location of the persistence data";
            leaf cflash-id {
              type string;
              description
                  "Attribute cflash-id for location";
            } //cflash-id

          } //container location

        } //container ancp

        container application-assurance {
          description
              "Configure application assurance persistence parameters";
          container description {
            description
                "Configures a description related to application assurance persistence";
            leaf description-string {
              type string {
                length "1..80";
              }
            } //description-string

          } //container description

          container location {
            description
                "Configures the location of the persistence data";
            leaf cflash-id {
              type string;
              description
                  "Attribute cflash-id for location";
            } //cflash-id

          } //container location

        } //container application-assurance

        container dhcp-server {
          description
              "Configure DHCP server persistence parameters";
          container description {
            description
                "Configures a description related to DHCP server persistence";
            leaf description-string {
              type string {
                length "1..80";
              }
            } //description-string

          } //container description

          container location {
            description
                "Configures the location of the persistence data";
            leaf cflash-id {
              type string;
              description
                  "Attribute cflash-id for location";
            } //cflash-id

          } //container location

        } //container dhcp-server

        container nat-port-forwarding {
          description
              "Configure NAT port forwarding persistence parameters";
          container description {
            description
                "Configures a description related to NAT port forwarding persistence";
            leaf description-string {
              type string {
                length "1..80";
              }
            } //description-string

          } //container description

          container location {
            description
                "Configures the location of the persistence data";
            leaf cflash-id {
              type string;
              description
                  "Attribute cflash-id for location";
            } //cflash-id

          } //container location

        } //container nat-port-forwarding

        container options {
          description
              "Configure persistence options";
          container dhcp-leasetime-threshold {
            description
                "Configure the threshold time for DHCP leases to be eligible for persistence";
            leaf days {
              type uint32 {
                range "0..7305";
              }
            } //days

            leaf hrs {
              type uint32 {
                range "0..23";
              }
            } //hrs

            leaf min {
              type uint32 {
                range "0..59";
              }
            } //min

            leaf sec {
              type uint32 {
                range "0..59";
              }
            } //sec

          } //container dhcp-leasetime-threshold

        } //container options

        container python-policy-cache {
          description
              "Configure Python policy cache persistency parameters";
          container description {
            description
                "Configures a description related to Python policy cache persistence";
            leaf description-string {
              type string {
                length "1..80";
              }
            } //description-string

          } //container description

          container location {
            description
                "Configure the flash device on a CPM card where the data for handling the 
                 python persistence is stored.";
            leaf cflash-id {
              type string;
              description
                  "Attribute cflash-id for location";
            } //cflash-id

          } //container location

        } //container python-policy-cache

        container subscriber-mgmt {
          description
              "Configure subscriber management persistence parameters";
          container description {
            description
                "Configures a description related to subscriber management persistence";
            leaf description-string {
              type string {
                length "1..80";
              }
            } //description-string

          } //container description

          container location {
            description
                "Configures the location of the persistence data";
            leaf cflash-id {
              type string;
              description
                  "Attribute cflash-id for location";
            } //cflash-id

          } //container location

        } //container subscriber-mgmt

      } //container persistence

      container port-topology {
        description
            "Configure system port topologies";
        list port {
          key "port-id";
          description
              "Configure the ports";
          leaf port-id {
            type string {
              length "1..17";
            }
            description
                "Attribute port-id for port";
          } //port-id

          leaf to {
            type string {
              length "1..17";
            }
            description
                "port-id";
          } //to

        } //list port

      } //container port-topology

      uses "conf-sys-pwrmgmt-r13:alu-conf-sys-pwrmgmt-r13";
      container power-module {
        description
            "Power Module configuration.";
        leaf power-module-id {
          type uint32 {
            range "1..12";
          }
          description
              "Attribute power-module-id for power-module";
        } //power-module-id

        container power-module-type {
          description
              "Administratively provision the Power Module.";
          leaf power-module-type {
            type string {
            }
            description
                "Attribute power-module-type for power-module-type";
          } //power-module-type

        } //container power-module-type

        leaf shutdown {
          type boolean;
          description
              "Administratively enable/disable the Power Module.";
        }

      } //container power-module

      list power-shelf {
        key "power-shelf-id chassis";
        description
            "Power Shelf configuration";
        leaf power-shelf-id {
          type uint32 {
            range "1..2";
          }
        } //power-shelf-id

        leaf chassis {
          type string;
        } //chassis

        container description {
          description
              "Configure the description of the Power Shelf.";
          leaf description-string {
            type string {
              length "1..80";
            }
          } //description-string

        } //container description

        container power-shelf-type {
          description
              "Administratively provision the Power Shelf.";
          leaf power-shelf-type {
            type string {
            }
          } //power-shelf-type

        } //container power-shelf-type

        leaf shutdown {
          type boolean;
          description
              "Administratively enable/disable the Power Shelf.";
        }

        container power-module {
          description
              "Power Module configuration.";
          leaf power-module-id {
            type uint32 {
              range "1..10";
            }
            description
                "Attribute power-module-id for power-module";
          } //power-module-id

          container power-module-type {
            description
                "Administratively provision the Power Module.";
            leaf power-module-type {
              type string {
              }
              description
                  "Attribute power-module-type for power-module-type";
            } //power-module-type

          } //container power-module-type

          leaf shutdown {
            type boolean;
            description
                "Administratively enable/disable the Power Module.";
          }

        } //container power-module

      } //list power-shelf

      uses "conf-sys-ptp-r13:alu-conf-sys-ptp-r13";
      container resource {
        description
            "Configure system-wide resource parameters";
        list ecmp-profile {
          key "id";
          description
              "Configure system ecmp resource";
          leaf id {
            type uint16 {
              range "1..2";
            }
          } //id

          leaf type {
            type enumeration {
              enum mpls;
              enum ip;
            }
          } //type

          leaf links {
            type uint32 {
              range "1..16";
            }
            description
                "[1..16]";
          } //links

          leaf groups {
            type uint32 {
              range "1..2048";
            }
            description
                "Attribute groups for ecmp-profile";
          } //groups

        } //list ecmp-profile

      } //container resource

      container rollback {
        description
            "Configure general rollback parameters";
        container local-max-checkpoints {
          description
              "Configures the maximum rollback files on compact flash";
          leaf number-of-files {
            type uint32 {
              range "1..50";
            }
          } //number-of-files

        } //container local-max-checkpoints

        container remote-max-checkpoints {
          description
              "Configures the maximum rollback files saved at a remote location (ftp)";
          leaf number-of-files {
            type uint32 {
              range "1..200";
            }
          } //number-of-files

        } //container remote-max-checkpoints

        container rescue-location {
          description
              "Configures the location of the rollback rescue file";
          leaf file-url {
            type string {
            }
            description
                "Attribute file-url for rescue-location";
          } //file-url

        } //container rescue-location

        container rollback-location {
          description
              "Configures the location and filename of the rollback checkpoint files";
          leaf file-url {
            type string {
            }
            description
                "Attribute file-url for rollback-location";
          } //file-url

        } //container rollback-location

      } //container rollback

      container satellite {
        description
            "Configure satellite parameters";
        container file-transfer {
          description
              "Configure satellite secure file transfer";
          leaf-list file-transfer-mode {
            type enumeration {
              enum ftp;
              enum scp;
            }
            max-elements 2;
          } //file-transfer-mode

        } //container file-transfer

        list eth-sat {
          key "sat-id";
          description
              "Configure the Ethernet satellite parameters";
          leaf sat-id {
            type uint32 {
              range "1..20";
            }
          } //sat-id

          container client-down-delay {
            description
                "Configure the delay between the last available uplink becoming unavailable and 
                 disabling associated client ports";
            leaf client-down-delay {
              type int32 {
                range "0..1800";
              }
            } //client-down-delay

          } //container client-down-delay

          container description {
            description
                "Configure the description of the Ethernet satellite";
            leaf description-string {
              type string {
                length "1..80";
              }
            } //description-string

          } //container description

          leaf enable-console-access {
            type boolean;
            description
                "Enable/disable console access on the Ethernet satellite";
          }

          list feature {
            key "feature-name";
            description
                "Enable/disable a feature on the Ethernet satellite";
            leaf feature-name {
              type enumeration {
                enum local-forward;
                enum ptp-tc;
              }
            } //feature-name

          } //list feature

          container mac-address {
            description
                "Configure the MAC address of the Ethernet satellite";
            leaf mac-address {
              type yang:mac-address;
            } //mac-address

          } //container mac-address

          container port-map {
            description
                "Configure the client port to uplink port mapping";
            leaf client-port-id {
              type string {
                length "1..17";
              }
              description
                  "Attribute client-port-id for port-map";
            } //client-port-id

            leaf primary {
              type string {
                length "1..17";
              }
              description
                  "Attribute primary-uplink-port-id for port-map";
            } //primary

            leaf secondary {
              type string {
                length "1..17";
              }
              description
                  "Attribute secondary-uplink-port-id for port-map";
            } //secondary

            leaf system-default {
              type boolean;
              description
                  "keyword";
            } //system-default

          } //container port-map

          leaf ptp-tc {
            type boolean;
            description
                "Enabled/disable PTP transparent clock on the Ethernet satellite";
          }

          container sat-type {
            description
                "Provision the Ethernet satellite type";
            leaf sat-type {
              type string {
              }
              description
                  "Attribute sat-type for sat-type";
            } //sat-type

            leaf port-template {
              type string {
                length "1..32";
              }
            } //port-template

          } //container sat-type

          leaf shutdown {
            type boolean;
            description
                "Administratively enable/disable the Ethernet satellite";
          }

          container software-repository {
            description
                "Configure which software repository is used for the Ethernet satellite";
            leaf repository-name {
              type string {
                length "1..32";
              }
            } //repository-name

          } //container software-repository

          leaf sync-e {
            type boolean;
            description
                "Enable/disable SyncE on the Ethernet satellite";
          }

        } //list eth-sat

        list local-forward {
          key "local-forward-id";
          description
              "Configure satellite local forward services";
          leaf local-forward-id {
            type uint32 {
              range "1..10240";
            }
          } //local-forward-id

          container description {
            description
                "Configure the description of the local forward service";
            leaf description-string {
              type string {
                length "1..80";
              }
            } //description-string

          } //container description

          leaf shutdown {
            type boolean;
            description
                "Administratively enable/disable the local forward service";
          }

          list sap {
            key "sap-id";
            description
                "Configure SAPs in the local forward service";
            leaf sap-id {
              type string;
              description
                  "Attribute sap-id for sap";
            } //sap-id

            container description {
              description
                  "Configure the description of the SAP in a local forward service";
              leaf description-string {
                type string {
                  length "1..80";
                }
              } //description-string

            } //container description

            leaf shutdown {
              type boolean;
              description
                  "Administratively enable/disable the SAP in a local forward service";
            }

          } //list sap

        } //list local-forward

        list port-template {
          key "template-name";
          description
              "Configure satellite port templates";
          leaf template-name {
            type string {
              length "1..32";
            }
          } //template-name

          leaf sat-type {
            type string {
            }
            description
                "Attribute sat-type for port-template";
          } //sat-type

          container description {
            description
                "Configure the description of the Ethernet satellite port template";
            leaf description-string {
              type string {
                length "1..80";
              }
            } //description-string

          } //container description

          leaf shutdown {
            type boolean;
            description
                "Administratively enable/disable the Ethernet satellite port template";
          }

          container port {
            description
                "Configure attributes of ports in the template";
            leaf port-id {
              type string {
                length "1..17";
              }
            } //port-id

            container role {
              description
                  "Configure the role of the port";
              leaf role-type {
                type enumeration {
                  enum none;
                  enum uplink;
                  enum client;
                  enum system-default;
                }
              } //role-type

            } //container role

            container uplink {
              description
                  "Configure the uplink of the port";
              leaf port-id {
                type string {
                  length "1..17";
                }
              } //port-id

              leaf system-default {
                type boolean;
              } //system-default

              leaf none {
                type boolean;
              } //none

            } //container uplink

          } //container port

        } //list port-template

        list tdm-sat {
          key "sat-id";
          description
              "Configure the Time Division Multiplexing satellite parameters";
          leaf sat-id {
            type uint32 {
              range "1..20";
            }
          } //sat-id

          container description {
            description
                "Configure the description of the TDM satellite";
            leaf description-string {
              type string {
                length "1..80";
              }
            } //description-string

          } //container description

          container mac-address {
            description
                "Configure the MAC address of the TDM satellite";
            leaf mac-address {
              type yang:mac-address;
            } //mac-address

          } //container mac-address

          container sat-type {
            description
                "Provision the TDM satellite type";
            leaf sat-type {
              type string {
              }
              description
                  "Attribute sat-type for sat-type";
            } //sat-type

          } //container sat-type

          leaf shutdown {
            type boolean;
            description
                "Administratively enable/disable the TDM satellite";
          }

          container software-repository {
            description
                "Configure which software repository is used for the TDM satellite";
            leaf repository-name {
              type string {
                length "1..32";
              }
            } //repository-name

          } //container software-repository

          leaf sync-e {
            type boolean;
            description
                "Enable/disable SyncE on the TDM satellite";
          }

        } //list tdm-sat

      } //container satellite

      container script-control {
        description
            "Configure command script parameters";
        list script {
          key "script-name owner";
          description
              "Configure script";
          leaf script-name {
            type string {
              length "1..32";
            }
          } //script-name

          leaf owner {
            type string {
              length "1..32";
            }
            description
                "[32 chars max] Default - \"TiMOS CLI\"";
          } //owner

          container description {
            description
                "Description for this script";
            leaf description-string {
              type string {
                length "1..80";
              }
              description
                  "[80 chars max]";
            } //description-string

          } //container description

          container location {
            description
                "Location of script to be scheduled";
            leaf file-url {
              type string {
                length "1..255";
              }
              description
                  "Attribute file-url for location";
            } //file-url

          } //container location

          leaf shutdown {
            type boolean;
            description
                "Administratively enable/disable the script";
          }

        } //list script

        list script-policy {
          key "policy-name owner";
          description
              "Configure script-policy parameters for a script";
          leaf policy-name {
            type string {
              length "1..32";
            }
          } //policy-name

          leaf owner {
            type string {
              length "1..32";
            }
            description
                "[32 chars max] Default - \"TiMOS CLI\"";
          } //owner

          container expire-time {
            description
                "Maximum amount of time to keep the run history status entry from a script run";
            leaf seconds {
              type uint32 {
                range "0..21474836";
              }
              default 3600;
              description
                  "[0..21474836] Default: 3600 (1 hour)";
            } //seconds

            leaf forever {
              type boolean;
            } //forever

          } //container expire-time

          container lifetime {
            description
                "Maximum amount of time the script may run";
            leaf seconds {
              type uint32 {
                range "0..21474836";
              }
              default 3600;
              description
                  "[0..21474836] Default: 3600 (1 hour)";
            } //seconds

            leaf forever {
              type boolean;
            } //forever

          } //container lifetime

          leaf lock-override {
            type boolean;
            description
                "Force explicit lock break for script";
          }

          container max-completed {
            description
                "Maximum number of script run history status entries to keep";
            leaf unsigned {
              type uint32 {
                range "1..1500";
              }
              default 1;
              description
                  "[1..1500] Default - 1";
            } //unsigned

          } //container max-completed

          container results {
            description
                "Location to receive CLI output display of a script run";
            leaf file-url {
              type string {
                length "1..255";
              }
              description
                  "Attribute file-url for results";
            } //file-url

          } //container results

          container script {
            description
                "Script to run";
            leaf script-name {
              type string {
                length "1..32";
              }
            } //script-name

            leaf owner {
              type string {
                length "1..32";
              }
              default "TiMOS CLI";
              description
                  "[32 chars max] Default - \"TiMOS CLI\"";
            } //owner

          } //container script

          leaf shutdown {
            type boolean;
            description
                "Administratively enable/disable script-policy";
          }

        } //list script-policy

      } //container script-control

      uses "conf-sys-sec-r13:alu-conf-sys-sec-r13";
      container snmp {
        description
            "Configure general SNMP parameters";
        container engineID {
          description
              "Set/reset the SNMP Engine ID to uniquely identify the SNMPv3 node";
          leaf engine-id {
            type string;
            description
                "[10..64 hex digits]";
          } //engine-id

        } //container engineID

        container general-port {
          description
              "Port number to be used to send general SNMP messages";
          leaf port {
            type int32 {
              range "0..65535";
            }
          } //port

        } //container general-port

        container packet-size {
          description
              "Configure the maximum SNMP packet size";
          leaf bytes {
            type uint32 {
              range "484..9216";
            }
          } //bytes

        } //container packet-size

        leaf shutdown {
          type boolean;
          description
              "Start/shutdown the SNMP daemon";
        }

        container streaming {
          description
              "Configure general streaming parameters";
          leaf shutdown {
            type boolean;
            description
                "Start/shutdown the streaming daemon";
          }

        } //container streaming

      } //container snmp

      list software-repository {
        key "repository-name";
        description
            "Configure system software repository parameters";
        leaf repository-name {
          type string {
            length "1..32";
          }
        } //repository-name

        container description {
          description
              "Configure the description of the software repository";
          leaf description-string {
            type string {
              length "1..80";
            }
          } //description-string

        } //container description

        container primary-location {
          description
              "Configure the primary location of the directory that contains the run-time 
               images";
          leaf file-url {
            type string {
              length "1..180";
            }
            description
                "Attribute file-url for primary-location";
          } //file-url

        } //container primary-location

        container secondary-location {
          description
              "Configure the secondary location of the directory that contains the run-time 
               images";
          leaf file-url {
            type string {
              length "1..180";
            }
            description
                "Attribute file-url for secondary-location";
          } //file-url

        } //container secondary-location

        container tertiary-location {
          description
              "Configure the tertiary location of the directory that contains the run-time 
               images";
          leaf file-url {
            type string {
            }
            description
                "Attribute file-url for tertiary-location";
          } //file-url

        } //container tertiary-location

      } //list software-repository

      container switch-fabric {
        description
            "Configure switch-fabric parameters";
        container sfm-loss-threshold {
          description
              "Configure the number of SFMs which are allowed to fail before the system goes 
               into SFM overload state";
          leaf num-sfm {
            type uint32 {
              range "1..7";
            }
            description
                "Attribute num-sfm for sfm-loss-threshold";
          } //num-sfm

        } //container sfm-loss-threshold

        container failure-recovery {
          description
              "Configure switch fabric failure recovery parameters";
          leaf shutdown {
            type boolean;
            description
                "Administratively enable/disable the automatic switch fabric failure recovery 
                 process";
          }

        } //container failure-recovery

      } //container switch-fabric

      container sync-if-timing {
        description
            "Configure synchronous interface timing";
        leaf abort {
          type boolean;
          description
              "Discard the changes that have been made to sync interface timing during a 
               session";
        }

        leaf begin {
          type boolean;
          description
              "Switch to edit mode for sync interface timing - use commit to save or abort to 
               discard the changes made in a session";
        }

        leaf commit {
          type boolean;
          description
              "Save the changes made to sync interface timing during a session";
        }

        container ql-minimum {
          description
              "Configure the minimum quality level of the input";
          leaf ql-minimum-id {
            type enumeration {
              enum prs;
              enum stu;
              enum st2;
              enum tnc;
              enum st3e;
              enum st3;
              enum prc;
              enum ssua;
              enum ssub;
              enum sec;
              enum eec1;
              enum eec2;
            }
          } //ql-minimum-id

        } //container ql-minimum

        leaf ql-selection {
          type boolean;
          description
              "Enable/disable reference selection based on quality-level";
        }

        container ref-order {
          description
              "Priority order of timing references";
          leaf-list ref {
            type enumeration {
              enum bits;
              enum synce;
              enum ref1;
              enum ref2;
              enum ptp;
              enum gnss;
            }
            max-elements 5;
            description
                "Attribute ref for ref-order";
          } //ref

        } //container ref-order

        leaf revert {
          type boolean;
          description
              "Revert/do not revert to a higher priority re-validated reference source";
        }

        container wait-to-restore {
          description
              "Configure the wait-to-restore timer";
          leaf minutes {
            type uint32 {
              range "1..12";
            }
          } //minutes

        } //container wait-to-restore

        container bits {
          description
              "Configure parameters for the Building Integrated Timing Supply (BITS)";
          container interface-type {
            description
                "Configure the interface type of the BITS timing reference";
            leaf t1 {
              type boolean;
            } //t1

            leaf e1 {
              type boolean;
            } //e1

            leaf esf-sf {
              type enumeration {
                enum esf;
                enum sf;
              }
              description
                  "keywords";
            } //esf-sf

            leaf pcm30crc-pcm31crc {
              type enumeration {
                enum pcm30crc;
                enum pcm31crc;
              }
              description
                  "keywords";
            } //pcm30crc-pcm31crc

            leaf ds1 {
              type boolean;
            } //ds1

            leaf t2048khz-g703 {
              type boolean;
            } //t2048khz-g703

          } //container interface-type

          container ql-override {
            description
                "Override the quality level of a timing reference";
            leaf ql-override-id {
              type enumeration {
                enum prs;
                enum stu;
                enum st2;
                enum tnc;
                enum st3e;
                enum st3;
                enum prc;
                enum ssua;
                enum ssub;
                enum sec;
              }
            } //ql-override-id

          } //container ql-override

          container ssm-bit {
            description
                "Configure the sa-bit to use for conveying SSM information";
            leaf sa-bit {
              type uint32 {
                range "4..8";
              }
              description
                  "[4-8]";
            } //sa-bit

          } //container ssm-bit

          container input {
            description
                "Configure the external BITS input timing reference";
            leaf shutdown {
              type boolean;
              description
                  "Administratively shutdown the BITS input timing reference";
            }

          } //container input

          container output {
            description
                "Configure the external BITS output timing reference";
            container line-length {
              description
                  "Configure the line-length for the BITS output";
              leaf line-length-id {
                type enumeration {
                  enum 110;
                  enum 220;
                  enum 330;
                  enum 440;
                  enum 550;
                  enum 660;
                }
              } //line-length-id

            } //container line-length

            container ql-minimum {
              description
                  "Configure the minimum quality level of the BITS output";
              leaf ql-minimum-id {
                type enumeration {
                  enum prs;
                  enum stu;
                  enum st2;
                  enum tnc;
                  enum st3e;
                  enum st3;
                  enum prc;
                  enum ssua;
                  enum ssub;
                  enum sec;
                  enum eec1;
                  enum eec2;
                }
              } //ql-minimum-id

            } //container ql-minimum

            leaf shutdown {
              type boolean;
              description
                  "Administratively shutdown the BITS output timing reference";
            }

            container source {
              description
                  "Configure the source of the BITS output.";
              leaf source-id {
                type enumeration {
                  enum line-ref;
                  enum internal-clock;
                }
              } //source-id

            } //container source

            leaf squelch {
              type boolean;
              description
                  "Squelch the signal of the BITS output";
            }

          } //container output

        } //container bits

        container gnss {
          description
              "Configure parameters for the gnss timing reference";
          container ql-override {
            description
                "Override the quality level of a timing reference";
            leaf ql-override-id {
              type enumeration {
                enum prs;
                enum stu;
                enum st2;
                enum tnc;
                enum st3e;
                enum st3;
                enum prc;
                enum ssua;
                enum ssub;
                enum sec;
              }
            } //ql-override-id

          } //container ql-override

          leaf shutdown {
            type boolean;
            description
                "Administratively shutdown the timing reference";
          }

        } //container gnss

        container ptp {
          description
              "Configure parameters for Precision Timing Protocol (PTP) timing reference";
          container ql-override {
            description
                "Override the quality level of a timing reference";
            leaf ql-override-id {
              type enumeration {
                enum prs;
                enum stu;
                enum st2;
                enum tnc;
                enum st3e;
                enum st3;
                enum prc;
                enum ssua;
                enum ssub;
                enum sec;
              }
            } //ql-override-id

          } //container ql-override

          leaf shutdown {
            type boolean;
            description
                "Administratively shutdown the PTP timing reference";
          }

        } //container ptp

        container ref1 {
          description
              "Configure parameters for the first timing reference";
          container ql-override {
            description
                "Override the quality level of a timing reference";
            leaf ql-override-id {
              type enumeration {
                enum prs;
                enum stu;
                enum st2;
                enum tnc;
                enum st3e;
                enum st3;
                enum prc;
                enum ssua;
                enum ssub;
                enum sec;
                enum eec1;
                enum eec2;
              }
            } //ql-override-id

          } //container ql-override

          leaf shutdown {
            type boolean;
            description
                "Administratively shutdown the timing reference";
          }

          container source-port {
            description
                "Configure the source port for the first timing reference";
            leaf port-id {
              type string {
                length "1..64";
              }
              description
                  "Attribute port-id for source-port";
            } //port-id

          } //container source-port

        } //container ref1

        container ref2 {
          description
              "Configure parameters for the second timing reference";
          container ql-override {
            description
                "Override the quality level of a timing reference";
            leaf ql-override-id {
              type enumeration {
                enum prs;
                enum stu;
                enum st2;
                enum tnc;
                enum st3e;
                enum st3;
                enum prc;
                enum ssua;
                enum ssub;
                enum sec;
                enum eec1;
                enum eec2;
              }
            } //ql-override-id

          } //container ql-override

          leaf shutdown {
            type boolean;
            description
                "Administratively shutdown the timing reference";
          }

          container source-port {
            description
                "Configure the source port for the second timing reference";
            leaf port-id {
              type string {
                length "1..64";
              }
              description
                  "Attribute port-id for source-port";
            } //port-id

          } //container source-port

        } //container ref2

        container synce {
          description
              "Configure parameters for the synce timing reference";
          container ql-override {
            description
                "Override the quality level of a timing reference";
            leaf ql-override-id {
              type enumeration {
                enum prs;
                enum stu;
                enum st2;
                enum tnc;
                enum st3e;
                enum st3;
                enum prc;
                enum ssua;
                enum ssub;
                enum sec;
                enum eec1;
                enum eec2;
              }
            } //ql-override-id

          } //container ql-override

          leaf shutdown {
            type boolean;
            description
                "Administratively shutdown the timing reference";
          }

        } //container synce

      } //container sync-if-timing

      container telemetry {
        description
            "Configure telemetry parameters";
        list destination-group {
          key "name";
          description
              "Configure destination group parameters";
          leaf name {
            type string;
          } //name

          leaf allow-unsecure-connection {
            type boolean;
            description
                "Enable/disable gRPC client encryption";
          }

          container description {
            description
                "Description for this destination-group";
            leaf description-string {
              type string {
                length "1..80";
              }
            } //description-string

          } //container description

          container tls-client-profile {
            description
                "TLS profile for gRPC client";
            leaf name {
              type string;
            } //name

          } //container tls-client-profile

          list destination {
            key "ip-address-fqdn port";
            description
                "Configure destination parameters";
            leaf ip-address-fqdn {
              type string {
                length "1..255";
              }
            } //ip-address-fqdn

            leaf port {
              type int32 {
                range "1..65535";
              }
            } //port

            container router-instance {
              description
                  "Configure router-instance for the destination";
              leaf router-instance {
                type string {
                  length "1..32";
                }
              } //router-instance

              leaf service {
                type string;
              } //service

            } //container router-instance

          } //list destination

          container tcp-keepalive {
            description
                "Parameters for TCP keep-alive";
            container idle-time {
              description
                  "Number of seconds until the first TCP keep-alive is sent";
              leaf idle {
                type uint32 {
                  range "1..100000";
                }
                default 600;
              } //idle

            } //container idle-time

            container interval {
              description
                  "Number of seconds between two TCP keep-alives";
              leaf interval {
                type uint32 {
                  range "1..100000";
                }
                default 15;
              } //interval

            } //container interval

            container retries {
              description
                  "Number of missed keep-alives before the TCP connection is declared down";
              leaf count {
                type uint32 {
                  range "3..100";
                }
                default 4;
              } //count

            } //container retries

            leaf shutdown {
              type boolean;
              description
                  "Enable/disable TCP keep-alives";
            }

          } //container tcp-keepalive

        } //list destination-group

        container persistent-subscriptions {
          description
              "Configure persistent subscriptions parameters";
          list subscription {
            key "name";
            description
                "Configure pesistent subscription parameters";
            leaf name {
              type string;
            } //name

            container description {
              description
                  "Description for this persistent subscription";
              leaf description-string {
                type string {
                  length "1..80";
                }
              } //description-string

            } //container description

            container destination-group {
              description
                  "Assigns a destination-group to persistent subscription";
              leaf name {
                type string;
              } //name

            } //container destination-group

            container encoding {
              description
                  "Configure encoding";
              leaf encoding {
                type enumeration {
                  enum json;
                  enum bytes;
                  enum proto;
                }
                default "json";
                description
                    "<json|bytes|proto> - keywords";
              } //encoding

            } //container encoding

            container local-source-address {
              description
                  "Configure source IP address";
              leaf ip-int-name-ip-address-ipv6-address {
                type string;
              } //ip-int-name-ip-address-ipv6-address

            } //container local-source-address

            container mode {
              description
                  "Configure mode";
              leaf mode {
                type enumeration {
                  enum target-defined;
                  enum on-change;
                  enum sample;
                }
                description
                    "<target-defined|on-change|sample> - keywords";
              } //mode

            } //container mode

            container originated-qos-marking {
              description
                  "Configure QoS marking";
              leaf dscp-name {
                type string {
                  length "1..32";
                }
                description
                    "Attribute dscp-name for originated-qos-marking";
              } //dscp-name

            } //container originated-qos-marking

            container sample-interval {
              description
                  "Configure sample interval for sample mode";
              leaf sample-interval {
                type string;
                description
                    "<1000..18446744073709551615> - milliseconds";
              } //sample-interval

            } //container sample-interval

            container sensor-group {
              description
                  "Assigns a sensor-group to persistent subscription";
              leaf name {
                type string;
              } //name

            } //container sensor-group

            leaf shutdown {
              type boolean;
              description
                  "Enable/disable persistent subscription";
            }

          } //list subscription

        } //container persistent-subscriptions

        container sensor-groups {
          description
              "Configure sensor groups parameters";
          list sensor-group {
            key "name";
            description
                "Configure sensor group parameters";
            leaf name {
              type string;
            } //name

            container description {
              description
                  "Description for this sensor-group";
              leaf description-string {
                type string {
                  length "1..80";
                }
              } //description-string

            } //container description

            list path {
              key "string";
              description
                  "Configure path for the sensor-group";
              leaf string {
                type string {
                  length "1..512";
                }
              } //string

            } //list path

          } //list sensor-group

        } //container sensor-groups

      } //container telemetry

      container thresholds {
        description
            "Configure monitoring thresholds";
        list cflash-cap-alarm {
          key "cflash-id";
          description
              "Configure cflash capacity alarm thresholds";
          leaf cflash-id {
            type string;
            description
                "Attribute cflash-id for cflash-cap-alarm";
          } //cflash-id

          leaf rising-threshold {
            type int32;
          } //rising-threshold

          leaf falling-threshold {
            type int32;
          } //falling-threshold

          leaf interval {
            type int32 {
              range "1..2147483647";
            }
          } //interval

          leaf event-type {
            type enumeration {
              enum both;
              enum log;
              enum none;
              enum trap;
            }
            description
                "[log | trap | both | none] Def: both";
          } //event-type

          leaf startup-alarm {
            type enumeration {
              enum either;
              enum falling;
              enum rising;
            }
            description
                "[rising | falling | either] Def: either";
          } //startup-alarm

        } //list cflash-cap-alarm

        list cflash-cap-alarm-pct {
          key "cflash-id";
          description
              "Configure cflash capacity alarm thresholds using percentages";
          leaf cflash-id {
            type string;
            description
                "Attribute cflash-id for cflash-cap-alarm-pct";
          } //cflash-id

          leaf rising-threshold {
            type uint32 {
              range "0..100";
            }
          } //rising-threshold

          leaf falling-threshold {
            type uint32 {
              range "0..100";
            }
            description
                "percentage";
          } //falling-threshold

          leaf interval {
            type int32 {
              range "1..2147483647";
            }
          } //interval

          leaf rmon-event-type {
            type enumeration {
              enum both;
              enum log;
              enum none;
              enum trap;
            }
            default "both";
            description
                "[log | trap | both | none] - Default: both";
          } //rmon-event-type

          leaf startup-alarm {
            type enumeration {
              enum either;
              enum falling;
              enum rising;
            }
            default "either";
            description
                "[rising | falling | either] - Default: either";
          } //startup-alarm

        } //list cflash-cap-alarm-pct

        list cflash-cap-warn {
          key "cflash-id";
          description
              "Configure cflash capacity warning thresholds";
          leaf cflash-id {
            type string;
            description
                "Attribute cflash-id for cflash-cap-warn";
          } //cflash-id

          leaf rising-threshold {
            type int32;
          } //rising-threshold

          leaf falling-threshold {
            type int32;
          } //falling-threshold

          leaf interval {
            type int32 {
              range "1..2147483647";
            }
          } //interval

          leaf event-type {
            type enumeration {
              enum both;
              enum log;
              enum none;
              enum trap;
            }
            description
                "[log | trap | both | none] Def: both";
          } //event-type

          leaf startup-alarm {
            type enumeration {
              enum either;
              enum falling;
              enum rising;
            }
            description
                "[rising | falling | either] Def: either";
          } //startup-alarm

        } //list cflash-cap-warn

        list cflash-cap-warn-pct {
          key "cflash-id";
          description
              "Configure cflash capacity warning thresholds using percentages";
          leaf cflash-id {
            type string;
            description
                "Attribute cflash-id for cflash-cap-warn-pct";
          } //cflash-id

          leaf rising-threshold {
            type uint32 {
              range "0..100";
            }
          } //rising-threshold

          leaf falling-threshold {
            type uint32 {
              range "0..100";
            }
            description
                "percentage";
          } //falling-threshold

          leaf interval {
            type int32 {
              range "1..2147483647";
            }
          } //interval

          leaf rmon-event-type {
            type enumeration {
              enum both;
              enum log;
              enum none;
              enum trap;
            }
            default "both";
            description
                "[log | trap | both | none] - Default: both";
          } //rmon-event-type

          leaf startup-alarm {
            type enumeration {
              enum either;
              enum falling;
              enum rising;
            }
            default "either";
            description
                "[rising | falling | either] - Default: either";
          } //startup-alarm

        } //list cflash-cap-warn-pct

        container kb-memory-use-alarm {
          description
              "Configure memory (in kilobytes) use alarm thresholds";
          leaf rising-threshold {
            type int32;
          } //rising-threshold

          leaf falling-threshold {
            type int32;
          } //falling-threshold

          leaf interval {
            type int32 {
              range "1..2147483647";
            }
          } //interval

          leaf rmon-event-type {
            type enumeration {
              enum both;
              enum log;
              enum none;
              enum trap;
            }
            description
                "[log | trap | both | none] Def: both";
          } //rmon-event-type

          leaf startup-alarm {
            type enumeration {
              enum either;
              enum falling;
              enum rising;
            }
            description
                "[rising | falling | either] Def: either";
          } //startup-alarm

        } //container kb-memory-use-alarm

        container kb-memory-use-warn {
          description
              "Configure memory (in kilobytes) usage warning thresholds";
          leaf rising-threshold {
            type int32;
          } //rising-threshold

          leaf falling-threshold {
            type int32;
          } //falling-threshold

          leaf interval {
            type int32 {
              range "1..2147483647";
            }
          } //interval

          leaf rmon-event-type {
            type enumeration {
              enum both;
              enum log;
              enum none;
              enum trap;
            }
            description
                "[log | trap | both | none] Def: both";
          } //rmon-event-type

          leaf startup-alarm {
            type enumeration {
              enum either;
              enum falling;
              enum rising;
            }
            description
                "[rising | falling | either] Def: either";
          } //startup-alarm

        } //container kb-memory-use-warn

        container memory-use-alarm {
          description
              "Configure memory use alarm thresholds";
          leaf rising-threshold {
            type int32;
          } //rising-threshold

          leaf falling-threshold {
            type int32;
          } //falling-threshold

          leaf interval {
            type int32 {
              range "1..2147483647";
            }
            description
                "[1..214783647]";
          } //interval

          leaf rmon-event-type {
            type enumeration {
              enum both;
              enum log;
              enum none;
              enum trap;
            }
            description
                "[log | trap | both | none] Def: both";
          } //rmon-event-type

          leaf startup-alarm {
            type enumeration {
              enum either;
              enum falling;
              enum rising;
            }
            description
                "[rising | falling | either] Def: either";
          } //startup-alarm

        } //container memory-use-alarm

        container memory-use-warn {
          description
              "Configure memory usage warning thresholds";
          leaf rising-threshold {
            type int32;
          } //rising-threshold

          leaf falling-threshold {
            type int32;
          } //falling-threshold

          leaf interval {
            type int32 {
              range "1..2147483647";
            }
            description
                "[1..214783647]";
          } //interval

          leaf rmon-event-type {
            type enumeration {
              enum both;
              enum log;
              enum none;
              enum trap;
            }
            description
                "[log | trap | both | none] Def: both";
          } //rmon-event-type

          leaf startup-alarm {
            type enumeration {
              enum either;
              enum falling;
              enum rising;
            }
            description
                "[rising | falling | either] Def: either";
          } //startup-alarm

        } //container memory-use-warn

        container rmon {
          description
              "Configure RMON monitoring thresholds";
          list alarm {
            key "rmon-alarm-id";
            description
                "Configure RMON alarm thresholds";
            leaf rmon-alarm-id {
              type uint32 {
                range "0..65535";
              }
              description
                  "[1..65535]";
            } //rmon-alarm-id

            leaf variable-oid {
              type string {
                length "1..255";
              }
            } //variable-oid

            leaf interval {
              type int32 {
                range "1..2147483647";
              }
            } //interval

            leaf sample-type {
              type enumeration {
                enum absolute;
                enum delta;
              }
              description
                  "[absolute | delta] Def: absolute";
            } //sample-type

            leaf startup-alarm {
              type enumeration {
                enum either;
                enum falling;
                enum rising;
              }
              description
                  "[rising | falling | either] Def: either";
            } //startup-alarm

            leaf rising-event {
              type uint32 {
                range "0..65535";
              }
              description
                  "[1..65535]";
            } //rising-event

            leaf rising-threshold {
              type int32;
            } //rising-threshold

            leaf falling-event {
              type uint32 {
                range "0..65535";
              }
              description
                  "[1..65535]";
            } //falling-event

            leaf falling-threshold {
              type int32;
            } //falling-threshold

            leaf owner {
              type string {
                length "1..80";
              }
              default "TiMOS CLI";
              description
                  "[80 chars max] Default - \"TiMOS CLI\"";
            } //owner

          } //list alarm

          list event {
            key "rmon-event-id";
            description
                "Configure RMON threshold event";
            leaf rmon-event-id {
              type uint32 {
                range "1..65535";
              }
              description
                  "[1..65535]";
            } //rmon-event-id

            leaf event-type {
              type enumeration {
                enum both;
                enum log;
                enum none;
                enum trap;
              }
              description
                  "[log | trap | both | none] Def: both";
            } //event-type

            leaf description {
              type string {
                length "1..80";
              }
            } //description

            leaf owner {
              type string {
                length "1..80";
              }
              default "TiMOS CLI";
              description
                  "[80 chars max] Default - \"TiMOS CLI\"";
            } //owner

          } //list event

        } //container rmon

      } //container thresholds

      container time {
        description
            "Configure time zone or NTP or SNTP parameters";
        leaf prefer-local-time {
          type boolean;
          description
              "Enable/disable the preference of local-time over UTC";
        }

        container zone {
          description
              "Configure time zone and time offset for system";
          leaf std-zone-name-non-std-zone-name {
            type string {
              length "1..5";
            }
            description
                "- non-std-zone-name [5 chars max] 
                 - std-zone-name [GMT|WET|CET|EET|MSK|MSD|AST|NST| 
                 EST|CST|MST|PST|HST|AKST|AWST|ACST|AEST|NZST|UTC]";
          } //std-zone-name-non-std-zone-name

          leaf hh-mm {
            type string;
            description
                "hh - [-11..12] 
                 mm - [0..59] - Should be 0 if hour offset is 12";
          } //hh-mm

        } //container zone

        list dst-zone {
          key "std-zone-name-non-std-zone-name";
          description
              "Configure summer time settings";
          leaf std-zone-name-non-std-zone-name {
            type string {
              length "1..5";
            }
            description
                "- non-std-zone-name [5 chars max] 
                 - std-zone-name [ADT|NDT|AKDT|CDT|CEST|EDT|EEST|MDT| 
                 NZDT|PDT|WEST]";
          } //std-zone-name-non-std-zone-name

          container end {
            description
                "Configure end of summer time setting";
            leaf end-week {
              type enumeration {
                enum first;
                enum second;
                enum third;
                enum fourth;
                enum last;
              }
            } //end-week

            leaf end-day {
              type enumeration {
                enum sunday;
                enum monday;
                enum tuesday;
                enum wednesday;
                enum thursday;
                enum friday;
                enum saturday;
              }
            } //end-day

            leaf end-month {
              type enumeration {
                enum january;
                enum february;
                enum march;
                enum april;
                enum may;
                enum june;
                enum july;
                enum august;
                enum september;
                enum october;
                enum november;
                enum december;
              }
            } //end-month

            leaf hours-minutes {
              type string;
              description
                  "hh:mm";
            } //hours-minutes

          } //container end

          container offset {
            description
                "Offset for summer time setting";
            leaf offset {
              type uint16;
              description
                  "0..60";
            } //offset

          } //container offset

          container start {
            description
                "Configure start of summer time setting";
            leaf start-week {
              type enumeration {
                enum first;
                enum second;
                enum third;
                enum fourth;
                enum last;
              }
            } //start-week

            leaf start-day {
              type enumeration {
                enum sunday;
                enum monday;
                enum tuesday;
                enum wednesday;
                enum thursday;
                enum friday;
                enum saturday;
              }
            } //start-day

            leaf start-month {
              type enumeration {
                enum january;
                enum february;
                enum march;
                enum april;
                enum may;
                enum june;
                enum july;
                enum august;
                enum september;
                enum october;
                enum november;
                enum december;
              }
            } //start-month

            leaf hours-minutes {
              type string;
              description
                  "hh:mm";
            } //hours-minutes

          } //container start

        } //list dst-zone

        container ntp {
          presence
              "Configure parameters for NTP protocol";
          leaf authentication-check {
            type boolean;
            description
                "Configure the option to skip the rejection of NTP PDUs";
          }

          list authentication-key {
            key "key-id";
            description
                "Configure the authentication key and type used to verify NTP PDUs";
            leaf key-id {
              type uint16 {
                range "1..255";
              }
            } //key-id

            leaf key {
              type string {
                length "1..500";
              }
              description
                  "Max 32 chars";
            } //key

            leaf hash-hash2-custom {
              type enumeration {
                enum hash;
                enum hash2;
                enum custom;
              }
              description
                  "keyword";
            } //hash-hash2-custom

            leaf type {
              type enumeration {
                enum des;
                enum message-digest;
              }
            } //type

          } //list authentication-key

          list broadcast {
            key "router interface";
            description
                "Configure an interface to transmit NTP broadcast PDUs";
            leaf router {
              type string {
                length "1..32";
              }
              description
                  "Base|management Default - Base";
            } //router

            leaf interface {
              type string {
                length "1..32";
              }
              description
                  "Max 32 chars";
            } //interface

            leaf key-id {
              type uint16 {
                range "1..255";
              }
            } //key-id

            leaf version {
              type int32 {
                range "2..4";
              }
            } //version

            leaf ttl {
              type uint8 {
                range "1..255";
              }
              description
                  "[1..255]";
            } //ttl

          } //list broadcast

          container broadcastclient {
            description
                "Configure an interface to receive NTP broadcast PDUs";
            leaf router {
              type string {
                length "1..32";
              }
              default "Base";
              description
                  "<router-name>|<vprn-svc-id> 
                   router-name - Base|management Default - Base 
                   vprn-svc-id - [1..2147483647]";
            } //router

            leaf service-name {
              type string;
            } //service-name

            leaf interface {
              type string {
                length "1..32";
              }
              description
                  "Max 32 chars";
            } //interface

            leaf authenticate {
              type boolean;
            } //authenticate

          } //container broadcastclient

          container multicast {
            description
                "Configure an interface to transmit NTP multicast PDUs";
            leaf key-id {
              type uint16 {
                range "1..255";
              }
            } //key-id

            leaf version {
              type int32 {
                range "2..4";
              }
            } //version

          } //container multicast

          container multicastclient {
            description
                "Configure an interface to receive NTP multicast PDUs";
            leaf authenticate {
              type boolean;
            } //authenticate

          } //container multicastclient

          container ntp-server {
            description
                "Configure the node to assume the role of an NTP server";
            leaf transmit {
              type uint16 {
                range "1..255";
              }
              status "obsolete";
            } //transmit

            leaf authenticate {
              type boolean;
              description
                  "keyword - If specified server requires authentication.";
            } //authenticate

          } //container ntp-server

          list peer {
            key "ip-address";
            description
                "Configure NTP to use the specified address as an NTP peer";
            leaf router {
              type string {
                length "1..32";
              }
              default "Base";
              description
                  "<router-name>|<vprn-svc-id> 
                   router-name - Base|management Default - Base 
                   vprn-svc-id - [1..2147483647]";
            } //router

            leaf service-name {
              type string;
            } //service-name

            leaf ip-address {
              type string;
              description
                  "Attribute ip-address for peer";
            } //ip-address

            leaf key-id {
              type uint16 {
                range "1..255";
              }
            } //key-id

            leaf version {
              type int32 {
                range "2..4";
              }
            } //version

            leaf prefer {
              type boolean;
            } //prefer

          } //list peer

          list server {
            key "ip-address";
            description
                "Configure NTP to use the specified address as an NTP server";
            leaf router {
              type string {
                length "1..32";
              }
              default "Base";
              description
                  "<router-name>|<vprn-svc-id> 
                   router-name - Base|management Default - Base 
                   vprn-svc-id - [1..2147483647]";
            } //router

            leaf service-name {
              type string;
            } //service-name

            leaf ip-address {
              type string;
              description
                  "Attribute ip-address for server";
            } //ip-address

            leaf key-id {
              type uint32 {
                range "1..255";
              }
            } //key-id

            leaf version {
              type uint32 {
                range "2..4";
              }
            } //version

            leaf prefer {
              type boolean;
            } //prefer

          } //list server

          leaf shutdown {
            type boolean;
            description
                "Enable/disable NTP protocol execution";
          }

        } //container ntp

        container sntp {
          presence
              "Configure parameters for SNTP protocol";
          leaf broadcast-client {
            type boolean;
            description
                "Enable/disable broadcast client mode for SNTP";
          }

          list server-address {
            key "ip-address";
            description
                "Create/delete SNTP server for unicast client mode";
            leaf ip-address {
              type inet:ip-address;
            } //ip-address

            leaf version {
              type int16 {
                range "1..3";
              }
              default 3;
            } //version

            leaf normal-preferred {
              type enumeration {
                enum normal;
                enum preferred;
              }
              description
                  "keywords";
            } //normal-preferred

            leaf interval {
              type uint32 {
                range "64..1024";
              }
            } //interval

          } //list server-address

          leaf shutdown {
            type boolean;
            description
                "Enable/disable SNTP protocol execution";
          }

        } //container sntp

      } //container time

      container vsd {
        description
            "Configure VSD information";
        container system-id {
          description
              "Configure system identifier for VSD servers";
          leaf name {
            type string;
          } //name

        } //container system-id

      } //container vsd

      container xmpp {
        description
            "Configure XMPP parameters";
        list server {
          key "xmpp-server-name";
          description
              "Configure XMPP Server Name";
          leaf xmpp-server-name {
            type string {
              length "1..32";
            }
          } //xmpp-server-name

          leaf domain-name {
            type string {
            }
          } //domain-name

          leaf username {
            type string {
              length "1..32";
            }
          } //username

          leaf password {
            type string {
              length "1..32";
            }
          } //password

          leaf router {
            type string {
              length "1..32";
            }
            description
                "Attribute router-instance for server";
          } //router

          leaf service-name {
            type string;
          } //service-name

          leaf shutdown {
            type boolean;
            description
                "Administratively enable or disable XMPP server";
          }

        } //list server

      } //container xmpp

    } //container system

  } //grouping alu-conf-system-r13

} //module  alu-conf-system-r13
