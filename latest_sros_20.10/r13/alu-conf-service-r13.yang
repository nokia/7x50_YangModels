module alu-conf-service-r13 {
  yang-version "1";

  namespace "urn:alcatel-lucent.com:sros:ns:yang:conf-service-r13";

  prefix "conf-service-r13";

  import alu-conf-svc-apipe-r13 {
    prefix "conf-svc-apipe-r13";
  }
  import alu-conf-svc-cpipe-r13 {
    prefix "conf-svc-cpipe-r13";
  }
  import alu-conf-svc-cust-r13 {
    prefix "conf-svc-cust-r13";
  }
  import alu-conf-svc-dynsrv-r13 {
    prefix "conf-svc-dynsrv-r13";
  }
  import alu-conf-svc-egrmcgroup-r13 {
    prefix "conf-svc-egrmcgroup-r13";
  }
  import alu-conf-svc-epipe-r13 {
    prefix "conf-svc-epipe-r13";
  }
  import alu-conf-svc-fpipe-r13 {
    prefix "conf-svc-fpipe-r13";
  }
  import alu-conf-svc-ies-r13 {
    prefix "conf-svc-ies-r13";
  }
  import alu-conf-svc-ipfix-r13 {
    prefix "conf-svc-ipfix-r13";
  }
  import alu-conf-svc-ipipe-r13 {
    prefix "conf-svc-ipipe-r13";
  }
  import alu-conf-svc-nat-r13 {
    prefix "conf-svc-nat-r13";
  }
  import alu-conf-svc-sdp-r13 {
    prefix "conf-svc-sdp-r13";
  }
  import alu-conf-svc-template-r13 {
    prefix "conf-svc-template-r13";
  }
  import alu-conf-svc-upnp-r13 {
    prefix "conf-svc-upnp-r13";
  }
  import alu-conf-svc-vpls-r13 {
    prefix "conf-svc-vpls-r13";
  }
  import alu-conf-svc-vprn-r13 {
    prefix "conf-svc-vprn-r13";
  }
  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure services on SR OS based routers. 
       
       Copyright 2014-2015 Alcatel-Lucent, 2016 Nokia. All rights reserved. 
       Reproduction of this document is authorized on the condition that the 
       foregoing copyright notice is included. 
       
       This alu-conf-service-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-04-17";

  grouping alu-conf-service-r13 {
    container service {
      description
          "Configure services";
      uses "conf-svc-apipe-r13:alu-conf-svc-apipe-r13";
      uses "conf-svc-cpipe-r13:alu-conf-svc-cpipe-r13";
      uses "conf-svc-cust-r13:alu-conf-svc-cust-r13";
      uses "conf-svc-dynsrv-r13:alu-conf-svc-dynsrv-r13";
      uses "conf-svc-egrmcgroup-r13:alu-conf-svc-egrmcgroup-r13";
      uses "conf-svc-epipe-r13:alu-conf-svc-epipe-r13";
      uses "conf-svc-fpipe-r13:alu-conf-svc-fpipe-r13";
      uses "conf-svc-ies-r13:alu-conf-svc-ies-r13";
      uses "conf-svc-ipfix-r13:alu-conf-svc-ipfix-r13";
      uses "conf-svc-ipipe-r13:alu-conf-svc-ipipe-r13";
      list mac-list {
        key "name";
        description
            "Configure mac-list for mac-range entry";
        leaf name {
          type string;
        } //name

        list description {
          key "description-string";
          description
              "Description for the mac-list";
          leaf description-string {
            type string {
              length "1..80";
            }
          } //description-string

        } //list description

        list mac {
          key "ieee-address";
          description
              "Configure mac address";
          leaf ieee-address {
            type alu:ieee-address;
          } //ieee-address

          leaf mask {
            type alu:ieee-address;
          } //mask

        } //list mac

      } //list mac-list

      container mac-notification {
        description
            "Configure settings for MAC-notification messages";
        container count {
          description
              "Configure count for MAC-notification messages";
          leaf value {
            type uint32 {
              range "1..10";
            }
          } //value

        } //container count

        container interval {
          description
              "Configure interval for MAC-notification messages";
          leaf deci-seconds {
            type uint32 {
              range "1..100";
            }
            description
                "[1..100] tenths of a second";
          } //deci-seconds

        } //container interval

      } //container mac-notification

      container md-auto-id {
        description
            "Configure auto identifier ranges for model-driven CLI";
        container customer-id-range {
          description
              "Configure customer identifier range";
          leaf start {
            type uint32 {
              range "2..2147483647";
            }
          } //start

          leaf end {
            type uint32 {
              range "2..2147483647";
            }
            description
                "customer-id";
          } //end

        } //container customer-id-range

        container pw-template-id-range {
          description
              "Configure pw-template identifier range";
          leaf start {
            type uint32 {
              range "1..2147483647";
            }
          } //start

          leaf end {
            type uint32 {
              range "1..2147483647";
            }
            description
                "pw-template-id";
          } //end

        } //container pw-template-id-range

        container service-id-range {
          description
              "Configure service identifier range";
          leaf start {
            type uint32 {
              range "1..2147483647";
            }
          } //start

          leaf end {
            type uint32 {
              range "1..2147483647";
            }
            description
                "service-id";
          } //end

        } //container service-id-range

      } //container md-auto-id

      container mrp {
        description
            "Manage the mrp-policies";
        container copy {
          description
              "Copy mrp policy and entries";
          leaf src-mrp-policy {
            type string {
              length "1..32";
            }
          } //src-mrp-policy

          leaf to {
            type string {
              length "1..32";
            }
          } //to

        } //container copy

        list mrp-policy {
          key "policy-name";
          description
              "Configure a mrp policy";
          leaf policy-name {
            type string {
              length "1..32";
            }
          } //policy-name

          container default-action {
            description
                "Default action for the mrp policy";
            leaf default-action-id {
              type enumeration {
                enum block;
                enum allow;
              }
            } //default-action-id

          } //container default-action

          container description {
            description
                "Description for the mrp policy";
            leaf description-string {
              type string {
                length "1..80";
              }
            } //description-string

          } //container description

          container renum {
            description
                "Renumber an entry";
            leaf src-entry-id {
              type int32 {
                range "1..65535";
              }
            } //src-entry-id

            leaf to {
              type int32 {
                range "1..65535";
              }
            } //to

          } //container renum

          container scope {
            description
                "Configure scope for this mrp policy";
            leaf scope-id {
              type enumeration {
                enum exclusive;
                enum template;
              }
            } //scope-id

          } //container scope

          list entry {
            key "entry-id";
            description
                "Configure mrp policy entry";
            leaf entry-id {
              type int32 {
                range "1..65535";
              }
            } //entry-id

            container action {
              description
                  "Configure action for the mrp policy entry";
              leaf action {
                type enumeration {
                  enum none;
                  enum block;
                  enum allow;
                  enum end-station;
                }
              } //action

            } //container action

            container description {
              description
                  "Description for the mrp policy entry";
              leaf description-string {
                type string {
                  length "1..80";
                }
              } //description-string

            } //container description

            container match {
              presence
                  "Configure match criteria for this mrp policy entry";
              container isid {
                description
                    "Configure ISID values/ranges that match this entry";
                leaf value {
                  type int32 {
                    range "0..16777215";
                  }
                } //value

                leaf to {
                  type int32 {
                    range "0..16777215";
                  }
                  description
                      "Used to specify a range of matching isid values";
                } //to

              } //container isid

            } //container match

          } //list entry

        } //list mrp-policy

      } //container mrp

      uses "conf-svc-nat-r13:alu-conf-svc-nat-r13";
      list oper-group {
        key "group-name";
        description
            "Configure a Operational-Group information";
        leaf group-name {
          type string {
            length "1..32";
          }
        } //group-name

        container bfd-enable {
          description
              "Configure a BFD destination";
          leaf interface {
            type string {
              length "1..32";
            }
            description
                "[32 chars max] (must start with a letter)";
          } //interface

          leaf dest-ip {
            type string;
            description
                "a.b.c.d";
          } //dest-ip

          leaf service {
            type string;
          } //service

        } //container bfd-enable

        container hold-time {
          description
              "Configure hold-time information";
          container group {
            description
                "Configure group up/down time information";
            leaf down {
              type boolean;
            } //down

            leaf secs {
              type int32 {
                range "0..3600";
              }
            } //secs

            leaf up {
              type boolean;
            } //up

          } //container group

        } //container hold-time

      } //list oper-group

      container pbb {
        description
            "Configure global PBB parameters";
        container leaf-source-bmac {
          description
              "Configure leaf backbone source MAC address used for PBB";
          leaf ieee-address {
            type alu:ieee-address;
            description
                "xx:xx:xx:xx:xx:xx or xx-xx-xx-xx-xx-xx";
          } //ieee-address

        } //container leaf-source-bmac

        list mac-name {
          key "name";
          description
              "Configure MAC name for MAC address";
          leaf name {
            type string {
              length "1..32";
            }
            description
                "32 char max";
          } //name

          leaf ieee-address {
            type string;
            description
                "xx:xx:xx:xx:xx:xx or xx-xx-xx-xx-xx-xx";
          } //ieee-address

        } //list mac-name

        container source-bmac {
          description
              "Configure source b-vpls MAC address to use with PBB";
          leaf ieee-address {
            type string;
            description
                "xx:xx:xx:xx:xx:xx or xx-xx-xx-xx-xx-xx";
          } //ieee-address

        } //container source-bmac

      } //container pbb

      container proxy-arp-nd {
        description
            "Configure proxy ARP/ND information";
        list mac-list {
          key "name";
          description
              "Configure proxy ARP/ND MAC-list information";
          leaf name {
            type string;
          } //name

          list mac {
            key "ieee-address";
            description
                "Configure proxy ARP/ND MAC address information";
            leaf ieee-address {
              type alu:ieee-address;
              description
                  "xx:xx:xx:xx:xx:xx or xx-xx-xx-xx-xx-xx";
            } //ieee-address

          } //list mac

        } //list mac-list

      } //container proxy-arp-nd

      container pw-routing {
        description
            "Configure pseudowire routing parameters";
        container boot-timer {
          description
              "Configure boot-timer";
          leaf secs {
            type uint32 {
              range "0..600";
            }
          } //secs

        } //container boot-timer

        container retry-count {
          description
              "Configure retry count";
          leaf retry-count-id {
            type uint32 {
              range "10..10000";
            }
          } //retry-count-id

        } //container retry-count

        container retry-timer {
          description
              "Configure retry timer";
          leaf secs {
            type uint32 {
              range "10..480";
            }
          } //secs

        } //container retry-timer

        container spe-address {
          description
              "Configure switch-point address";
          leaf global-id-prefix {
            type string {
              length "1..26";
            }
            description
                "<global-id>:{<prefix>|<ipaddress>} 
                 global-id - [1..4294967295] 
                 prefix - [1..4294967295] 
                 ipaddress - a.b.c.d";
          } //global-id-prefix

        } //container spe-address

        list static-route {
          key "route-name";
          description
              "Configure static pseudowire route";
          leaf route-name {
            type string {
            }
            description
                "Attribute route-name for static-route";
          } //route-name

        } //list static-route

        list local-prefix {
          key "local-prefix";
          description
              "Configure a local-prefix";
          leaf local-prefix {
            type string {
              length "1..26";
            }
            description
                "<global-id>:<ip-addr>|<raw-prefix> 
                 ip-addr - a.b.c.d 
                 raw-prefix - [1..4294967295] 
                 global-id - [1..4294967295]";
          } //local-prefix

          list advertise-bgp {
            key "route-distinguisher";
            description
                "Configure BGP advertisement";
            leaf route-distinguisher {
              type string {
                length "1..21";
              }
              description
                  "<ip-addr:comm-val>|<2byte-asnumber:ext-comm-val>|<4byte-asnumber:comm-val> 
                   ip-addr - a.b.c.d 
                   comm-val - [0..65535] 
                   2byte-asnumber - [1..65535] 
                   ext-comm-val - [0..4294967295] 
                   4byte-asnumber - [1..4294967295]";
            } //route-distinguisher

            leaf community {
              type string {
                length "1..11";
              }
              description
                  "<asnumber:comm-val> 
                   asnumber - [1..65535] 
                   comm-val - [0..65535]";
            } //community

          } //list advertise-bgp

        } //list local-prefix

        list path {
          key "name";
          description
              "Configure path-name";
          leaf name {
            type string {
              length "1..32";
            }
          } //name

          list hop {
            key "hop-index";
            description
                "Configure path-hop";
            leaf hop-index {
              type uint32 {
                range "1..16";
              }
            } //hop-index

            leaf ip-address {
              type inet:ip-address;
            } //ip-address

          } //list hop

          leaf shutdown {
            type boolean;
            description
                "Administratively enable/disable the pseudowire path";
          }

        } //list path

      } //container pw-routing

      list pw-template {
        key "policy-id";
        description
            "Configure a pseudowire template policy";
        leaf policy-id {
          type uint32 {
            range "1..2147483647";
          }
        } //policy-id

        leaf use-provisioned-sdp {
          type boolean;
        } //use-provisioned-sdp

        leaf prefer-provisioned-sdp {
          type boolean;
        } //prefer-provisioned-sdp

        leaf name {
          type string;
        } //name

        leaf auto-gre-sdp {
          type boolean;
        } //auto-gre-sdp

        container accounting-policy {
          description
              "Configure accounting-policy to be used";
          leaf acct-policy-id {
            type uint64 {
              range "1..99";
            }
          } //acct-policy-id

        } //container accounting-policy

        leaf allow-fragmentation {
          type boolean;
          description
              "Allow GRE encapsulated packets to be sent without setting the DF bit";
        }

        container auto-learn-mac-protect {
          description
              "Enable/disable automatic update of MAC protect list";
          leaf exclude-list {
            type string;
          } //exclude-list

        } //container auto-learn-mac-protect

        leaf block-on-peer-fault {
          type boolean;
          description
              "Enable/Disable block traffic on peer fault";
        }

        leaf collect-stats {
          type boolean;
          description
              "Enable/disable statistics collection";
        }

        leaf controlword {
          type boolean;
          description
              "Enable/Disable the use of ControlWord";
        }

        leaf disable-aging {
          type boolean;
          description
              "Enable/disable aging of MAC addresses";
        }

        leaf disable-learning {
          type boolean;
          description
              "Enable/disable learning of new MAC addresses";
        }

        leaf discard-unknown-source {
          type boolean;
          description
              "Enable/disable discarding of frames with unknown source MAC address";
        }

        list encryption-keygroup {
          key "direction";
          description
              "Configure in/outbound keygroup identifier";
          leaf id-name {
            type string;
          } //id-name

          leaf direction {
            type enumeration {
              enum inbound;
              enum outbound;
            }
          } //direction

        } //list encryption-keygroup

        leaf entropy-label {
          type boolean;
          description
              "Enable/disable use of entropy-label";
        }

        container force-qinq-vc-forwarding {
          description
              "Forces qinq-vc-type forwarding in the data-path";
          leaf c-tag-c-tag---s-tag-c-tag {
            type enumeration {
              enum c-tag-c-tag;
              enum s-tag-c-tag;
            }
            description
                "c-tag-c-tag | s-tag-c-tag";
          } //c-tag-c-tag---s-tag-c-tag

        } //container force-qinq-vc-forwarding

        leaf force-vlan-vc-forwarding {
          type boolean;
          description
              "Forces vlan-vc-type forwarding in the data-path";
        }

        container hash-label {
          description
              "Enable/disable use of hash-label";
          leaf signal-capability {
            type boolean;
          } //signal-capability

        } //container hash-label

        container l2pt-termination {
          description
              "Configure L2PT termination on this spoke SDP";
          leaf cdp {
            type boolean;
            description
                "keyword - cisco discovery protocol";
          } //cdp

          leaf dtp {
            type boolean;
            description
                "keyword - dynamic trunking protocol";
          } //dtp

          leaf pagp {
            type boolean;
            description
                "keyword - port aggregation protocol";
          } //pagp

          leaf stp {
            type boolean;
            description
                "keyword - all spanning tree protocols: stp, rstp, mstp, pvst (default)";
          } //stp

          leaf udld {
            type boolean;
            description
                "keyword - unidirectional link detection";
          } //udld

          leaf vtp {
            type boolean;
            description
                "keyword - virtual trunk protocol";
          } //vtp

        } //container l2pt-termination

        container limit-mac-move {
          description
              "Configure mac move";
          leaf blockable-non-blockable {
            type enumeration {
              enum blockable;
              enum non-blockable;
            }
          } //blockable-non-blockable

        } //container limit-mac-move

        leaf mac-pinning {
          type boolean;
          description
              "Enable/disable MAC address pinning on this spoke SDP";
        }

        container max-nbr-mac-addr {
          description
              "Configure the maximum number of MAC entries in the FDB from this SDP";
          leaf table-size {
            type string;
            description
                "Attribute table-size for max-nbr-mac-addr";
          } //table-size

        } //container max-nbr-mac-addr

        container pw-template-name {
          status "obsolete";
          description
              "Configure a name to the pw-template";
          leaf pw-template-name {
            type string;
          } //pw-template-name

        } //container pw-template-name

        container restrict-protected-src {
          description
              "Enable/disable protected src MAC restriction";
          leaf discard-frame {
            type boolean;
            description
                "keyword - discard frame and trap on a protected MAC";
          } //discard-frame

          leaf alarm-only {
            type boolean;
            description
                "keyword - trap on a protected MAC";
          } //alarm-only

        } //container restrict-protected-src

        list sdp-exclude {
          key "group-name";
          description
              "Configure excluded SDP group";
          leaf group-name {
            type string {
              length "1..32";
            }
          } //group-name

        } //list sdp-exclude

        list sdp-include {
          key "group-name";
          description
              "Configure included SDP group";
          leaf group-name {
            type string {
              length "1..32";
            }
          } //group-name

        } //list sdp-include

        container vc-type {
          description
              "Configure VC type";
          leaf ether-vlan {
            type enumeration {
              enum ether;
              enum vlan;
            }
            description
                "keywords - specify virtual circuit type";
          } //ether-vlan

        } //container vc-type

        container vlan-vc-tag {
          description
              "Configure VLAN VC tag";
          leaf vlan-id {
            type uint32 {
              range "0..4094";
            }
          } //vlan-id

        } //container vlan-vc-tag

        container egress {
          description
              "Spoke SDP binding egress configuration";
          container filter {
            description
                "Apply egress filter";
            leaf ip {
              type uint32 {
                range "1..65535";
              }
            } //ip

            leaf mac {
              type uint32 {
                range "1..65535";
              }
              description
                  "filter-id";
            } //mac

            leaf ipv6 {
              type uint32 {
                range "1..65535";
              }
              description
                  "filter-id";
            } //ipv6

          } //container filter

          container qos {
            description
                "Configure egress qos";
            leaf network-policy-id {
              type uint32 {
                range "1..65535";
              }
            } //network-policy-id

            leaf name {
              type string;
            } //name

            leaf port-redirect-group {
              type string {
                length "1..32";
              }
            } //port-redirect-group

            leaf instance {
              type uint16 {
                range "1..65535";
              }
            } //instance

          } //container qos

          container filter-name {
            presence
                "Apply egress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

          container mfib-allowed-mda-destinations {
            description
                "Configure MFIB allowed MDA destinations";
            list mda {
              key "mda-id";
              description
                  "Add/remove MDA";
              leaf mda-id {
                type string {
                  length "1..7";
                }
                description
                    "Attribute mda-id for mda";
              } //mda-id

            } //list mda

          } //container mfib-allowed-mda-destinations

        } //container egress

        container igmp-snooping {
          description
              "Configure IGMP snooping parameters";
          leaf fast-leave {
            type boolean;
            description
                "Enable/disable IGMP fast-leave processing";
          }

          container import {
            description
                "Import a policy to filter IGMP packets";
            leaf policy-name {
              type string {
                length "1..32";
              }
            } //policy-name

          } //container import

          container last-member-query-interval {
            description
                "Configure the IGMP Last Member Query Interval";
            leaf t1-10-seconds {
              type uint32 {
                range "1..50";
              }
            } //t1-10-seconds

          } //container last-member-query-interval

          container max-num-groups {
            description
                "Configure the max number of multicast groups allowed";
            leaf max-num-groups-id {
              type uint32 {
                range "1..1000";
              }
            } //max-num-groups-id

          } //container max-num-groups

          container query-interval {
            description
                "Configure the IGMP Query Interval";
            leaf seconds {
              type uint32 {
                range "2..1024";
              }
            } //seconds

          } //container query-interval

          container query-response-interval {
            description
                "Configure the IGMP Query Response Interval";
            leaf seconds {
              type uint32 {
                range "1..1023";
              }
            } //seconds

          } //container query-response-interval

          container robust-count {
            description
                "Configure the IGMP Robustness Variable";
            leaf robust-count {
              type uint32 {
                range "2..7";
              }
            } //robust-count

          } //container robust-count

          leaf send-queries {
            type boolean;
            description
                "Enable/disable generation of IGMP General Queries";
          }

          container version {
            description
                "Configure the version of IGMP";
            leaf version {
              type uint32 {
                range "1..3";
              }
              description
                  "[1, 2 or 3]";
            } //version

          } //container version

        } //container igmp-snooping

        container ingress {
          description
              "Spoke SDP binding ingress configuration";
          container filter {
            description
                "Apply ingress filter";
            leaf ip {
              type uint32 {
                range "1..65535";
              }
            } //ip

            leaf mac {
              type uint32 {
                range "1..65535";
              }
              description
                  "filter-id";
            } //mac

            leaf ipv6 {
              type uint32 {
                range "1..65535";
              }
              description
                  "filter-id";
            } //ipv6

          } //container filter

          container qos {
            description
                "Configure ingress qos";
            leaf network-policy-id {
              type uint32 {
                range "1..65535";
              }
            } //network-policy-id

            leaf name {
              type string;
            } //name

            leaf fp-redirect-group {
              type string {
                length "1..32";
              }
            } //fp-redirect-group

            leaf instance {
              type uint16 {
                range "1..65535";
              }
            } //instance

          } //container qos

          container filter-name {
            presence
                "Apply ingress filter names";
            container ip {
              description
                  "Configure the IPv4 filter";
              leaf name {
                type string;
              } //name

            } //container ip

            container ipv6 {
              description
                  "Configure the IPv6 filter";
              leaf name {
                type string;
              } //name

            } //container ipv6

            container mac {
              description
                  "Configure the MAC filter";
              leaf name {
                type string;
              } //name

            } //container mac

          } //container filter-name

        } //container ingress

        container split-horizon-group {
          description
              "Configure a split horizon group";
          leaf group-name {
            type string {
              length "1..32";
            }
          } //group-name

          leaf auto-learn-mac-protect {
            type boolean;
            description
                "Enable/disable automatic update of MAC protect list";
          }

          container description {
            description
                "Description for this group";
            leaf description-string {
              type string {
                length "1..80";
              }
            } //description-string

          } //container description

          container restrict-protected-src {
            description
                "Enable/disable protected src MAC restriction";
            leaf alarm-only {
              type boolean;
              description
                  "keyword - only trap on a protected MAC";
            } //alarm-only

            leaf discard-frame {
              type boolean;
              description
                  "keyword - discard frame and trap on a protected MAC";
            } //discard-frame

          } //container restrict-protected-src

          leaf restrict-unprotected-dst {
            type boolean;
            description
                "Enable/disable unprotected dest MAC restriction";
          }

        } //container split-horizon-group

        container stp {
          description
              "Configure STP parameters";
          leaf auto-edge {
            type boolean;
            description
                "Enable/disable automatic detection of edge port";
          }

          leaf edge-port {
            type boolean;
            description
                "Configure spoke-sdp as edge port";
          }

          container link-type {
            description
                "Configure STP link type";
            leaf pt-pt-shared {
              type enumeration {
                enum pt-pt;
                enum shared;
              }
              description
                  "link type";
            } //pt-pt-shared

          } //container link-type

          container path-cost {
            description
                "Configure path-cost";
            leaf stp-path-cost {
              type uint32 {
                range "1..200000000";
              }
            } //stp-path-cost

          } //container path-cost

          container priority {
            description
                "Configure stp priority";
            leaf stp-priority {
              type uint32 {
                range "0..255";
              }
            } //stp-priority

          } //container priority

          leaf root-guard {
            type boolean;
            description
                "Enable/disable STP root-guard";
          }

          leaf shutdown {
            type boolean;
            description
                "Enable/disable spanning tree protocol";
          }

        } //container stp

      } //list pw-template

      uses "conf-svc-sdp-r13:alu-conf-svc-sdp-r13";
      container sdp-group {
        description
            "Configure a SDP group";
        list group-name {
          key "group-name";
          description
              "Configure a SDP group name";
          leaf group-name {
            type string {
              length "1..32";
            }
          } //group-name

          leaf value {
            type uint32 {
              range "0..31";
            }
          } //value

        } //list group-name

      } //container sdp-group

      container system {
        description
            "Configure service level system information";
        container bgp-auto-rd-range {
          description
              "Specify route-distinguisher community value range";
          leaf ip-address {
            type inet:ip-address;
          } //ip-address

          leaf comm-val {
            type uint32 {
              range "1..65535";
            }
          } //comm-val

          leaf to {
            type uint32 {
              range "1..65535";
            }
          } //to

        } //container bgp-auto-rd-range

        container fdb-table-size {
          description
              "Configure the maximum number of MAC entries in the FDB";
          leaf table-size {
            type string;
            description
                "Attribute table-size for fdb-table-size";
          } //table-size

        } //container fdb-table-size

        container vpn-gre-source-ip {
          description
              "Configure VPN GRE source IP address";
          leaf ip-address {
            type inet:ip-address;
          } //ip-address

        } //container vpn-gre-source-ip

        container bgp-evpn {
          description
              "Configure service system BGP EVPN information";
          container ad-per-es-route-target {
            description
                "Configure service BGP EVPN AD per-ES routes information";
            leaf evi-rt {
              type boolean;
              description
                  "keyword - Configure service BGP EVPN AD per-ES per EVI";
            } //evi-rt

            leaf evi-rt-set {
              type boolean;
              description
                  "keyword - Configure service BGP EVPN AD per-ES per EVI set";
            } //evi-rt-set

            leaf route-distinguisher {
              type inet:ip-address;
            } //route-distinguisher

          } //container ad-per-es-route-target

          leaf evpn-etree-leaf-label {
            type boolean;
            description
                "Enable/Disable EVPN Etree LEaf Label allocation";
          }

          container ingress-replication-bum-label-block {
            description
                "Configure segment routing local block";
            leaf reserved-label-block-name {
              type string;
            } //reserved-label-block-name

          } //container ingress-replication-bum-label-block

          container multicast-leave-sync-propagation {
            description
                "Configure multicast leave sync propagation time";
            leaf time {
              type int32 {
                range "0..300";
              }
              description
                  "[0..300]: default is 5 secs";
            } //time

          } //container multicast-leave-sync-propagation

          container route-distinguisher {
            description
                "Configure service BGP EVPN route-distinguisher information";
            leaf rd {
              type string {
                length "1..21";
              }
              default "system-ip:0";
              description
                  "<ip-addr:comm-val> 
                   ip-addr - a.b.c.d 
                   comm-val - [0..65535] 
                   default: system-ip:0 
                   ";
            } //rd

          } //container route-distinguisher

          list ethernet-segment {
            key "name";
            description
                "Configure service BGP EVPN ethernet segment information";
            leaf name {
              type string;
            } //name

            leaf virtual {
              type boolean;
            } //virtual

            container es-activation-timer {
              description
                  "Configure ethernet segment activation timer";
              leaf seconds {
                type uint32 {
                  range "0..100";
                }
              } //seconds

            } //container es-activation-timer

            container es-orig-ip {
              description
                  "Configure ES route's originating IP address.";
              leaf ip-address-ipv6-address {
                type string;
              } //ip-address-ipv6-address

            } //container es-orig-ip

            container esi {
              description
                  "Configure ethernet segment identifier";
              leaf esi {
                type string;
                description
                    "Attribute esi for esi";
              } //esi

            } //container esi

            container lag {
              description
                  "Configure lag for service BGP EVPN ethernet segment";
              leaf lag-id {
                type string;
                description
                    "Attribute lag-id for lag";
              } //lag-id

            } //container lag

            container multi-homing {
              description
                  "Configure multi-homing for service BGP EVPN ethernet segment";
              leaf single-active {
                type boolean;
              } //single-active

              leaf no-esi-label {
                type boolean;
              } //no-esi-label

              leaf all-active {
                type boolean;
              } //all-active

            } //container multi-homing

            container network-interconnect-vxlan {
              description
                  "Configure network interconnect vxlan information";
              leaf instance {
                type uint32 {
                }
              } //instance

            } //container network-interconnect-vxlan

            container oper-group {
              description
                  "Configure operational-group for the ethernet-segment";
              leaf name {
                type string;
              } //name

            } //container oper-group

            container port {
              description
                  "Configure port for service BGP EVPN ethernet segment";
              leaf port-id {
                type string {
                }
                description
                    "Attribute port-id for port";
              } //port-id

            } //container port

            container pw-port {
              description
                  "Configure pw-port for service BGP EVPN ethernet segment";
              leaf pw-port-id {
                type uint32 {
                  range "1..32767";
                }
              } //pw-port-id

            } //container pw-port

            container route-next-hop {
              description
                  "Configure next hop IP for ES and AD per-ES routes.";
              leaf ip-address-ipv6-address {
                type string;
              } //ip-address-ipv6-address

            } //container route-next-hop

            container sdp {
              description
                  "Configure sdp for service BGP EVPN ethernet segment";
              leaf sdp-id {
                type uint32 {
                  range "1..32767";
                }
              } //sdp-id

            } //container sdp

            leaf shutdown {
              type boolean;
              description
                  "Enable/disable administrative state of the ethernet segment";
            }

            container source-bmac-lsb {
              description
                  "Configure source BMAC address LSB information";
              leaf MAC-Lsb {
                type string;
                description
                    "[1..65535] or xx-xx or xx:xx";
              } //MAC-Lsb

              leaf es-bmac-table-size {
                type int32 {
                  range "1..511999";
                }
              } //es-bmac-table-size

            } //container source-bmac-lsb

            list vc-id-range {
              key "from";
              description
                  "Configure VC ID range";
              leaf from {
                type uint32 {
                  range "1..4294967295";
                }
              } //from

              leaf to {
                type uint32 {
                  range "1..4294967295";
                }
              } //to

            } //list vc-id-range

            container dot1q {
              description
                  "Configure dot1q port or lag information";
              list q-tag-range {
                key "qtag1";
                description
                    "Configure Dot1q Tag range";
                leaf qtag1 {
                  type string;
                  description
                      "Attribute qtag1 for q-tag-range";
                } //qtag1

                leaf to {
                  type string;
                  description
                      "qtag1";
                } //to

              } //list q-tag-range

            } //container dot1q

            container qinq {
              description
                  "Configure qinq port or lag information";
              list s-tag {
                key "qtag1 c-tag-range qtag2";
                description
                    "Configure C-Tag range information for a S-VLAN";
                leaf qtag1 {
                  type string;
                  description
                      "Attribute qtag1 for s-tag";
                } //qtag1

                leaf c-tag-range {
                  type boolean;
                } //c-tag-range

                leaf qtag2 {
                  type string;
                  description
                      "Attribute qtag2 for s-tag";
                } //qtag2

                leaf to {
                  type string;
                  description
                      "qtag2";
                } //to

              } //list s-tag

              list s-tag-range {
                key "qtag1";
                description
                    "Configure S-Tag range information";
                leaf qtag1 {
                  type string;
                  description
                      "Attribute qtag1 for s-tag-range";
                } //qtag1

                leaf to {
                  type string;
                  description
                      "qtag1";
                } //to

              } //list s-tag-range

            } //container qinq

            container service-carving {
              description
                  "Configure service carving mode for BGP EVPN ethernet segment";
              container mode {
                description
                    "Configure service carving for BGP EVPN ethernet segment";
                leaf auto-manual-off {
                  type enumeration {
                    enum auto;
                    enum manual;
                    enum off;
                  }
                  description
                      "auto|manual|off";
                } //auto-manual-off

              } //container mode

              container manual {
                description
                    "Configure manual service carving for BGP EVPN ethernet segment";
                list evi {
                  key "start";
                  description
                      "Configure EVI range (primary for non-preference based DF election and 
                       lowest-preference for preference based DF election)";
                  leaf start {
                    type int32 {
                      range "1..65535";
                    }
                  } //start

                  leaf to {
                    type int32 {
                      range "1..65535";
                    }
                  } //to

                  leaf primary {
                    type boolean;
                    status "obsolete";
                  } //primary

                } //list evi

                list isid {
                  key "start";
                  description
                      "Configure ISID range (primary for non-preference based DF election and 
                       lowest-preference for preference based DF election)";
                  leaf start {
                    type int32 {
                      range "1..16777215";
                    }
                  } //start

                  leaf to {
                    type int32 {
                      range "1..16777215";
                    }
                  } //to

                  leaf primary {
                    type boolean;
                    status "obsolete";
                  } //primary

                } //list isid

                container preference {
                  description
                      "Configure DF preference election information";
                  leaf non-revertive {
                    type boolean;
                  } //non-revertive

                  container value {
                    description
                        "Configure DF preference value";
                    leaf value {
                      type uint32 {
                        range "0..65535";
                      }
                    } //value

                  } //container value

                } //container preference

              } //container manual

            } //container service-carving

            container service-id {
              description
                  "Configure service id vxlan information under ethernet segment";
              list service-range {
                key "svc-id";
                description
                    "Configure service range information";
                leaf svc-id {
                  type uint32 {
                    range "1..2147483647";
                  }
                } //svc-id

                leaf to {
                  type uint32 {
                    range "1..2147483647";
                  }
                } //to

              } //list service-range

            } //container service-id

          } //list ethernet-segment

        } //container bgp-evpn

        container gre-eth-bridged {
          description
              "Configure GRE tunnel information";
          list tunnel-termination {
            key "ip-address-ipv6-address";
            description
                "Configure gre ethernet tunnel-termination ip information";
            leaf ip-address-ipv6-address {
              type string;
            } //ip-address-ipv6-address

            leaf fpe {
              type uint32 {
                range "1..64";
              }
            } //fpe

          } //list tunnel-termination

        } //container gre-eth-bridged

        container pw-port-list {
          description
              "Configure Port List binding to Flex PW Ports";
          list port {
            key "port-id";
            description
                "Configure Port List binding to Flex PW Ports";
            leaf port-id {
              type string;
              description
                  "Attribute port-id for port";
            } //port-id

          } //list port

        } //container pw-port-list

        container vxlan {
          description
              "Configure vxlan information";
          container assisted-replication-ip {
            description
                "Configure vxlan tunnel assisted replication ip information";
            leaf ip-address {
              type inet:ip-address;
            } //ip-address

          } //container assisted-replication-ip

          list tunnel-termination {
            key "ip-address";
            description
                "Configure vxlan tunnel-termination ip information";
            leaf ip-address {
              type string;
              description
                  "Attribute ip-address for tunnel-termination";
            } //ip-address

            leaf fpe {
              type uint32 {
                range "1..64";
              }
            } //fpe

          } //list tunnel-termination

        } //container vxlan

      } //container system

      uses "conf-svc-template-r13:alu-conf-svc-template-r13";
      uses "conf-svc-upnp-r13:alu-conf-svc-upnp-r13";
      uses "conf-svc-vpls-r13:alu-conf-svc-vpls-r13";
      uses "conf-svc-vprn-r13:alu-conf-svc-vprn-r13";
      container vsd {
        description
            "Configure Virtualised Services Directory";
        container service-range {
          description
              "Specify service-range for VSD";
          leaf svc-id {
            type uint32 {
              range "1..2147483647";
            }
          } //svc-id

          leaf to {
            type uint32 {
              range "1..2147483647";
            }
            description
                "svc-id";
          } //to

        } //container service-range

        list domain {
          key "name";
          description
              "Configure VSD Domain";
          leaf name {
            type string;
          } //name

          leaf type {
            type enumeration {
              enum l2-domain;
              enum vrf-gre;
              enum vrf-vxlan;
              enum l2-domain-irb;
            }
          } //type

          container description {
            description
                "Set VSD Domain Description";
            leaf description-string {
              type string {
                length "1..80";
              }
            } //description-string

          } //container description

          leaf shutdown {
            type boolean;
            description
                "Administratively enable/disable the domain";
          }

        } //list domain

      } //container vsd

    } //container service

  } //grouping alu-conf-service-r13

} //module  alu-conf-service-r13
