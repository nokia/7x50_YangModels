module alu-conf-isa-r13 {
  yang-version "1";

  namespace "urn:alcatel-lucent.com:sros:ns:yang:conf-isa-r13";

  prefix "conf-isa-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure Integrated Services Adaptors on SR 
       OS based routers. 
       
       Copyright 2014-2015 Alcatel-Lucent, 2016 Nokia. All rights reserved. 
       Reproduction of this document is authorized on the condition that the 
       foregoing copyright notice is included. 
       
       This alu-conf-isa-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-11-09";

  grouping alu-conf-isa-r13 {
    container isa {
      description
          "Configure Integrated Services Adaptors";
      list application-assurance-group {
        key "aa-group-id";
        description
            "Configure an ISA Application Assurance Group";
        leaf aa-group-id {
          type uint32 {
            range "1..255";
          }
        } //aa-group-id

        leaf aa-sub-scale {
          type enumeration {
            enum residential;
            enum vpn;
            enum mobile-gateway;
            enum lightweight-internet;
            enum residential-8k;
            enum residential-16k;
            enum residential-32k;
            enum residential-64k;
            enum vpn-1k;
            enum vpn-2k;
            enum vpn-4k;
            enum vpn-8k;
            enum mobile-gateway-1m;
            enum mobile-gateway-2m;
            enum lightweight-internet-512k;
          }
          description
              "Attribute sub-scale for application-assurance-group";
        } //aa-sub-scale

        list backup {
          key "mda-id-esa-vm-id";
          description
              "Configure ISA-AA-Group backup ISA-AA";
          leaf mda-id-esa-vm-id {
            type string {
              length "1..8";
            }
            description
                "Attribute mda-id/esa-vm-id for backup";
          } //mda-id-esa-vm-id

        } //list backup

        container description {
          description
              "Configure ISA-AA-Group description";
          leaf description {
            type string {
              length "1..80";
            }
          } //description

        } //container description

        list divert-fc {
          key "fc-name";
          description
              "Configure ISA-AA-Group forwarding classes that divert";
          leaf fc-name {
            type enumeration {
              enum be;
              enum l2;
              enum af;
              enum l1;
              enum h2;
              enum ef;
              enum h1;
              enum nc;
            }
            description
                "<be|l2|af|l1|h2|ef|h1|nc> - keywords";
          } //fc-name

        } //list divert-fc

        leaf fail-to-open {
          type boolean;
          description
              "Configure ISA-AA-Group failure mode";
        }

        list flow-attribute {
          key "flow-attribute-name";
          description
              "Enable or disable flow attributes for this ISA application assurance group";
          leaf flow-attribute-name {
            type string {
            }
          } //flow-attribute-name

        } //list flow-attribute

        leaf flow-attributes {
          type boolean;
          status "obsolete";
          description
              "Enable or disable flow attributes for this ISA application assurance group";
        }

        container http-enrich-max-pkt {
          description
              "Configure the maximum HTTP enriched packet size";
          leaf size-in-octets {
            type uint32 {
              range "576..9212";
            }
            default 1500;
            description
                "[576..9212] - Default: 1500";
          } //size-in-octets

        } //container http-enrich-max-pkt

        container isa-capacity-cost-high-threshold {
          description
              "Configure ISA-AA capacity cost high threshold";
          leaf threshold {
            type uint32;
          } //threshold

        } //container isa-capacity-cost-high-threshold

        container isa-capacity-cost-low-threshold {
          description
              "Configure ISA-AA capacity cost low threshold";
          leaf threshold {
            type uint32;
          } //threshold

        } //container isa-capacity-cost-low-threshold

        leaf isa-overload-cut-through {
          type boolean;
          description
              "Enable/disable cut-through processing on overload";
        }

        container minimum-isa-generation {
          description
              "Configure the minimum ISA generation";
          leaf min-isa-generation {
            type uint32 {
              range "1..2";
            }
          } //min-isa-generation

        } //container minimum-isa-generation

        leaf partitions {
          type boolean;
          description
              "Configure ISA-AA-Group partition mode";
        }

        list primary {
          key "mda-id-esa-vm-id";
          description
              "Configure ISA-AA-Group primary ISA-AA";
          leaf mda-id-esa-vm-id {
            type string {
              length "1..8";
            }
            description
                "Attribute mda-id/esa-vm-id for primary";
          } //mda-id-esa-vm-id

        } //list primary

        leaf shutdown {
          type boolean;
          description
              "Administratively enable/disable an ISA-AA-Group";
        }

        container transit-prefix-ipv4-entries {
          description
              "Configure ISA-AA-Group per MDA transit prefix IPv4 entry limit";
          leaf entries {
            type string;
            description
                "Attribute entries for transit-prefix-ipv4-entries";
          } //entries

        } //container transit-prefix-ipv4-entries

        container transit-prefix-ipv4-remote-entries {
          description
              "Configure ISA-AA-Group per MDA transit prefix IPv4 remote entry limit";
          leaf entries {
            type uint32;
            description
                "Attribute entries for transit-prefix-ipv4-remote-entries";
          } //entries

        } //container transit-prefix-ipv4-remote-entries

        container transit-prefix-ipv6-entries {
          description
              "Configure ISA-AA-Group per MDA transit prefix IPv6 entry limit";
          leaf entries {
            type uint32;
            description
                "Attribute entries for transit-prefix-ipv6-entries";
          } //entries

        } //container transit-prefix-ipv6-entries

        container transit-prefix-ipv6-remote-entries {
          description
              "Configure ISA-AA-Group per MDA transit prefix IPv6 remote entry limit";
          leaf entries {
            type uint32;
            description
                "Attribute entries for transit-prefix-ipv6-remote-entries";
          } //entries

        } //container transit-prefix-ipv6-remote-entries

        leaf vm-traffic-distribution-by-ip {
          type boolean;
          description
              "Configure the ISA VM traffic distribution by IP";
        }

        leaf vm-traffic-distribution-by-teid {
          type boolean;
          description
              "Configure the ISA VM traffic distribution by TEID";
        }

        container overload-sub-quarantine {
          description
              "Configure the ISA overload sub quarantine";
          leaf shutdown {
            type boolean;
            description
                "Administrively enable/disable overload sub quarantine";
          }

        } //container overload-sub-quarantine

        container qos {
          description
              "Configure QoS parameters for this ISA-AA group";
          container egress {
            description
                "Configure egress QoS parameters for this ISA-AA group";
            container from-subscriber {
              description
                  "Configure egress from-subscriber QoS parameters for this ISA-AA group";
              container port-scheduler-policy {
                description
                    "Configure egress from-subscriber port-scheduler-policy for this ISA-AA group";
                leaf port-scheduler-policy-name {
                  type string {
                    length "1..32";
                  }
                } //port-scheduler-policy-name

              } //container port-scheduler-policy

              container queue-policy {
                description
                    "Configure egress from-subscriber network queue-policy for this ISA-AA group";
                leaf network-queue-policy-name {
                  type string {
                    length "1..32";
                  }
                } //network-queue-policy-name

              } //container queue-policy

              container wa-shared-high-wmark {
                description
                    "Configure weighted average shared buffer utilization high watermark";
                leaf percent {
                  type string;
                  description
                      "[1..100 | max] percent - default max = disabled";
                } //percent

                leaf max {
                  type boolean;
                } //max

              } //container wa-shared-high-wmark

              container wa-shared-low-wmark {
                description
                    "Configure weighted average shared buffer utilization low watermark";
                leaf percent {
                  type uint32 {
                    range "0..99";
                  }
                } //percent

              } //container wa-shared-low-wmark

              container pool {
                description
                    "Configure egress from-subscriber pool for this ISA-AA group";
                leaf pool-name {
                  type string {
                    length "1..32";
                  }
                } //pool-name

                container resv-cbs {
                  description
                      "Configure egress from-subscriber reserved CBS for this ISA-AA group";
                  leaf percent-or-default {
                    type string;
                    description
                        "[0..100] or \"default\"";
                  } //percent-or-default

                } //container resv-cbs

                container slope-policy {
                  description
                      "Configure egress from-subscriber slope policy for this ISA-AA group";
                  leaf slope-policy-name {
                    type string {
                      length "1..32";
                    }
                  } //slope-policy-name

                } //container slope-policy

              } //container pool

            } //container from-subscriber

            container to-subscriber {
              description
                  "Configure egress to-subscriber QoS parameters for this ISA-AA group";
              container port-scheduler-policy {
                description
                    "Configure egress to-subscriber port-scheduler-policy for this ISA-AA group";
                leaf port-scheduler-policy-name {
                  type string {
                    length "1..32";
                  }
                } //port-scheduler-policy-name

              } //container port-scheduler-policy

              container queue-policy {
                description
                    "Configure egress to-subscriber network queue-policy for this ISA-AA group";
                leaf network-queue-policy-name {
                  type string {
                    length "1..32";
                  }
                } //network-queue-policy-name

              } //container queue-policy

              container wa-shared-high-wmark {
                description
                    "Configure weighted average shared buffer utilization high watermark";
                leaf percent {
                  type string;
                  description
                      "[1..100 | max] percent - default max = disabled";
                } //percent

                leaf max {
                  type boolean;
                } //max

              } //container wa-shared-high-wmark

              container wa-shared-low-wmark {
                description
                    "Configure weighted average shared buffer utilization low watermark";
                leaf percent {
                  type uint32 {
                    range "0..99";
                  }
                } //percent

              } //container wa-shared-low-wmark

              container pool {
                description
                    "Configure egress to-subscriber pool for this ISA-AA group";
                leaf pool-name {
                  type string {
                    length "1..32";
                  }
                } //pool-name

                container resv-cbs {
                  description
                      "Configure egress to-subscriber reserved CBS for this ISA-AA group";
                  leaf percent-or-default {
                    type string;
                    description
                        "[0..100|default]";
                  } //percent-or-default

                } //container resv-cbs

                container slope-policy {
                  description
                      "Configure egress to-subscriber slope policy for this ISA-AA group";
                  leaf slope-policy-name {
                    type string {
                      length "1..32";
                    }
                  } //slope-policy-name

                } //container slope-policy

              } //container pool

            } //container to-subscriber

          } //container egress

        } //container qos

        container shared-resources {
          description
              "Configure the shared resources pool";
          container gtp-tunnel-database {
            description
                "Configure the allocation of shared resource pool for stateful GTP firewall 
                 functions";
            leaf size {
              type uint32 {
                range "0..100";
              }
              description
                  "[0 - 100] - default 0";
            } //size

          } //container gtp-tunnel-database

          container web-service-url-filter {
            description
                "Configure the allocation of shared resource pool for web service url filters";
            leaf size {
              type uint32 {
                range "0..100";
              }
              description
                  "[0 - 100] - default 0";
            } //size

          } //container web-service-url-filter

        } //container shared-resources

        container statistics {
          description
              "Configure statistics generation";
          container performance {
            description
                "Configure performance statistics for this ISA-AA group";
            container accounting-policy {
              description
                  "Configure accounting-policy to be used";
              leaf acct-policy-id {
                type uint64 {
                  range "1..99";
                }
              } //acct-policy-id

            } //container accounting-policy

            leaf collect-stats {
              type boolean;
              description
                  "Enable/Disable statistics collection";
            }

          } //container performance

        } //container statistics

      } //list application-assurance-group

      list lns-group {
        key "lns-group-id";
        description
            "Configure an ISA LNS Group";
        leaf lns-group-id {
          type uint32 {
            range "1..4";
          }
        } //lns-group-id

        container description {
          description
              "Configure the ISA LNS group description";
          leaf description-string {
            type string {
              length "1..80";
            }
          } //description-string

        } //container description

        list esa-vm {
          key "vapp-id";
          description
              "Configure an ISA LNS group ESA VM";
          leaf vapp-id {
            type string {
            }
            description
                "Attribute vapp-id for esa-vm";
          } //vapp-id

          leaf drain {
            type boolean;
            description
                "Start/stop draining this esa-vm";
          } //drain

        } //list esa-vm

        list mda {
          key "mda-id";
          description
              "Configure an ISA LNS group MDA";
          leaf mda-id {
            type string {
              length "1..4";
            }
            description
                "Attribute mda-id for mda";
          } //mda-id

          leaf drain {
            type boolean;
            description
                "Start/stop draining this mda";
          } //drain

        } //list mda

        container port-policy {
          description
              "Configure the ISA LNS group port policy";
          leaf policy-name {
            type string {
              length "1..32";
            }
          } //policy-name

        } //container port-policy

        leaf shutdown {
          type boolean;
          description
              "Administratively enable/disable the ISA LNS group";
        }

      } //list lns-group

      list nat-group {
        key "nat-group-id";
        description
            "Configure an ISA NAT Group";
        leaf nat-group-id {
          type uint32 {
            range "1..4";
          }
        } //nat-group-id

        container active-mda-limit {
          description
              "Configure the ISA NAT group maximum number of MDA";
          leaf number {
            type uint32 {
              range "1..14";
            }
          } //number

        } //container active-mda-limit

        container description {
          description
              "Configure the ISA NAT group description";
          leaf description-string {
            type string {
              length "1..80";
            }
          } //description-string

        } //container description

        list esa-vm {
          key "vapp-id";
          description
              "Configure an ISA NAT group ESA VM";
          leaf vapp-id {
            type string {
            }
            description
                "Attribute vapp-id for esa-vm";
          } //vapp-id

        } //list esa-vm

        container failed-mda-limit {
          description
              "Configure the maximum number of failed ISA MDA in active/active mode";
          leaf failed-mda-limit-id {
            type uint32 {
              range "1..2";
            }
          } //failed-mda-limit-id

        } //container failed-mda-limit

        container load-balancing {
          status "obsolete";
          description
              "Configure the load balancing profile";
          leaf selection {
            type enumeration {
              enum profile-1;
              enum profile-2;
            }
          } //selection

        } //container load-balancing

        list mda {
          key "mda-id";
          description
              "Configure an ISA NAT group MDA";
          leaf mda-id {
            type string {
              length "1..4";
            }
            description
                "Attribute mda-id for mda";
          } //mda-id

        } //list mda

        container radius-accounting-policy {
          description
              "Configure the ISA NAT group RADIUS accounting policy";
          leaf nat-accounting-policy {
            type string {
              length "1..32";
            }
          } //nat-accounting-policy

        } //container radius-accounting-policy

        container redundancy {
          description
              "Configure the intra-chassis redundancy mode of operation";
          leaf redundancy-id {
            type enumeration {
              enum active-active;
              enum active-standby;
              enum l2aware-bypass;
              enum inter-chassis;
            }
          } //redundancy-id

        } //container redundancy

        container scaling-profile {
          description
              "Configure the ISA scaling profile";
          leaf scaling-profile-id {
            type enumeration {
              enum profile1;
              enum profile2;
              enum profile3;
            }
          } //scaling-profile-id

        } //container scaling-profile

        leaf shutdown {
          type boolean;
          description
              "Administratively enable/disable the ISA NAT group";
        }

        leaf suppress-lsn-events {
          type boolean;
          description
              "Suppress the generation of Large Scale NAT (LSN) events when RADIUS accounting 
               is enabled";
        }

        leaf suppress-lsn-sub-blks-free {
          type boolean;
          description
              "Suppress the tmnxNatLsnSubBlksFree summary notification and use the 
               tmnxNatPlBlockAllocationLsn notifications";
        }

        container inter-chassis-redundancy {
          description
              "Configure inter-chassis redundancy";
          container flow-timeout-on-switchover {
            description
                "Configure the part of the flow timeout applied after a switchover";
            leaf percent {
              type uint32 {
                range "1..50";
              }
            } //percent

          } //container flow-timeout-on-switchover

          container ip-mtu {
            description
                "Configure the IP MTU for ISA-to-ISA communication";
            leaf bytes {
              type uint32 {
                range "512..9000";
              }
            } //bytes

          } //container ip-mtu

          container keepalive {
            description
                "Configure the keepalive timer and drop count";
            leaf deciseconds {
              type uint32 {
                range "2..250";
              }
            } //deciseconds

            leaf dropcount {
              type uint32 {
                range "2..20";
              }
            } //dropcount

          } //container keepalive

          container local-ip-range-start {
            description
                "Configure the start of the IP address range the ISAs in this system's NAT 
                 group use for ISA-to-ISA communication";
            leaf ip-address {
              type inet:ip-address;
              description
                  "a.b.c.d";
            } //ip-address

          } //container local-ip-range-start

          list monitor-oper-group {
            key "name";
            description
                "Configure monitoring operational-groups";
            leaf name {
              type string;
            } //name

            leaf health-drop {
              type uint32 {
                range "1..255";
              }
            } //health-drop

          } //list monitor-oper-group

          list monitor-port {
            key "port-id";
            description
                "Configure monitoring ports";
            leaf port-id {
              type string {
                length "1..32";
              }
              description
                  "slot/mda/port or lag-<lag-id>";
            } //port-id

            leaf health-drop {
              type uint32 {
                range "1..255";
              }
            } //health-drop

          } //list monitor-port

          leaf preferred {
            type boolean;
            description
                "Configure if this system is the preferred active system for this ISA NAT group 
                 if both systems have equal health";
          }

          container remote-ip-range-start {
            description
                "Configure the start of the IP address range the ISAs in the peer system's NAT 
                 group use for ISA-to-ISA communication";
            leaf ip-address {
              type inet:ip-address;
              description
                  "a.b.c.d";
            } //ip-address

          } //container remote-ip-range-start

          container replication-threshold {
            description
                "Configure the time before a NAT traffic flow is synchronized with the peer";
            leaf seconds {
              type uint32 {
                range "0..300";
              }
            } //seconds

          } //container replication-threshold

          container router {
            description
                "Configure the router instance for ISA-to-ISA communication";
            leaf router-instance {
              type string;
              description
                  "Attribute router-instance for router";
            } //router-instance

          } //container router

        } //container inter-chassis-redundancy

        container session-limits {
          description
              "Configure the ISA NAT group session limits";
          container reserved {
            description
                "Configure the number of sessions reserved for prioritized sessions";
            leaf num-sessions {
              type uint32 {
                range "0..6291456";
              }
            } //num-sessions

          } //container reserved

          container upnp-mappings {
            description
                "Limit the number of Universal Plug 'n Play mappings per member";
            leaf upnp-mappings-id {
              type uint32 {
                range "1..524288";
              }
            } //upnp-mappings-id

          } //container upnp-mappings

          container watermarks {
            description
                "Configure the ISA NAT group watermarks";
            leaf high {
              type uint32 {
                range "1..100";
              }
            } //high

            leaf low {
              type uint32 {
                range "0..99";
              }
            } //low

          } //container watermarks

        } //container session-limits

      } //list nat-group

      list tunnel-group {
        key "tunnel-group-id";
        description
            "Configure an ISA Tunnel Group";
        leaf tunnel-group-id {
          type string;
          description
              "Attribute tunnel-group-id for tunnel-group";
        } //tunnel-group-id

        leaf isa-scale-mode {
          type enumeration {
            enum tunnel-limit-2k;
            enum tunnel-limit-32k;
            enum tunnel-limit-64k;
            enum tunnel-limit-8;
            enum tunnel-limit-32;
          }
          description
              "Attribute isa-scale-mode for tunnel-group";
        } //isa-scale-mode

        container active-mda-number {
          description
              "Configure number of active MDAs";
          leaf active-mda-number-id {
            type uint32 {
              range "1..16";
            }
          } //active-mda-number-id

        } //container active-mda-number

        container backup {
          description
              "Configure ISA-Tunnel-Group backup ISA";
          leaf mda-id {
            type string {
              length "1..4";
            }
            description
                "Attribute mda-id for backup";
          } //mda-id

        } //container backup

        container description {
          description
              "Configure the ISA group description";
          leaf description-string {
            type string {
              length "1..80";
            }
          } //description-string

        } //container description

        list esa-vm {
          key "esa-id-vm-id";
          description
              "Configure the esa-vm";
          leaf esa-id-vm-id {
            type string {
              length "1..8";
            }
            description
                "Attribute esa-id/vm-id for esa-vm";
          } //esa-id-vm-id

        } //list esa-vm

        leaf ipsec-responder-only {
          type boolean;
          description
              "Enable/Disable responder-only for IPsec Ikev2 tunnels only";
        }

        list mda {
          key "mda";
          description
              "Configure MDA to associate with";
          leaf mda {
            type string {
              length "1..32";
            }
            description
                "slot/mda";
          } //mda

        } //list mda

        leaf multi-active {
          type boolean;
          description
              "Configure multi-active status of tunnel-group";
        }

        container primary {
          description
              "Configure ISA-Tunnel-Group primary ISA";
          leaf mda-id {
            type string {
              length "1..4";
            }
            description
                "Attribute mda-id for primary";
          } //mda-id

        } //container primary

        container reassembly {
          description
              "Configure reassembly wait time";
          leaf wait-msecs {
            type int32 {
              range "1..5000";
            }
            description
                "[1..5000] milli-secs in 100 increments";
          } //wait-msecs

        } //container reassembly

        leaf shutdown {
          type boolean;
          description
              "Administratively enable/disable an ISA-Tunnel-Group";
        }

        container stats-collection {
          description
              "Configure ISA statistics collection parameters";
          leaf gw-traffic-forward {
            type boolean;
            status "obsolete";
            description
                "Enable/disable the gateway traffic forwarding statistics collection";
          }

          leaf isa-dp-cpu-usage {
            type boolean;
            description
                "Enable/disable the data-plane CPU usage historical statistics collection";
          }

        } //container stats-collection

      } //list tunnel-group

      list video-group {
        key "video-group-id";
        description
            "Configure an ISA Video Group";
        leaf video-group-id {
          type uint32 {
            range "1..4";
          }
        } //video-group-id

        leaf ad-insert {
          type boolean;
          description
              "Enable/disable ad insert server for the group";
        }

        leaf analyzer {
          type boolean;
          description
              "Enable/disable analyzer for the group";
        }

        container description {
          description
              "Configure video group description";
          leaf description-string {
            type string {
              length "1..80";
            }
          } //description-string

        } //container description

        leaf enable-rt-client {
          type boolean;
          description
              "Enable/Disable Retransmission for client for the group";
        }

        leaf fcc-server {
          type boolean;
          description
              "Enable/disable FCC server for the group";
        }

        leaf local-rt-server {
          type boolean;
          description
              "Enable/disable local RT server for the group";
        }

        list primary {
          key "mda-id";
          description
              "Configure video group primary ISA";
          leaf mda-id {
            type string {
              length "1..4";
            }
            description
                "Attribute mda-id for primary";
          } //mda-id

        } //list primary

        container resv-ret {
          description
              "Configure reserve RET bandwidth";
          leaf resv-ret {
            type uint32;
            description
                "in Mbps";
          } //resv-ret

        } //container resv-ret

        leaf shutdown {
          type boolean;
          description
              "Administratively enable/disable a video group";
        }

        leaf stream-selection {
          type boolean;
          description
              "Enable/disable stream-selection for the group";
        }

        container watermark {
          description
              "Configure ISA watermark";
          container bandwidth {
            description
                "Configure watermark for bandwidth";
            container fcc {
              description
                  "Configure FCC bandwidth watermark";
              leaf percent {
                type uint32 {
                  range "1..99";
                }
                default 90;
                description
                    "[1..99] - Default: 90";
              } //percent

            } //container fcc

            container ret {
              description
                  "Configure RET bandwidth watermark";
              leaf percent {
                type uint32 {
                  range "1..99";
                }
                default 90;
                description
                    "[1..99] - Default: 90";
              } //percent

            } //container ret

            container total {
              description
                  "Configure total bandwidth watermark";
              leaf percent {
                type uint32 {
                  range "1..99";
                }
                default 90;
                description
                    "[1..99] - Default: 90";
              } //percent

            } //container total

          } //container bandwidth

          container session {
            description
                "Configure watermark for sessions";
            container fcc {
              description
                  "Configure FCC session watermark";
              leaf percent {
                type uint32 {
                  range "1..99";
                }
                default 90;
                description
                    "[1..99] - Default: 90";
              } //percent

            } //container fcc

            container ret {
              description
                  "Configure RET session watermark";
              leaf percent {
                type uint32 {
                  range "1..99";
                }
                default 90;
                description
                    "[1..99] - Default: 90";
              } //percent

            } //container ret

            container total {
              description
                  "Configure total session watermark";
              leaf percent {
                type uint32 {
                  range "1..99";
                }
                default 90;
                description
                    "[1..99] - Default: 90";
              } //percent

            } //container total

          } //container session

        } //container watermark

      } //list video-group

      list wlan-gw-group {
        key "wlan-gw-group-id";
        description
            "Configure an ISA WLAN Gateway Group";
        leaf wlan-gw-group-id {
          type uint32 {
            range "1..4";
          }
        } //wlan-gw-group-id

        leaf redundancy {
          type enumeration {
            enum iom;
            enum mda;
          }
        } //redundancy

        container active-iom-limit {
          description
              "Configure the ISA WLAN-GW group maximum number of IOM";
          leaf number {
            type string;
            description
                "Attribute number for active-iom-limit";
          } //number

        } //container active-iom-limit

        container active-mda-limit {
          description
              "Configure the ISA WLAN-GW group maximum number of MDA";
          leaf number {
            type uint32 {
              range "1..14";
            }
          } //number

        } //container active-mda-limit

        container description {
          description
              "Configure the ISA WLAN-GW group description";
          leaf description-string {
            type string {
              length "1..80";
            }
          } //description-string

        } //container description

        list esa-vm {
          key "vapp-id";
          description
              "Configure an ISA WLAN-GW group ESA VM";
          leaf vapp-id {
            type string {
            }
            description
                "Attribute vapp-id for esa-vm";
          } //vapp-id

        } //list esa-vm

        list iom {
          key "slot-number";
          description
              "Configure an ISA WLAN-GW group IOM";
          leaf slot-number {
            type string;
            description
                "Attribute slot-number for iom";
          } //slot-number

          leaf application {
            type boolean;
          } //application

          leaf load-balancing {
            type boolean;
          } //load-balancing

          leaf ue-anchoring {
            type boolean;
          } //ue-anchoring

        } //list iom

        list mda {
          key "mda-id";
          description
              "Configure an ISA WLAN-GW group MDA";
          leaf mda-id {
            type string {
              length "1..4";
            }
            description
                "Attribute mda-id for mda";
          } //mda-id

        } //list mda

        container port-policy {
          description
              "Configure the ISA WLAN-GW group port policy";
          leaf port-policy-string {
            type string {
              length "1..32";
            }
          } //port-policy-string

        } //container port-policy

        container scaling-profile {
          description
              "Configure the ISA scaling profile";
          leaf scaling-profile-id {
            type enumeration {
              enum profile1;
              enum profile2;
              enum profile3;
            }
          } //scaling-profile-id

        } //container scaling-profile

        leaf shutdown {
          type boolean;
          description
              "Administratively enable/disable the ISA WLAN-GW group";
        }

        container tunnel-port-policy {
          description
              "Configure the ISA WLAN-GW group port policy for per-tunnel QoS processing";
          leaf tunnel-port-policy-string {
            type string;
          } //tunnel-port-policy-string

        } //container tunnel-port-policy

        container distributed-sub-mgmt {
          presence
              "Configure WLAN Gateway distributed subscriber management";
          container isa-aa-group {
            description
                "Configure an ISA Application Assurance Group for WLAN Gateway dsm subscribers";
            leaf aa-group-id {
              type uint32 {
                range "1..255";
              }
            } //aa-group-id

          } //container isa-aa-group

          container isa-aa-oversubscription-factor {
            description
                "Configure the factor of oversubscription of the WLAN-GW MDA to the AA MDA";
            leaf factor {
              type uint32 {
                range "1..10";
              }
            } //factor

          } //container isa-aa-oversubscription-factor

        } //container distributed-sub-mgmt

        container nat {
          description
              "Configure NAT for an ISA WLAN-GW group";
          container load-balancing {
            status "obsolete";
            description
                "Configure the load balancing profile";
            leaf selection {
              type enumeration {
                enum profile-1;
                enum profile-2;
              }
            } //selection

          } //container load-balancing

          leaf lsn {
            type boolean;
            description
                "Enable/disable Large Scale NAT";
          }

          container radius-accounting-policy {
            description
                "Configure the ISA WLAN-GW group NAT RADIUS accounting policy";
            leaf nat-accounting-policy {
              type string {
                length "1..32";
              }
            } //nat-accounting-policy

          } //container radius-accounting-policy

          leaf suppress-lsn-events {
            type boolean;
            description
                "Suppress the generation of Large Scale NAT (LSN) events when RADIUS accounting 
                 is enabled";
          }

          leaf suppress-lsn-sub-blks-free {
            type boolean;
            description
                "Suppress the tmnxNatLsnSubBlksFree summary notification and use the 
                 tmnxNatPlBlockAllocationLsn notifications";
          }

          container session-limits {
            description
                "Configure the ISA WLAN-GW NAT group session limits";
            container reserved {
              description
                  "Configure the number of sessions reserved for prioritized sessions";
              leaf num-sessions {
                type uint32 {
                  range "0..6291456";
                }
              } //num-sessions

            } //container reserved

            container upnp-mappings {
              description
                  "Limit the number of Universal Plug 'n Play mappings per member";
              leaf upnp-mappings-id {
                type uint32 {
                  range "1..524288";
                }
              } //upnp-mappings-id

            } //container upnp-mappings

            container watermarks {
              description
                  "Configure the ISA NAT group watermarks";
              leaf high {
                type uint32 {
                  range "1..100";
                }
              } //high

              leaf low {
                type uint32 {
                  range "0..99";
                }
              } //low

            } //container watermarks

          } //container session-limits

        } //container nat

        container watermarks {
          description
              "Configure per-member watermarks for the number of user-equipment, 
               bridge-domain, radius-proxy-client";
          list mark {
            key "entity";
            description
                "Configure a set of high and low watermarks";
            leaf entity {
              type enumeration {
                enum user-equipment;
                enum bridge-domain;
                enum radius-proxy-client;
              }
            } //entity

            leaf high {
              type uint32 {
                range "1..100";
              }
            } //high

            leaf low {
              type uint32 {
                range "0..99";
              }
            } //low

          } //list mark

        } //container watermarks

      } //list wlan-gw-group

    } //container isa

  } //grouping alu-conf-isa-r13

} //module  alu-conf-isa-r13
