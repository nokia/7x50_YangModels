module alu-conf-sys-sec-r13 {
  yang-version "1";

  namespace "urn:alcatel-lucent.com:sros:ns:yang:conf-sys-sec-r13";

  prefix "conf-sys-sec-r13";

  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure system security related parameters 
       on SR OS based routers. 
       
       Copyright 2014-2015 Alcatel-Lucent, 2016 Nokia. All rights reserved. 
       Reproduction of this document is authorized on the condition that the 
       foregoing copyright notice is included. 
       
       This alu-conf-sys-sec-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-08-24";

  grouping alu-conf-sys-sec-r13 {
    container security {
      description
          "Configure system security related parameters";
      container copy {
        description
            "Copy a profile or user";
        leaf user {
          type string {
            length "1..32";
          }
        } //user

        leaf profile {
          type string {
            length "1..32";
          }
        } //profile

        leaf to {
          type string {
            length "1..32";
          }
        } //to

        leaf overwrite {
          type boolean;
        } //overwrite

      } //container copy

      leaf ftp-server {
        type boolean;
        description
            "Start/Stop FTP server";
      }

      container hash-control {
        status "obsolete";
        description
            "Specify hash read/write version";
        leaf read-version {
          type enumeration {
            enum 1;
            enum 2;
            enum all;
          }
          description
              "keywords";
        } //read-version

        leaf write-version {
          type enumeration {
            enum 1;
            enum 2;
          }
          description
              "keywords";
        } //write-version

      } //container hash-control

      leaf per-peer-queuing {
        type boolean;
        description
            "Enable/disable CPM hardware queuing per peer";
      }

      leaf telnet-server {
        type boolean;
        description
            "Start/Stop telnet server";
      }

      leaf telnet6-server {
        type boolean;
        description
            "Start/Stop telnet IPv6 server";
      }

      container vprn-network-exceptions {
        description
            "Configure rate for MPLS Exception messages";
        leaf number {
          type int32 {
            range "1..1000";
          }
        } //number

        leaf seconds {
          type int32 {
            range "1..60";
          }
        } //seconds

      } //container vprn-network-exceptions

      container cli-script {
        description
            "cli-script for vsd server, cron, event-handler";
        container authorization {
          description
              "authorization for cli-script execution";
          container cron {
            description
                "cli-script authorization for cron";
            container cli-user {
              description
                  "cli-user authorized for script execution";
              leaf user-name {
                type string {
                  length "1..32";
                }
              } //user-name

            } //container cli-user

          } //container cron

          container event-handler {
            description
                "cli-script authorization for event-handler";
            container cli-user {
              description
                  "cli-user authorized for script execution";
              leaf user-name {
                type string {
                  length "1..32";
                }
              } //user-name

            } //container cli-user

          } //container event-handler

          container vsd {
            description
                "cli-script execution authorized vsd server";
            container cli-user {
              description
                  "cli-user authorized for script execution";
              leaf user-name {
                type string {
                  length "1..32";
                }
              } //user-name

            } //container cli-user

          } //container vsd

        } //container authorization

      } //container cli-script

      list cli-session-group {
        key "session-group-name";
        description
            "Create/delete Cli Session Groups";
        leaf session-group-name {
          type string;
        } //session-group-name

        container combined-max-sessions {
          description
              "Maximum number of concurrent SSH & Telnet sessions";
          leaf number-of-sessions {
            type int32 {
              range "0..50";
            }
          } //number-of-sessions

        } //container combined-max-sessions

        container description {
          description
              "Description for this Cli Session Group";
          leaf description-string {
            type string {
              length "1..80";
            }
          } //description-string

        } //container description

        container ssh-max-sessions {
          description
              "Maximum number of concurrent SSH sessions";
          leaf number-of-sessions {
            type int32 {
              range "0..50";
            }
          } //number-of-sessions

        } //container ssh-max-sessions

        container telnet-max-sessions {
          description
              "Maximum number of concurrent Telnet sessions";
          leaf number-of-sessions {
            type int32 {
              range "0..50";
            }
          } //number-of-sessions

        } //container telnet-max-sessions

      } //list cli-session-group

      container cpm-filter {
        description
            "Configure a CPM filter";
        container default-action {
          description
              "Configure the default filter action";
          leaf drop {
            type boolean;
          } //drop

          leaf accept {
            type boolean;
          } //accept

        } //container default-action

        container ip-filter {
          description
              "Configure a CPM IP-filter";
          container renum {
            description
                "Renumber an entry";
            leaf old-entry-id {
              type string;
              description
                  "Attribute old-entry-id for renum";
            } //old-entry-id

            leaf new-entry-id {
              type string;
              description
                  "Attribute new-entry-id for renum";
            } //new-entry-id

          } //container renum

          leaf shutdown {
            type boolean;
            description
                "Set the admin state of the IP filter";
          }

          list entry {
            key "entry-id";
            description
                "Configure ip-filter entry";
            leaf entry-id {
              type string;
              description
                  "Attribute entry-id for entry";
            } //entry-id

            container action {
              description
                  "Configure action for the filter entry";
              leaf drop {
                type boolean;
              } //drop

              leaf accept {
                type boolean;
                description
                    "keyword";
              } //accept

              leaf queue {
                type uint32 {
                  range "33..2000";
                }
              } //queue

            } //container action

            container description {
              description
                  "Description for this filter entry";
              leaf description-string {
                type string {
                  length "1..80";
                }
              } //description-string

            } //container description

            container log {
              description
                  "Configure log for the filter entry";
              leaf log-id {
                type uint16 {
                  range "101..199";
                }
              } //log-id

            } //container log

            container match {
              description
                  "Configure match criteria for this ip filter entry";
              leaf protocol {
                type string;
                description
                    "Attribute protocol-id for match";
              } //protocol

              container dscp {
                description
                    "Configure DSCP match condition";
                leaf dscp-name {
                  type string {
                    length "1..32";
                  }
                  description
                      "Attribute dscp-name for dscp";
                } //dscp-name

              } //container dscp

              container dst-ip {
                description
                    "Configure dest. ip match condition";
                leaf ip-address-mask {
                  type inet:ip-prefix;
                  description
                      "<ip-address>/<mask>";
                } //ip-address-mask

                leaf ip-address {
                  type inet:ip-address;
                  description
                      "Attribute ip-address for dst-ip";
                } //ip-address

                leaf ipv4-address-mask {
                  type string;
                  description
                      "a.b.c.d (dotted quad equivalent of mask length)";
                } //ipv4-address-mask

                leaf ip-prefix-list {
                  type string {
                    length "1..32";
                  }
                } //ip-prefix-list

              } //container dst-ip

              container dst-port {
                description
                    "Configure dest. port match condition";
                leaf tcp-udp-port-number {
                  type string;
                  description
                      "Attribute tcp/udp port-number for dst-port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp-port-number";
                } //range

                leaf port-list {
                  type string {
                    length "1..32";
                  }
                } //port-list

              } //container dst-port

              container fragment {
                description
                    "Configure fragmentation match condition";
                leaf true-false {
                  type enumeration {
                    enum true;
                    enum false;
                  }
                  description
                      "keywords - sets/resets fragmentation check";
                } //true-false

              } //container fragment

              container icmp-code {
                description
                    "Configure ICMP code match condition";
                leaf icmp-code {
                  type string;
                  description
                      "Attribute icmp-code for icmp-code";
                } //icmp-code

              } //container icmp-code

              container icmp-type {
                description
                    "Configure ICMP type match condition";
                leaf icmp-type {
                  type string;
                  description
                      "Attribute icmp-type for icmp-type";
                } //icmp-type

              } //container icmp-type

              container ip-option {
                description
                    "Configure ip-option match condition";
                leaf ip-option-value {
                  type string;
                  description
                      "[0..255] - accepted in decimal hex or binary";
                } //ip-option-value

                leaf ip-option-mask {
                  type string;
                  description
                      "[0..255] - accepted in decimal hex or binary";
                } //ip-option-mask

              } //container ip-option

              container multiple-option {
                description
                    "Configure multiple-option match condition";
                leaf true-false {
                  type enumeration {
                    enum true;
                    enum false;
                  }
                  description
                      "keywords - sets/resets multiple-option check";
                } //true-false

              } //container multiple-option

              container option-present {
                description
                    "Configure option-present match condition";
                leaf true-false {
                  type enumeration {
                    enum true;
                    enum false;
                  }
                  description
                      "keywords - sets/resets option-present check";
                } //true-false

              } //container option-present

              container port {
                description
                    "Configure port match condition";
                leaf tcp-udp-port-number {
                  type string;
                  description
                      "Attribute tcp/udp port-number for port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp port-number";
                } //range

                leaf port-list {
                  type string {
                    length "1..32";
                  }
                } //port-list

              } //container port

              container router {
                description
                    "Match a router|service-id";
                leaf router-instance {
                  type string {
                    length "1..32";
                  }
                  default "Base";
                  description
                      "Attribute router-instance for router";
                } //router-instance

                leaf service-name {
                  type string;
                } //service-name

              } //container router

              container src-ip {
                description
                    "Configure source ip match condition";
                leaf ip-address-mask {
                  type inet:ip-prefix;
                  description
                      "<ip-address>/<mask>";
                } //ip-address-mask

                leaf ip-address {
                  type inet:ip-address;
                  description
                      "Attribute ip-address for src-ip";
                } //ip-address

                leaf ipv4-address-mask {
                  type string;
                  description
                      "a.b.c.d (dotted quad equivalent of mask length)";
                } //ipv4-address-mask

                leaf ip-prefix-list {
                  type string {
                    length "1..32";
                  }
                } //ip-prefix-list

              } //container src-ip

              container src-port {
                description
                    "Configure source port match condition";
                leaf tcp-udp-port-number {
                  type string;
                  description
                      "Attribute tcp/udp port-number for src-port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp port-number";
                } //range

                leaf port-list {
                  type string {
                    length "1..32";
                  }
                } //port-list

              } //container src-port

              container tcp-ack {
                description
                    "Configure TCP ACK match condition";
                leaf true-false {
                  type enumeration {
                    enum true;
                    enum false;
                  }
                  description
                      "keywords - sets/resets TCP ACK check";
                } //true-false

              } //container tcp-ack

              container tcp-syn {
                description
                    "Configure TCP SYN match condition";
                leaf true-false {
                  type enumeration {
                    enum true;
                    enum false;
                  }
                  description
                      "keywords - sets/resets TCP SYN check";
                } //true-false

              } //container tcp-syn

            } //container match

          } //list entry

        } //container ip-filter

        container ipv6-filter {
          description
              "Configure a CPM IPv6-filter";
          container renum {
            description
                "Renumber an IPv6-filter entry";
            leaf old-entry-id {
              type string;
              description
                  "Attribute old-entry-id for renum";
            } //old-entry-id

            leaf new-entry-id {
              type string;
              description
                  "Attribute new-entry-id for renum";
            } //new-entry-id

          } //container renum

          leaf shutdown {
            type boolean;
            description
                "Set the admin state of the IPv6 filter";
          }

          list entry {
            key "entry-id";
            description
                "Configure IPv6-filter entry";
            leaf entry-id {
              type string;
              description
                  "Attribute entry-id for entry";
            } //entry-id

            container action {
              description
                  "Configure action for the IPv6-filter entry";
              leaf drop {
                type boolean;
              } //drop

              leaf accept {
                type boolean;
                description
                    "keyword";
              } //accept

              leaf queue {
                type int32 {
                  range "33..2000";
                }
              } //queue

            } //container action

            container description {
              description
                  "Description for this filter entry";
              leaf description-string {
                type string {
                  length "1..80";
                }
              } //description-string

            } //container description

            container log {
              description
                  "Configure log for the IPv6-filter entry";
              leaf log-id {
                type uint16 {
                  range "101..199";
                }
              } //log-id

            } //container log

            container match {
              description
                  "Configure match criteria for this IPv6 filter entry";
              leaf next-header {
                type string;
                description
                    "Attribute next-header for match";
              } //next-header

              container dscp {
                description
                    "Configure DSCP match condition";
                leaf dscp-name {
                  type string {
                    length "1..32";
                  }
                  description
                      "Attribute dscp-name for dscp";
                } //dscp-name

              } //container dscp

              container dst-ip {
                description
                    "Configure dest. ipv6 match condition";
                leaf ipv6-address-prefix-length {
                  type string;
                  description
                      "ipv6-address x:x:x:x:x:x:x:x (eight 16-bit pieces) 
                       x:x:x:x:x:x:d.d.d.d 
                       x [0..FFFF]H 
                       d [0..255]D 
                       prefix-length [1..128]";
                } //ipv6-address-prefix-length

                leaf ipv6-prefix-list {
                  type string {
                    length "1..32";
                  }
                } //ipv6-prefix-list

              } //container dst-ip

              container dst-port {
                description
                    "Configure dest. port match condition";
                leaf tcp-udp-port-number {
                  type string;
                  description
                      "Attribute tcp/udp port-number for dst-port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp port-number";
                } //range

                leaf port-list {
                  type string {
                    length "1..32";
                  }
                } //port-list

              } //container dst-port

              container flow-label {
                description
                    "Configure flow label match condition";
                leaf value {
                  type uint32 {
                    range "0..1048575";
                  }
                } //value

              } //container flow-label

              container fragment {
                description
                    "Configure fragmentation match condition";
                leaf true-false {
                  type enumeration {
                    enum true;
                    enum false;
                  }
                  description
                      "keywords - sets/resets fragmentation check";
                } //true-false

              } //container fragment

              container hop-by-hop-opt {
                description
                    "Configure hop-by-hop options ext header match condition";
                leaf true-false {
                  type enumeration {
                    enum true;
                    enum false;
                  }
                  description
                      "keywords - sets/resets hop-by-hop options check";
                } //true-false

              } //container hop-by-hop-opt

              container icmp-code {
                description
                    "Configure ICMP code match condition";
                leaf icmp-code {
                  type string;
                  description
                      "Attribute icmp-code for icmp-code";
                } //icmp-code

              } //container icmp-code

              container icmp-type {
                description
                    "Configure ICMP type match condition";
                leaf icmp-type {
                  type string;
                  description
                      "Attribute icmp-type for icmp-type";
                } //icmp-type

              } //container icmp-type

              container port {
                description
                    "Configure port match condition";
                leaf tcp-udp-port-number {
                  type string;
                  description
                      "Attribute tcp/udp port-number for port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp port-number";
                } //range

                leaf port-list {
                  type string {
                    length "1..32";
                  }
                } //port-list

              } //container port

              container router {
                description
                    "Match a router|service-id";
                leaf router-instance {
                  type string {
                    length "1..32";
                  }
                  default "Base";
                  description
                      "Attribute router-instance for router";
                } //router-instance

                leaf service-name {
                  type string;
                } //service-name

              } //container router

              container src-ip {
                description
                    "Configure source IPv6 address match condition";
                leaf ipv6-address-prefix-length {
                  type string;
                  description
                      "ipv6-address x:x:x:x:x:x:x:x (eight 16-bit pieces) 
                       x:x:x:x:x:x:d.d.d.d 
                       x [0..FFFF]H 
                       d [0..255]D 
                       prefix-length [1..128]";
                } //ipv6-address-prefix-length

                leaf ipv6-prefix-list {
                  type string {
                    length "1..32";
                  }
                } //ipv6-prefix-list

              } //container src-ip

              container src-port {
                description
                    "Configure source port match condition";
                leaf tcp-udp-port-number {
                  type string;
                  description
                      "Attribute tcp/udp port-number for src-port";
                } //tcp-udp-port-number

                leaf mask {
                  type string {
                  }
                  description
                      "[0x0000..0xFFFF] | [0..65535] | [0b0000000000000000..0b1111111111111111]";
                } //mask

                leaf-list range {
                  type string;
                  max-elements 2;
                  description
                      "tcp/udp port-number";
                } //range

                leaf port-list {
                  type string {
                    length "1..32";
                  }
                } //port-list

              } //container src-port

              container tcp-ack {
                description
                    "Configure TCP ACK match condition";
                leaf true-false {
                  type enumeration {
                    enum true;
                    enum false;
                  }
                  description
                      "keywords - sets/resets TCP ACK check";
                } //true-false

              } //container tcp-ack

              container tcp-syn {
                description
                    "Configure TCP SYN match condition";
                leaf true-false {
                  type enumeration {
                    enum true;
                    enum false;
                  }
                  description
                      "keywords - sets/resets TCP SYN check";
                } //true-false

              } //container tcp-syn

            } //container match

          } //list entry

        } //container ipv6-filter

        container mac-filter {
          description
              "Configure a CPM MAC-filter";
          container renum {
            description
                "Renumber an entry";
            leaf old-entry-id {
              type string;
              description
                  "Attribute old-entry-id for renum";
            } //old-entry-id

            leaf new-entry-id {
              type string;
              description
                  "Attribute new-entry-id for renum";
            } //new-entry-id

          } //container renum

          leaf shutdown {
            type boolean;
            description
                "Set the admin state of the Mac filter";
          }

          list entry {
            key "entry-id";
            description
                "Configure MAC-filter entry";
            leaf entry-id {
              type string;
              description
                  "Attribute entry-id for entry";
            } //entry-id

            container action {
              description
                  "Configure action for the MAC-filter entry";
              leaf drop {
                type boolean;
              } //drop

              leaf accept {
                type boolean;
                description
                    "keyword";
              } //accept

              leaf queue {
                type int32 {
                  range "33..2000";
                }
              } //queue

            } //container action

            container description {
              description
                  "Description for this filter entry";
              leaf description-string {
                type string {
                  length "1..80";
                }
              } //description-string

            } //container description

            container log {
              description
                  "Configure log for the filter entry";
              leaf log-id {
                type uint16 {
                  range "101..199";
                }
              } //log-id

            } //container log

            container match {
              description
                  "Configure match criteria for this MAC filter entry";
              leaf frame-type {
                type enumeration {
                  enum none;
                  enum 802dot2-llc;
                  enum 802dot1ag;
                  enum ethernet_II;
                }
              } //frame-type

              container cfm-opcode {
                description
                    "Configure CFM match condition";
                leaf lt-gt-eq {
                  type enumeration {
                    enum lt;
                    enum gt;
                    enum eq;
                  }
                  description
                      "keywords";
                } //lt-gt-eq

                leaf opcode {
                  type uint32 {
                    range "0..255";
                  }
                } //opcode

                leaf-list range {
                  type int32 {
                    range "0..255";
                  }
                  max-elements 2;
                  description
                      "opcode";
                } //range

              } //container cfm-opcode

              container dsap {
                description
                    "Configure dsap match condition";
                leaf dsap-value {
                  type string;
                  description
                      "[0..255] - accepts in decimal hex or binary";
                } //dsap-value

                leaf dsap-mask {
                  type string;
                  description
                      "[0..255] - accepts in decimal hex or binary";
                } //dsap-mask

              } //container dsap

              container dst-mac {
                description
                    "Configure dest. mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container dst-mac

              container etype {
                description
                    "Configure e-type match condition";
                leaf t0x0600..0xffff {
                  type string;
                  description
                      "[1536..65535] - accepts in decimal or hex";
                } //t0x0600..0xffff

              } //container etype

              container src-mac {
                description
                    "Configure source mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container src-mac

              container ssap {
                description
                    "Configure ssap match condition";
                leaf ssap-value {
                  type string;
                  description
                      "[0.255] - accepts in decimal hex or binary";
                } //ssap-value

                leaf ssap-mask {
                  type string;
                  description
                      "[0.255] - accepts in decimal hex or binary";
                } //ssap-mask

              } //container ssap

              container svc-id {
                description
                    "Configure service-id to match on";
                leaf service-id {
                  type string;
                  description
                      "Attribute service-id for svc-id";
                } //service-id

              } //container svc-id

            } //container match

          } //list entry

        } //container mac-filter

      } //container cpm-filter

      container cpm-queue {
        description
            "Configure a CPM queue";
        list queue {
          key "queue-id";
          description
              "Configure a Queue";
          leaf queue-id {
            type uint32 {
              range "33..2000";
            }
          } //queue-id

          container cbs {
            description
                "Configure CBS";
            leaf size-in-kbytes {
              type int32 {
                range "0..131072";
              }
              description
                  "[0..131072]";
            } //size-in-kbytes

            leaf max {
              type boolean;
              status "obsolete";
            } //max

            leaf default {
              type boolean;
            } //default

          } //container cbs

          container mbs {
            description
                "Configure MBS";
            leaf size-in-kbytes {
              type int32 {
                range "0..131072";
              }
              description
                  "[0..131072]";
            } //size-in-kbytes

            leaf max {
              type boolean;
              status "obsolete";
            } //max

            leaf default {
              type boolean;
            } //default

          } //container mbs

          container rate {
            description
                "Configure Rate";
            leaf pir-rate {
              type string {
              }
              description
                  "Attribute pir-rate for rate";
            } //pir-rate

            leaf cir {
              type string {
              }
              description
                  "[0..100000000|max]";
            } //cir

          } //container rate

        } //list queue

      } //container cpm-queue

      container cpu-protection {
        description
            "Configure CPU protection";
        container link-specific-rate {
          description
              "Configure a link-specific rate for CPU protection";
          leaf packet-rate-limit {
            type string;
            description
                "[ 1..65535 | max]";
          } //packet-rate-limit

        } //container link-specific-rate

        container port-overall-rate {
          description
              "Configure a per-port overall rate limit for CPU protection";
          leaf packet-rate-limit {
            type string;
            description
                "[ 1..65535 | max]";
          } //packet-rate-limit

          leaf action-low-priority {
            type boolean;
          } //action-low-priority

        } //container port-overall-rate

        container protocol-protection {
          description
              "Enable/Disable DOS protection of network control protocols";
          leaf allow-sham-links {
            type boolean;
          } //allow-sham-links

          leaf block-pim-tunneled {
            type boolean;
          } //block-pim-tunneled

        } //container protocol-protection

        container ip-src-monitoring {
          description
              "Configure IP source monitoring for CPU protection";
          container included-protocols {
            description
                "Configure protocols for IP source monitoring";
            leaf dhcp {
              type boolean;
              description
                  "Specify whether DHCP protocol should be included for IP source monitoring";
            }

            leaf gtp {
              type boolean;
              description
                  "Specify whether GTP protocol should be included for IP source monitoring";
            }

            leaf icmp {
              type boolean;
              description
                  "Specify whether ICMP protocol should be included for IP source monitoring";
            }

            leaf igmp {
              type boolean;
              description
                  "Specify whether IGMP protocol should be included for IP source monitoring";
            }

          } //container included-protocols

        } //container ip-src-monitoring

        list policy {
          key "cpu-protection-policy-id";
          description
              "Configure a CPU protection policy";
          leaf cpu-protection-policy-id {
            type uint32 {
              range "1..255";
            }
          } //cpu-protection-policy-id

          leaf alarm {
            type boolean;
            description
                "Enable notifications when a packet arrival rate limit is exceeded";
          }

          container description {
            description
                "Set the description of the policy";
            leaf description-string {
              type string {
                length "1..80";
              }
            } //description-string

          } //container description

          container out-profile-rate {
            description
                "Configure the threshold at which packets are marked out of profile";
            leaf packet-rate-limit {
              type string;
              description
                  "[ 1..65534 | max]";
            } //packet-rate-limit

            leaf log-events {
              type boolean;
            } //log-events

          } //container out-profile-rate

          container overall-rate {
            description
                "Configure an overall packet arrival rate limit";
            leaf packet-rate-limit {
              type string;
              description
                  "[ 1..65534 | max]";
            } //packet-rate-limit

          } //container overall-rate

          container per-source-rate {
            description
                "Configure a per-source packet arrival rate limit";
            leaf packet-rate-limit {
              type string;
              description
                  "[ 1..65534 | max]";
            } //packet-rate-limit

          } //container per-source-rate

          container eth-cfm {
            description
                "Configure packet arrival rate limits for Ethernet Connectivity Fault 
                 Management packets";
            list entry {
              key "entry";
              description
                  "Configure a packet arrival rate limit for Ethernet Connectivity Fault 
                   Management packets";
              leaf entry {
                type uint32 {
                  range "1..100";
                }
                description
                    "[1..100]";
              } //entry

              leaf levels {
                type string;
                description
                    "A set of values in the range 0..7, or 'all'. The values are matched against 
                     the domain level field of an incoming Eth-CFM packet. 
                     Five example values: 2 1,7 1-7 0,2-7 all";
              } //levels

              leaf opcodes {
                type string;
                description
                    "A set of values in the range 0..255, or 'all'. The values are matched against 
                     the OpCode field of an incoming Eth-CFM packet. 
                     Five example values: 2 1,3 1-3 0,2-255 all";
              } //opcodes

              leaf rate {
                type string;
                description
                    "[0..65534 | max] packets/second. Zero drops all packets meeting the 'levels' 
                     and 'opcodes' criteria.";
              } //rate

            } //list entry

          } //container eth-cfm

          container per-source-parameters {
            description
                "Configure additional parameters for per-source packet arrival rate limiting";
            container ip-src-monitoring {
              description
                  "Configure IP per-source rate limiting";
              leaf limit-dhcp-ci-addr-zero {
                type boolean;
                description
                    "keyword - rate limit DHCP packets containing Client IP address 0.0.0.0";
              }

            } //container ip-src-monitoring

          } //container per-source-parameters

        } //list policy

      } //container cpu-protection

      container dist-cpu-protection {
        description
            "Configure Distributed CPU Protection";
        list policy {
          key "policy-name";
          description
              "Configure Distributed CPU Protection Policy";
          leaf policy-name {
            type string;
          } //policy-name

          container description {
            description
                "Set the description of the policy";
            leaf description-string {
              type string {
                length "1..80";
              }
            } //description-string

          } //container description

          list local-monitoring-policer {
            key "policer-name";
            description
                "Configure Local-Monitoring Policer for Distributed CPU protection";
            leaf policer-name {
              type string;
            } //policer-name

            container description {
              description
                  "Set the description of the policy";
              leaf description-string {
                type string {
                  length "1..80";
                }
              } //description-string

            } //container description

            container exceed-action {
              description
                  "Configure Exceed Action for Local-Mon-Policer Distributed CPU protection";
              leaf discard-low-priority-none {
                type enumeration {
                  enum discard;
                  enum low-priority;
                  enum none;
                }
              } //discard-low-priority-none

            } //container exceed-action

            container log-events {
              description
                  "Controls creation of Log Events for Loc-Mon Policer";
              leaf verbose {
                type boolean;
                description
                    "keyword";
              } //verbose

            } //container log-events

            container rate {
              description
                  "Configure Rate Parameters for Local-Mon-Policer Distributed CPU protection";
              leaf packets {
                type string;
                description
                    "[0..255|max]";
              } //packets

              leaf within {
                type int32 {
                  range "1..32767";
                }
              } //within

              leaf initial-delay {
                type uint16 {
                  range "0..255";
                }
              } //initial-delay

              leaf kbps {
                type string;
                description
                    "[1..20000000|max]Kbps";
              } //kbps

              leaf mbs {
                type string;
                description
                    "[0..4194304 | default]";
              } //mbs

              leaf bytes-kilobytes {
                type enumeration {
                  enum bytes;
                  enum kilobytes;
                }
              } //bytes-kilobytes

            } //container rate

          } //list local-monitoring-policer

          list protocol {
            key "name";
            description
                "Configure Protocol for Distributed CPU protection";
            leaf name {
              type enumeration {
                enum arp;
                enum dhcp;
                enum http-redirect;
                enum icmp;
                enum icmp-ping-check;
                enum igmp;
                enum mld;
                enum ndis;
                enum pppoe-pppoa;
                enum all-unspecified;
                enum mpls-ttl;
                enum bfd-cpm;
                enum bgp;
                enum eth-cfm;
                enum isis;
                enum ldp;
                enum ospf;
                enum ospf+;
                enum pim;
                enum rsvp;
              }
              description
                  "Attribute name for protocol";
            } //name

            container enforcement {
              description
                  "Configure Enforcement Policer for Protocol";
              leaf static {
                type boolean;
              } //static

              leaf dynamic {
                type boolean;
              } //dynamic

              leaf policer-name {
                type string;
              } //policer-name

              leaf mon-policer-name {
                type string;
              } //mon-policer-name

            } //container enforcement

            container dynamic-parameters {
              description
                  "Configure Dynamic Parameters for Protocol";
              container detection-time {
                description
                    "Configure Detection Time for Protocol";
                leaf seconds {
                  type int32 {
                    range "1..128000";
                  }
                } //seconds

              } //container detection-time

              container exceed-action {
                description
                    "Configure Exceed Action for Protocol";
                leaf discard-low-priority-none {
                  type enumeration {
                    enum discard;
                    enum low-priority;
                    enum none;
                  }
                } //discard-low-priority-none

                leaf hold-down {
                  type string;
                  description
                      "[none|1..10080|indefinite]";
                } //hold-down

              } //container exceed-action

              container log-events {
                description
                    "Controls creation of Log Events for Static Policer";
                leaf verbose {
                  type boolean;
                  description
                      "keyword";
                } //verbose

              } //container log-events

              container rate {
                description
                    "Configure Rate Parameters for Protocol";
                leaf packets {
                  type string;
                  description
                      "[0..255|max]";
                } //packets

                leaf within {
                  type int32 {
                    range "1..32767";
                  }
                } //within

                leaf initial-delay {
                  type uint16 {
                    range "0..255";
                  }
                } //initial-delay

                leaf kbps {
                  type string;
                  description
                      "[1..20000000|max]Kbps";
                } //kbps

                leaf mbs {
                  type string;
                  description
                      "[0..4194304 | default]";
                } //mbs

                leaf bytes-kilobytes {
                  type enumeration {
                    enum bytes;
                    enum kilobytes;
                  }
                } //bytes-kilobytes

              } //container rate

            } //container dynamic-parameters

          } //list protocol

          list static-policer {
            key "policer-name";
            description
                "Configure Static-Policer for Distributed CPU protection";
            leaf policer-name {
              type string;
            } //policer-name

            container description {
              description
                  "Set the description of the policy";
              leaf description-string {
                type string {
                  length "1..80";
                }
              } //description-string

            } //container description

            container detection-time {
              description
                  "Configure Detection Time for Static Policer";
              leaf seconds {
                type int32 {
                  range "1..128000";
                }
              } //seconds

            } //container detection-time

            container exceed-action {
              description
                  "Configure Exceed Action for Static-Policer Distributed CPU protection";
              leaf discard-low-priority-none {
                type enumeration {
                  enum discard;
                  enum low-priority;
                  enum none;
                }
              } //discard-low-priority-none

              leaf hold-down {
                type string;
                description
                    "[none|1..10080|indefinite]";
              } //hold-down

            } //container exceed-action

            container log-events {
              description
                  "Controls creation of Log Events for Static Policer";
              leaf verbose {
                type boolean;
                description
                    "keyword";
              } //verbose

            } //container log-events

            container rate {
              description
                  "Configure Rate Parameters for Static-Policer Distributed CPU protection";
              leaf packets {
                type string;
                description
                    "Attribute ppi|max for rate";
              } //packets

              leaf within {
                type int32 {
                  range "1..32767";
                }
              } //within

              leaf initial-delay {
                type uint16 {
                  range "0..255";
                }
              } //initial-delay

              leaf kbps {
                type string;
                description
                    "[1..20000000|max]Kbps";
              } //kbps

              leaf mbs {
                type string;
                description
                    "[0..4194304 | default]";
              } //mbs

              leaf bytes-kilobytes {
                type enumeration {
                  enum bytes;
                  enum kilobytes;
                }
              } //bytes-kilobytes

            } //container rate

          } //list static-policer

        } //list policy

      } //container dist-cpu-protection

      container dot1x {
        description
            "Configure dot1x security parameters";
        leaf shutdown {
          type boolean;
          description
              "Start/shutdown the dot1x Authentication";
        }

        list radius-plcy {
          key "name";
          description
              "create/modify a RADIUS authentication policy";
          leaf name {
            type string {
              length "1..32";
            }
          } //name

          container retry {
            description
                "Number of retries for contacting the RADIUS server";
            leaf count {
              type uint32 {
                range "1..10";
              }
            } //count

          } //container retry

          list server {
            key "server-index";
            description
                "Add/remove a RADIUS server";
            leaf server-index {
              type uint32 {
                range "1..5";
              }
            } //server-index

            leaf address {
              type inet:ip-address;
            } //address

            leaf secret {
              type string {
                length "1..500";
              }
              description
                  "secret-key - [20 chars max] 
                   hash-key 
                   hash2-key 
                   custom-key";
            } //secret

            leaf hash-hash2-custom {
              type enumeration {
                enum hash;
                enum hash2;
                enum custom;
              }
              description
                  "keywords - specify hashing scheme";
            } //hash-hash2-custom

            leaf auth-port {
              type uint16 {
                range "1..65535";
              }
            } //auth-port

            leaf acct-port {
              type uint16 {
                range "1..65535";
              }
            } //acct-port

            leaf type {
              type enumeration {
                enum authorization;
                enum accounting;
                enum combined;
              }
              description
                  "[authorization | accounting | combined]";
            } //type

          } //list server

          leaf shutdown {
            type boolean;
            description
                "Enable/Disable the use of this policy";
          }

          list source-address {
            key "ip-address";
            description
                "Source address of the RADIUS packet";
            leaf ip-address {
              type inet:ip-address;
            } //ip-address

          } //list source-address

          container timeout {
            description
                "Timeout for a response from the RADIUS server";
            leaf seconds {
              type uint32 {
                range "1..90";
              }
            } //seconds

          } //container timeout

        } //list radius-plcy

      } //container dot1x

      list keychain {
        key "keychain-name";
        description
            "Configure keychains";
        leaf keychain-name {
          type string {
            length "1..32";
          }
          description
              "32 char max";
        } //keychain-name

        container description {
          description
              "Description for the keychain";
          leaf description {
            type string {
              length "1..80";
            }
            description
                "[80 char max]";
          } //description

        } //container description

        leaf shutdown {
          type boolean;
          description
              "Enable/disable key chain";
        }

        container direction {
          description
              "Configure stream direction to apply keys on";
          container bi {
            description
                "Configure keys for both send and receive stream directions";
            list entry {
              key "entry-id";
              description
                  "Configure key entry";
              leaf entry-id {
                type string;
                description
                    "[0..63|null-key]";
              } //entry-id

              leaf key {
                type string {
                  length "1..500";
                }
                description
                    "authentication-key - [20 chars max] 
                     hash-key 
                     hash2-key 
                     custom-key";
              } //key

              leaf hash-hash2-custom {
                type enumeration {
                  enum hash;
                  enum hash2;
                  enum custom;
                }
                description
                    "keywords - specify hashing scheme";
              } //hash-hash2-custom

              leaf algorithm {
                type enumeration {
                  enum aes-128-cmac-96;
                  enum aes-128-gcm-16;
                  enum hmac-sha-1-96;
                  enum password;
                  enum message-digest;
                  enum hmac-sha-1;
                  enum hmac-sha-256;
                  enum hmac-md5;
                }
                description
                    "Attribute algorithm for entry";
              } //algorithm

              container begin-time {
                description
                    "Configure calendar time for the key to become active";
                leaf date {
                  type string;
                  description
                      "YYYY/MM/DD";
                } //date

                leaf hours-minutes {
                  type string;
                  description
                      "hh:mm[:ss]";
                } //hours-minutes

                leaf now-forever {
                  type enumeration {
                    enum now;
                    enum forever;
                  }
                  description
                      "keyword - 'now' specifies a time equal to the current system time";
                } //now-forever

                leaf UTC {
                  type boolean;
                  description
                      "keyword - Date and Time will be interpreted as time in UTC instead of local 
                       time";
                } //UTC

              } //container begin-time

              container option {
                description
                    "Configure key entry option";
                leaf option-id {
                  type enumeration {
                    enum basic;
                    enum isis-enhanced;
                  }
                } //option-id

              } //container option

              leaf shutdown {
                type boolean;
                description
                    "Enable/disable key entry";
              }

              container tolerance {
                description
                    "Configure duration that a eligible receive key overlaps with active send key";
                leaf seconds {
                  type uint32 {
                    range "0..4294967294";
                  }
                  description
                      "0-4294967294 seconds";
                } //seconds

                leaf forever {
                  type boolean;
                } //forever

              } //container tolerance

            } //list entry

          } //container bi

          container uni {
            description
                "Configure keys for send or receive stream direction";
            container receive {
              description
                  "Configure keys to be applied on receive stream";
              list entry {
                key "entry-id";
                description
                    "Configure key entry";
                leaf entry-id {
                  type string;
                  description
                      "[0..63|null-key]";
                } //entry-id

                leaf key {
                  type string {
                    length "1..500";
                  }
                  description
                      "authentication-key - [20 chars max] 
                       hash-key 
                       hash2-key 
                       custom-key";
                } //key

                leaf hash-hash2-custom {
                  type enumeration {
                    enum hash;
                    enum hash2;
                    enum custom;
                  }
                  description
                      "keywords - specify hashing scheme";
                } //hash-hash2-custom

                leaf algorithm {
                  type enumeration {
                    enum aes-128-cmac-96;
                    enum aes-128-gcm-16;
                    enum hmac-sha-1-96;
                    enum password;
                    enum message-digest;
                    enum hmac-sha-1;
                    enum hmac-sha-256;
                    enum hmac-md5;
                  }
                  description
                      "Attribute algorithm for entry";
                } //algorithm

                container begin-time {
                  description
                      "Configure calendar time for the key to become active";
                  leaf date {
                    type string;
                    description
                        "YYYY/MM/DD";
                  } //date

                  leaf hours-minutes {
                    type string;
                    description
                        "hh:mm[:ss]";
                  } //hours-minutes

                  leaf now-forever {
                    type enumeration {
                      enum now;
                      enum forever;
                    }
                    description
                        "keyword - 'now' specifies a time equal to the current system time";
                  } //now-forever

                  leaf UTC {
                    type boolean;
                    description
                        "keyword - Date and Time will be interpreted as time in UTC instead of local 
                         time";
                  } //UTC

                } //container begin-time

                container end-time {
                  description
                      "Configure calendar time for the key to become inactive";
                  leaf date {
                    type string;
                    description
                        "YYYY/MM/DD";
                  } //date

                  leaf hours-minutes {
                    type string;
                    description
                        "hh:mm[:ss]";
                  } //hours-minutes

                  leaf now-forever {
                    type enumeration {
                      enum now;
                      enum forever;
                    }
                    description
                        "keyword - 'now' specifies a time equal to the current system time";
                  } //now-forever

                  leaf UTC {
                    type boolean;
                    description
                        "keyword - Date and Time will be interpreted as time in UTC instead of local 
                         time";
                  } //UTC

                } //container end-time

                leaf shutdown {
                  type boolean;
                  description
                      "Enable/disable key entry";
                }

                container tolerance {
                  description
                      "Configure duration that a eligible receive key overlaps with active send key";
                  leaf seconds {
                    type uint32 {
                      range "0..4294967294";
                    }
                    description
                        "0-4294967294 seconds";
                  } //seconds

                  leaf forever {
                    type boolean;
                  } //forever

                } //container tolerance

              } //list entry

            } //container receive

            container send {
              description
                  "Configure keys to be applied on send stream";
              list entry {
                key "entry-id";
                description
                    "Configure key entry";
                leaf entry-id {
                  type uint32 {
                    range "0..63";
                  }
                } //entry-id

                leaf key {
                  type string {
                    length "1..500";
                  }
                  description
                      "authentication-key - [20 chars max] 
                       hash-key 
                       hash2-key 
                       custom-key";
                } //key

                leaf hash-hash2-custom {
                  type enumeration {
                    enum hash;
                    enum hash2;
                    enum custom;
                  }
                  description
                      "keywords - specify hashing scheme";
                } //hash-hash2-custom

                leaf algorithm {
                  type enumeration {
                    enum aes-128-cmac-96;
                    enum aes-128-gcm-16;
                    enum hmac-sha-1-96;
                    enum password;
                    enum message-digest;
                    enum hmac-sha-1;
                    enum hmac-sha-256;
                    enum hmac-md5;
                  }
                  description
                      "Attribute algorithm for entry";
                } //algorithm

                container begin-time {
                  description
                      "Configure calendar time for the key to become active";
                  leaf date {
                    type string;
                    description
                        "YYYY/MM/DD";
                  } //date

                  leaf hours-minutes {
                    type string;
                    description
                        "hh:mm[:ss]";
                  } //hours-minutes

                  leaf now-forever {
                    type enumeration {
                      enum now;
                      enum forever;
                    }
                    description
                        "keyword - 'now' specifies a time equal to the current system time";
                  } //now-forever

                  leaf UTC {
                    type boolean;
                    description
                        "keyword - Date and Time will be interpreted as time in UTC instead of local 
                         time";
                  } //UTC

                } //container begin-time

                leaf shutdown {
                  type boolean;
                  description
                      "Enable/disable key entry";
                }

              } //list entry

            } //container send

          } //container uni

        } //container direction

        container tcp-option-number {
          description
              "Configure TCP option number to be placed in the TCP packet header";
          container receive {
            description
                "Configure TCP option number accepted in TCP packets received";
            leaf option-number {
              type enumeration {
                enum 253;
                enum 254;
                enum 253&254;
                enum tcp-ao;
              }
            } //option-number

          } //container receive

          container send {
            description
                "Configure TCP option number placed in TCP packets send";
            leaf option-number {
              type enumeration {
                enum 253;
                enum 254;
                enum tcp-ao;
              }
            } //option-number

          } //container send

        } //container tcp-option-number

      } //list keychain

      container ldap {
        description
            "Configure LDAP authentication parameters for the system";
        leaf public-key-authentication {
          type boolean;
          description
              "Enable/disable SSH public-key authentication via LDAP";
        }

        container retry {
          description
              "Number of attempts to retry contacting an LDAP server";
          leaf count {
            type uint32 {
              range "1..10";
            }
            description
                "[1..10] - Default 3";
          } //count

        } //container retry

        leaf shutdown {
          type boolean;
          description
              "Enable/disable LDAP protocol operation";
        }

        container timeout {
          description
              "Timeout for a response from an LDAP server";
          leaf seconds {
            type uint32 {
              range "1..90";
            }
            description
                "[1..90] - Default 3";
          } //seconds

        } //container timeout

        leaf use-default-template {
          type boolean;
          description
              "Enable/disable LDAP default template";
        }

        list server {
          key "server-index";
          description
              "Add/remove an LDAP server";
          leaf server-index {
            type uint32 {
              range "1..5";
            }
          } //server-index

          container address {
            description
                "Configure LDAP server address";
            leaf ip-address {
              type string;
              description
                  "Attribute ip-address for address";
            } //ip-address

            leaf port {
              type int32 {
                range "1..65535";
              }
              default 389;
              description
                  "[1..65535] TCP - Default: 389";
            } //port

          } //container address

          container bind-authentication {
            description
                "Configure LDAP server authentication";
            leaf root-dn {
              type string {
                length "1..512";
              }
            } //root-dn

            leaf password {
              type string {
                length "1..500";
              }
              description
                  "plain text - [128 chars max] 
                   hash 
                   hash2 
                   custom";
            } //password

            leaf hash-hash2-custom {
              type enumeration {
                enum hash;
                enum hash2;
                enum custom;
              }
            } //hash-hash2-custom

          } //container bind-authentication

          container ldap-server {
            description
                "Configure LDAP server name";
            leaf server-name {
              type string {
                length "1..32";
              }
            } //server-name

          } //container ldap-server

          container search {
            description
                "Configure LDAP server search domain";
            leaf base-dn {
              type string {
                length "1..512";
              }
            } //base-dn

          } //container search

          leaf shutdown {
            type boolean;
            description
                "Enable/disable this LDAP server";
          }

          container tls-profile {
            description
                "Configure TLS client transport profile";
            leaf tls-profile-name {
              type string {
                length "1..32";
              }
            } //tls-profile-name

          } //container tls-profile

        } //list server

      } //container ldap

      container management {
        description
            "Configure the node management via Base router";
        leaf allow-ftp {
          type boolean;
          description
              "allow/disallow access to ftp server";
        }

        leaf allow-grpc {
          type boolean;
          description
              "allow/disallow access to grpc server";
        }

        leaf allow-netconf {
          type boolean;
          description
              "allow/disallow access to netconf server";
        }

        leaf allow-ssh {
          type boolean;
          description
              "allow/disallow access to SSH server";
        }

        leaf allow-telnet {
          type boolean;
          description
              "allow/disallow access to telnet server";
        }

        leaf allow-telnet6 {
          type boolean;
          description
              "allow/disallow access to telnet IPv6 server";
        }

      } //container management

      container management-access-filter {
        presence
            "Configure management access filters";
        container ip-filter {
          presence
              "Configure a management access IP-filter";
          container default-action {
            description
                "Default-action for the management-access-filter";
            leaf permit-deny-deny-host-unreachable {
              type enumeration {
                enum permit;
                enum deny;
                enum deny-host-unreachable;
              }
              description
                  "keywords";
            } //permit-deny-deny-host-unreachable

          } //container default-action

          container renum {
            description
                "Renumber existing entries";
            leaf old-entry-number {
              type uint32 {
                range "1..9999";
              }
            } //old-entry-number

            leaf new-entry-number {
              type uint32 {
                range "1..9999";
              }
            } //new-entry-number

          } //container renum

          leaf shutdown {
            type boolean;
            description
                "Start/shutdown the management-access-filter";
          }

          list entry {
            key "entry-id";
            description
                "Match criteria entry for the management-access-filter";
            leaf entry-id {
              type uint32 {
                range "1..9999";
              }
            } //entry-id

            container action {
              description
                  "Action to take when a packet matches this entry";
              leaf permit-deny-deny-host-unreachable {
                type enumeration {
                  enum permit;
                  enum deny;
                  enum deny-host-unreachable;
                }
                description
                    "keywords";
              } //permit-deny-deny-host-unreachable

            } //container action

            container description {
              description
                  "Description for this entry";
              leaf description-string {
                type string {
                  length "1..80";
                }
              } //description-string

            } //container description

            container dst-port {
              description
                  "TCP/UDP port number or port range to match";
              leaf port {
                type int32 {
                  range "1..65535";
                }
              } //port

              leaf mask {
                type string {
                  length "1..18";
                }
                description
                    "[1..65535]decimal hex or binary";
              } //mask

            } //container dst-port

            leaf log {
              type boolean;
              description
                  "enable/disable match logging";
            }

            container protocol {
              description
                  "IP protocol to match";
              leaf protocol-id {
                type string;
                description
                    "Attribute protocol-id for protocol";
              } //protocol-id

            } //container protocol

            container router {
              description
                  "Router to match";
              leaf router-instance {
                type string {
                  length "1..32";
                }
                default "Base";
                description
                    "Attribute router-instance for router";
              } //router-instance

              leaf service-name {
                type string;
              } //service-name

            } //container router

            container src-ip {
              description
                  "Source IP address of packets to match";
              leaf ip-prefix-mask {
                type string;
                description
                    "ip-prefix a.b.c.d (host bits must be 0) 
                     mask [1..32]";
              } //ip-prefix-mask

              leaf netmask {
                type string;
                description
                    "a.b.c.d (network bits all 1 and host bits all 0)";
              } //netmask

              leaf ip-prefix-list {
                type string {
                  length "1..32";
                }
              } //ip-prefix-list

            } //container src-ip

            container src-port {
              description
                  "Source physical interface to match";
              leaf port-id {
                type string {
                  length "1..64";
                }
                description
                    "Attribute port-id for src-port";
              } //port-id

              leaf cpm {
                type boolean;
              } //cpm

              leaf lag {
                type string;
                description
                    "Attribute lag-id for src-port";
              } //lag

            } //container src-port

          } //list entry

        } //container ip-filter

        container ipv6-filter {
          presence
              "Configure a management access IPv6-filter";
          container default-action {
            description
                "Default-action for the management-access-filter";
            leaf permit-deny-deny-host-unreachable {
              type enumeration {
                enum permit;
                enum deny;
                enum deny-host-unreachable;
              }
              description
                  "keywords";
            } //permit-deny-deny-host-unreachable

          } //container default-action

          container renum {
            description
                "Renumber existing entries";
            leaf old-entry-number {
              type uint32 {
                range "1..9999";
              }
            } //old-entry-number

            leaf new-entry-number {
              type uint32 {
                range "1..9999";
              }
            } //new-entry-number

          } //container renum

          leaf shutdown {
            type boolean;
            description
                "Start/shutdown the management-access-filter";
          }

          list entry {
            key "entry-id";
            description
                "Match criteria entry for the management-access-filter";
            leaf entry-id {
              type uint32 {
                range "1..9999";
              }
            } //entry-id

            container action {
              description
                  "Action to take when a packet matches this entry";
              leaf permit-deny-deny-host-unreachable {
                type enumeration {
                  enum permit;
                  enum deny;
                  enum deny-host-unreachable;
                }
                description
                    "keywords";
              } //permit-deny-deny-host-unreachable

            } //container action

            container description {
              description
                  "Description for this entry";
              leaf description-string {
                type string {
                  length "1..80";
                }
              } //description-string

            } //container description

            container dst-port {
              description
                  "TCP/UDP port number or port range to match";
              leaf port {
                type int32 {
                  range "1..65535";
                }
              } //port

              leaf mask {
                type string {
                  length "1..18";
                }
                description
                    "[1..65535]decimal hex or binary";
              } //mask

            } //container dst-port

            container flow-label {
              description
                  "Configure flow label match condition";
              leaf value {
                type uint32 {
                  range "0..1048575";
                }
              } //value

            } //container flow-label

            leaf log {
              type boolean;
              description
                  "enable/disable match logging";
            }

            container next-header {
              description
                  "Next IPv6 header to match";
              leaf next-header {
                type string;
                description
                    "Attribute next-header for next-header";
              } //next-header

            } //container next-header

            container router {
              description
                  "Router to match";
              leaf router-instance {
                type string {
                  length "1..32";
                }
                default "Base";
                description
                    "Attribute router-instance for router";
              } //router-instance

              leaf service-name {
                type string;
              } //service-name

            } //container router

            container src-ip {
              description
                  "Source IP address of packets to match";
              leaf ipv6-address-prefix-length {
                type string;
                description
                    "ipv6-address x:x:x:x:x:x:x:x (eight 16-bit pieces) 
                     x:x:x:x:x:x:d.d.d.d 
                     x [0..FFFF]H 
                     d [0..255]D 
                     prefix-length [1..128]";
              } //ipv6-address-prefix-length

              leaf ipv6-prefix-list {
                type string {
                  length "1..32";
                }
              } //ipv6-prefix-list

            } //container src-ip

            container src-port {
              description
                  "Source physical interface to match";
              leaf port-id {
                type string {
                  length "1..64";
                }
                description
                    "Attribute port-id for src-port";
              } //port-id

              leaf cpm {
                type boolean;
              } //cpm

              leaf lag {
                type string;
                description
                    "Attribute lag-id for src-port";
              } //lag

            } //container src-port

          } //list entry

        } //container ipv6-filter

        container mac-filter {
          presence
              "Configure a management access MAC-filter";
          container default-action {
            description
                "Default-action for the management-access-filter";
            leaf permit-deny {
              type enumeration {
                enum permit;
                enum deny;
              }
              description
                  "keywords";
            } //permit-deny

          } //container default-action

          container renum {
            description
                "Renumber existing entries";
            leaf old-entry-number {
              type uint32 {
                range "1..9999";
              }
            } //old-entry-number

            leaf new-entry-number {
              type uint32 {
                range "1..9999";
              }
            } //new-entry-number

          } //container renum

          leaf shutdown {
            type boolean;
            description
                "Start/shutdown the management-access-filter";
          }

          list entry {
            key "entry-id";
            description
                "Match criteria entry for the management-access-filter";
            leaf entry-id {
              type uint32 {
                range "1..9999";
              }
              description
                  "[1..9999]";
            } //entry-id

            container action {
              description
                  "Action to take when a packet matches this entry";
              leaf deny {
                type boolean;
              } //deny

              leaf permit {
                type boolean;
                description
                    "keyword";
              } //permit

            } //container action

            container description {
              description
                  "Description for this filter entry";
              leaf description-string {
                type string {
                  length "1..80";
                }
              } //description-string

            } //container description

            leaf log {
              type boolean;
              description
                  "Enable/disable match logging";
            }

            container match {
              description
                  "Configure match criteria for this MAC filter entry";
              leaf frame-type {
                type enumeration {
                  enum 802dot3;
                  enum 802dot2-llc;
                  enum 802dot2-snap;
                  enum 802dot1ag;
                  enum ethernet_II;
                }
              } //frame-type

              container cfm-opcode {
                description
                    "Configure CFM match condition";
                leaf lt-gt-eq {
                  type enumeration {
                    enum lt;
                    enum gt;
                    enum eq;
                  }
                  description
                      "keywords";
                } //lt-gt-eq

                leaf opcode {
                  type uint32 {
                    range "0..255";
                  }
                } //opcode

                leaf-list range {
                  type int32 {
                    range "0..255";
                  }
                  max-elements 2;
                  description
                      "opcode";
                } //range

              } //container cfm-opcode

              container dot1p {
                description
                    "Configure Dot1p match condition";
                leaf dot1p-value {
                  type string;
                } //dot1p-value

                leaf dot1p-mask {
                  type string;
                  description
                      "[1..7] - accepts in decimal hex or binary";
                } //dot1p-mask

              } //container dot1p

              container dsap {
                description
                    "Configure dsap match condition";
                leaf dsap-value {
                  type string;
                  description
                      "[0..255] - accepts in decimal hex or binary";
                } //dsap-value

                leaf dsap-mask {
                  type string;
                  description
                      "[0..255] - accepts in decimal hex or binary";
                } //dsap-mask

              } //container dsap

              container dst-mac {
                description
                    "Configure dest. mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container dst-mac

              container etype {
                description
                    "Configure e-type match condition";
                leaf t0x0600..0xffff {
                  type string;
                  description
                      "[1536..65535] - accepts in decimal or hex";
                } //t0x0600..0xffff

              } //container etype

              container snap-oui {
                description
                    "Configure snap-oui match condition";
                leaf zero-non-zero {
                  type enumeration {
                    enum zero;
                    enum non-zero;
                  }
                  description
                      "keywords - specify snap-oui value";
                } //zero-non-zero

              } //container snap-oui

              container snap-pid {
                description
                    "Configure snap-pid match condition";
                leaf snap-pid {
                  type string;
                  description
                      "[0..65535] - accepts in decimal or hex";
                } //snap-pid

              } //container snap-pid

              container src-mac {
                description
                    "Configure source mac match condition";
                leaf ieee-address {
                  type alu:ieee-address;
                  description
                      "xx:xx:xx:xx:xx:xx or xx-xx-xx-xx-xx-xx";
                } //ieee-address

                leaf ieee-address-mask {
                  type string;
                  description
                      "xx:xx:xx:xx:xx:xx or xx-xx-xx-xx-xx-xx";
                } //ieee-address-mask

              } //container src-mac

              container ssap {
                description
                    "Configure ssap match condition";
                leaf ssap-value {
                  type string;
                  description
                      "[0.255] - accepts in decimal hex or binary";
                } //ssap-value

                leaf ssap-mask {
                  type string;
                  description
                      "[0.255] - accepts in decimal hex or binary";
                } //ssap-mask

              } //container ssap

              container svc-id {
                description
                    "Configure service-id to match on";
                leaf service-id {
                  type string;
                  description
                      "[1..2147483647] | <svc-name:64 char max>";
                } //service-id

              } //container svc-id

            } //container match

          } //list entry

        } //container mac-filter

      } //container management-access-filter

      container management-interface {
        description
            "Specify security configuration per interface";
        container classic-cli {
          description
              "Specify security configuration in classic cli";
          container read-algorithm {
            description
                "Specify hash read algorithm in classic cli";
            leaf hash {
              type boolean;
            } //hash

            leaf hash2 {
              type boolean;
            } //hash2

            leaf all-hash {
              type boolean;
            } //all-hash

            leaf custom {
              type boolean;
            } //custom

          } //container read-algorithm

          container write-algorithm {
            description
                "Specify hash write algorithm in classic cli";
            leaf hash {
              type boolean;
            } //hash

            leaf hash2 {
              type boolean;
            } //hash2

            leaf cleartext {
              type boolean;
            } //cleartext

            leaf custom {
              type boolean;
            } //custom

          } //container write-algorithm

        } //container classic-cli

        container grpc {
          description
              "Specify security configuration in grpc";
          container hash-algorithm {
            description
                "Specify hash write algorithm in grpc";
            leaf hash {
              type boolean;
            } //hash

            leaf hash2 {
              type boolean;
            } //hash2

            leaf cleartext {
              type boolean;
            } //cleartext

            leaf custom {
              type boolean;
            } //custom

          } //container hash-algorithm

        } //container grpc

        container md-cli {
          description
              "Specify security configuration in md-cli";
          leaf command-accounting-during-load {
            type boolean;
            description
                "Perform remote command accounting during a load or rollback operation";
          }

          container hash-algorithm {
            description
                "Specify hash write algorithm in md-cli";
            leaf hash {
              type boolean;
            } //hash

            leaf hash2 {
              type boolean;
            } //hash2

            leaf cleartext {
              type boolean;
            } //cleartext

            leaf custom {
              type boolean;
            } //custom

          } //container hash-algorithm

        } //container md-cli

        container netconf {
          description
              "Specify security configuration in netconf";
          container hash-algorithm {
            description
                "Specify hash write algorithm in netconf";
            leaf hash {
              type boolean;
            } //hash

            leaf hash2 {
              type boolean;
            } //hash2

            leaf cleartext {
              type boolean;
            } //cleartext

            leaf custom {
              type boolean;
            } //custom

          } //container hash-algorithm

        } //container netconf

        container output-authorization {
          description
              "Specify output authorization parameters";
          leaf md-interfaces {
            type boolean;
            description
                "Perform authorization of the outputs for md interfaces";
          }

          leaf telemetry-data {
            type boolean;
            description
                "Perform authorization of the outputs for telemetry data";
          }

        } //container output-authorization

      } //container management-interface

      container password {
        description
            "Configure password related parameters";
        container admin-password {
          description
              "Configure the password which enables the user to become an administrator";
          leaf password {
            type string {
            }
            description
                "Attribute password for admin-password";
          } //password

          leaf hash-hash2 {
            type enumeration {
              enum hash;
              enum hash2;
            }
            description
                "keywords - specify hashing scheme";
          } //hash-hash2

        } //container admin-password

        container aging {
          description
              "Max age in days allowed for passwords";
          leaf days {
            type uint32 {
              range "1..500";
            }
          } //days

        } //container aging

        container attempts {
          description
              "Max number of unsuccessful login attempts allowed in a specified time frame";
          leaf count {
            type uint32 {
              range "1..64";
            }
          } //count

          leaf time {
            type uint32 {
              range "0..60";
            }
          } //time

          leaf lockout {
            type uint32 {
              range "0..1440";
            }
          } //lockout

        } //container attempts

        container authentication-order {
          description
              "Sequence in which user password is authenticated";
          leaf-list method {
            type enumeration {
              enum local;
              enum radius;
              enum tacplus;
              enum ldap;
            }
            max-elements 4;
          } //method

          leaf exit-on-reject {
            type boolean;
          } //exit-on-reject

        } //container authentication-order

        container dynsvc-password {
          description
              "Configure the password which enables the user to configure dynamic services";
          leaf password {
            type string {
            }
            description
                "Attribute password for dynsvc-password";
          } //password

          leaf hash-hash2 {
            type enumeration {
              enum hash;
              enum hash2;
            }
            description
                "keywords - specify hashing scheme";
          } //hash-hash2

        } //container dynsvc-password

        container hashing {
          description
              "Password hashing algorithm";
          leaf hashing {
            type enumeration {
              enum bcrypt;
              enum sha2-pbkdf2;
              enum sha3-pbkdf2;
            }
            description
                "Attribute hashing for hashing";
          } //hashing

        } //container hashing

        container health-check {
          description
              "Enable/disable dynamic monitoring of radius, tacplus and ldap servers";
          leaf interval {
            type uint32 {
              range "6..1500";
            }
            description
                "[6..1500] in seconds";
          } //interval

        } //container health-check

        container history-size {
          description
              "Configure how many previous passwords a new password is matched against";
          leaf size {
            type uint32 {
              range "0..20";
            }
            description
                "[0..20] - default 0";
          } //size

        } //container history-size

        container minimum-age {
          description
              "Configure the minimum required age of a password before it can be changed 
               again";
          leaf days {
            type uint8 {
              range "0..1";
            }
          } //days

          leaf hrs {
            type uint32 {
              range "0..23";
            }
          } //hrs

          leaf min {
            type uint32 {
              range "0..59";
            }
          } //min

          leaf sec {
            type uint32 {
              range "0..59";
            }
          } //sec

        } //container minimum-age

        container minimum-change {
          description
              "Configure the minimum required distance between the old and the new password";
          leaf distance {
            type uint32 {
              range "1..20";
            }
          } //distance

        } //container minimum-change

        container vsd-password {
          description
              "Configure the password which enables the user to configure VSD services";
          leaf password {
            type string {
            }
            description
                "Attribute password for vsd-password";
          } //password

          leaf hash-hash2 {
            type enumeration {
              enum hash;
              enum hash2;
            }
            description
                "keywords - specify hashing scheme";
          } //hash-hash2

        } //container vsd-password

        container complexity-rules {
          description
              "Configure the complexity requirements for new local passwords";
          leaf allow-user-name {
            type boolean;
            description
                "Configure if the username is allowed as part of the password";
          }

          container credits {
            description
                "Configure the maximum credits given for usage of the different character 
                 classes in the local passwords";
            leaf lowercase {
              type uint32 {
                range "0..10";
              }
            } //lowercase

            leaf uppercase {
              type uint32 {
                range "0..10";
              }
              description
                  "credits";
            } //uppercase

            leaf numeric {
              type uint32 {
                range "0..10";
              }
              description
                  "credits";
            } //numeric

            leaf special-character {
              type uint32 {
                range "0..10";
              }
              description
                  "credits";
            } //special-character

          } //container credits

          container minimum-classes {
            description
                "Force the use of at least this many different character classes";
            leaf minimum {
              type uint32 {
                range "2..4";
              }
            } //minimum

          } //container minimum-classes

          container minimum-length {
            description
                "Configure the minimum length required for local passwords";
            leaf length {
              type uint32 {
                range "6..50";
              }
            } //length

          } //container minimum-length

          container repeated-characters {
            description
                "Configure how many times the same character is allowed to appear consecutively";
            leaf count {
              type uint32 {
                range "2..8";
              }
            } //count

          } //container repeated-characters

          container required {
            description
                "Force the user to use at least this many characters of each character class in 
                 his password";
            leaf lowercase {
              type uint32 {
                range "0..10";
              }
            } //lowercase

            leaf uppercase {
              type uint32 {
                range "0..10";
              }
              description
                  "count";
            } //uppercase

            leaf numeric {
              type uint32 {
                range "0..10";
              }
              description
                  "count";
            } //numeric

            leaf special-character {
              type uint32 {
                range "0..10";
              }
              description
                  "count";
            } //special-character

          } //container required

        } //container complexity-rules

        container enable-admin-control {
          description
              "Configure settings for enable-admin";
          container tacplus-map-to-priv-lvl {
            description
                "configure priv-lvl for interactive TACACS+ authentication request";
            leaf admin-priv-lvl {
              type uint32 {
                range "0..15";
              }
            } //admin-priv-lvl

          } //container tacplus-map-to-priv-lvl

        } //container enable-admin-control

      } //container password

      container pki {
        description
            "Configure PKI related parameters";
        container certificate-display-format {
          description
              "Configures the display format for certificate and CRL";
          leaf certificate-display-format-id {
            type enumeration {
              enum ascii;
              enum utf8;
            }
          } //certificate-display-format-id

        } //container certificate-display-format

        container certificate-expiration-warning {
          description
              "Configure certificate expiration warning";
          leaf hours {
            type int32 {
              range "0..8760";
            }
          } //hours

          leaf repeat {
            type int32 {
              range "0..8760";
            }
          } //repeat

        } //container certificate-expiration-warning

        container crl-expiration-warning {
          description
              "Configure CRL (certificate revoke list) expiration warning";
          leaf hours {
            type int32 {
              range "0..8760";
            }
          } //hours

          leaf repeat {
            type int32 {
              range "0..8760";
            }
          } //repeat

        } //container crl-expiration-warning

        container imported-format {
          description
              "Configure the encrypted file format";
          leaf imported-format-id {
            type enumeration {
              enum any;
              enum secure;
            }
          } //imported-format-id

        } //container imported-format

        container maximum-cert-chain-depth {
          description
              "Configure maximum certificate chain depth";
          leaf level {
            type uint32 {
              range "1..7";
            }
          } //level

        } //container maximum-cert-chain-depth

        list ca-profile {
          key "name";
          description
              "Create/delete Certificate-Authority profile parameters";
          leaf name {
            type string {
              length "1..32";
            }
          } //name

          container cert-file {
            description
                "Certificate file name";
            leaf filename {
              type string {
                length "1..95";
              }
            } //filename

          } //container cert-file

          container crl-file {
            description
                "CRL file name";
            leaf filename {
              type string {
                length "1..95";
              }
            } //filename

          } //container crl-file

          container description {
            description
                "Description of CA profile";
            leaf description-string {
              type string {
                length "1..80";
              }
            } //description-string

          } //container description

          container revocation-check {
            description
                "Configure revocation check method";
            leaf revocation-check-id {
              type enumeration {
                enum crl;
                enum crl-optional;
              }
            } //revocation-check-id

          } //container revocation-check

          leaf shutdown {
            type boolean;
            description
                "Enable/disable CA profile";
          }

          container auto-crl-update {
            description
                "Configure automated Certificate Revocation List update parameters";
            container periodic-update-interval {
              description
                  "Configure the interval between two consecutive CRL updates";
              leaf days {
                type uint32 {
                  range "0..366";
                }
                default 1;
                description
                    "[0..366] - Default: 1 day";
              } //days

              leaf hrs {
                type uint32 {
                  range "0..23";
                }
              } //hrs

              leaf min {
                type uint8 {
                  range "0..59";
                }
              } //min

              leaf sec {
                type uint8 {
                  range "0..59";
                }
              } //sec

            } //container periodic-update-interval

            container pre-update-time {
              description
                  "Configure the time period prior to the next update time of the current CRL";
              leaf days {
                type uint32 {
                  range "0..366";
                }
              } //days

              leaf hrs {
                type uint32 {
                  range "0..23";
                }
                default 1;
                description
                    "[0..23] - Default: 1 hour";
              } //hrs

              leaf min {
                type uint8 {
                  range "0..59";
                }
              } //min

              leaf sec {
                type uint8 {
                  range "0..59";
                }
              } //sec

            } //container pre-update-time

            container retry-interval {
              description
                  "Configure an interval before retrying to update CRL";
              leaf seconds {
                type uint32 {
                  range "1..31622400";
                }
                default 3600;
                description
                    "[1..31622400] - Default: 3600";
              } //seconds

            } //container retry-interval

            container schedule-type {
              description
                  "Configure the type of time scheduler for an automated CRL update";
              leaf schedule-type {
                type enumeration {
                  enum next-update-based;
                  enum periodic;
                }
                default "next-update-based";
                description
                    "next-update-based|periodic - Default: next-update-based";
              } //schedule-type

            } //container schedule-type

            leaf shutdown {
              type boolean;
              description
                  "Enable/disable an automated CRL update";
            }

            container crl-urls {
              description
                  "Configure the source URLs for CRL files";
              list url-entry {
                key "entry-id";
                description
                    "Create/delete URL entries";
                leaf entry-id {
                  type uint32 {
                    range "1..8";
                  }
                } //entry-id

                container file-transmission-profile {
                  description
                      "Configure the file transmission profile for updating a CRL";
                  leaf profile-name {
                    type string;
                  } //profile-name

                } //container file-transmission-profile

                container url {
                  description
                      "Configure the CRL update location";
                  leaf url {
                    type string {
                      length "1..180";
                    }
                  } //url

                } //container url

              } //list url-entry

            } //container crl-urls

          } //container auto-crl-update

          container cmpv2 {
            description
                "Configure CMPv2 parameters";
            leaf accept-unprotected-errormsg {
              type boolean;
              description
                  "Configure to accept unprotected error messages";
            }

            leaf accept-unprotected-pkiconf {
              type boolean;
              description
                  "Configure to accept unprotected PKI configuration messages";
            }

            leaf always-set-sender-for-ir {
              type boolean;
              description
                  "Configure to always set the sender field in CMPv2 header of all Initial 
                   Registration (IR) messages with the subject name. By default, the sender field 
                   is only set if an optional certificate is specified in the CMPv2 request.";
            }

            container http-response-timeout {
              description
                  "Configure HTTP response timeout";
              leaf timeout {
                type uint64 {
                  range "1..3600";
                }
              } //timeout

            } //container http-response-timeout

            container http-version {
              description
                  "Configure the http version for CMPv2 messages";
              leaf t1.0-1.1 {
                type string;
              } //t1.0-1.1

            } //container http-version

            container response-signing-cert {
              description
                  "Configure certificate file name of the response";
              leaf filename {
                type string {
                  length "1..95";
                }
              } //filename

            } //container response-signing-cert

            leaf same-recipnonce-for-pollreq {
              type boolean;
              description
                  "Configure to have same recipient nonce for poll requests";
            }

            container url {
              description
                  "Configure URL for CMPv2";
              leaf url-string {
                type string {
                  length "1..180";
                }
              } //url-string

              leaf service-id {
                type uint64 {
                  range "0..2147483647";
                }
                description
                    "1..2147483647: service in whose virtual router the server is reachable";
              } //service-id

              leaf service-name {
                type string {
                  length "1..64";
                }
                description
                    "[64 chars max]: service in whose virtual router the server is reachable 
                     If both service-id and service-name are not configured: server is reachable in 
                     the mgmt router (checked first) or base router";
              } //service-name

            } //container url

            container key-list {
              description
                  "Configure CMPv2 key parameters";
              list key {
                key "reference";
                description
                    "Configure CMPv2 key";
                leaf password {
                  type string {
                    length "1..500";
                  }
                  description
                      "password - [64 chars max] 
                       hash-key 
                       hash2-key 
                       custom-key";
                } //password

                leaf hash-hash2-custom {
                  type enumeration {
                    enum hash;
                    enum hash2;
                    enum custom;
                  }
                } //hash-hash2-custom

                leaf reference {
                  type string {
                    length "1..64";
                  }
                } //reference

              } //list key

            } //container key-list

          } //container cmpv2

          container ocsp {
            description
                "Configure OCSP parameters";
            container responder-url {
              description
                  "Configure responder URL";
              leaf url-string {
                type string {
                  length "1..180";
                }
              } //url-string

            } //container responder-url

            container service {
              description
                  "Configure OCSP service";
              leaf service-id {
                type uint64 {
                  range "0..2147483647";
                }
                description
                    "service-id :1..2147483647 
                     base-router:0";
              } //service-id

              leaf name {
                type string {
                  length "1..64";
                }
                description
                    "[64 chars max] 
                     base-router: empty string";
              } //name

            } //container service

            container transmission-profile {
              description
                  "Configure the file transmission profile for OCSP";
              leaf name {
                type string;
              } //name

            } //container transmission-profile

          } //container ocsp

        } //list ca-profile

        list common-name-list {
          key "name";
          description
              "Configure list of allowed common names";
          leaf name {
            type string;
          } //name

          list common-name {
            key "index";
            description
                "Configure allowed common name";
            leaf index {
              type uint32 {
                range "1..128";
              }
            } //index

            leaf cn-type {
              type enumeration {
                enum ip-address;
                enum domain-name;
              }
            } //cn-type

            leaf cn-value {
              type string {
                length "1..255";
              }
            } //cn-value

          } //list common-name

        } //list common-name-list

      } //container pki

      list profile {
        key "user-profile-name";
        description
            "Create/delete user profiles";
        leaf user-profile-name {
          type string {
            length "1..32";
          }
        } //user-profile-name

        container cli-session-group {
          description
              "Add/remove cli-session-group the profile belongs to";
          leaf session-group-name {
            type string;
          } //session-group-name

        } //container cli-session-group

        container combined-max-sessions {
          description
              "Maximum number of concurrent SSH & Telnet sessions";
          leaf number-of-sessions {
            type int32 {
              range "0..50";
            }
          } //number-of-sessions

        } //container combined-max-sessions

        container default-action {
          description
              "Default action for the profile";
          leaf deny-all-permit-all-none-read-only-all {
            type enumeration {
              enum deny-all;
              enum permit-all;
              enum none;
              enum read-only-all;
            }
            description
                "keywords";
          } //deny-all-permit-all-none-read-only-all

        } //container default-action

        leaf li {
          type boolean;
          description
              "Enable/disable Lawful Intercept profile identifier";
        }

        container renum {
          description
              "Renumber existing entries";
          leaf old-entry-number {
            type uint32 {
              range "1..9999";
            }
          } //old-entry-number

          leaf new-entry-number {
            type uint32 {
              range "1..9999";
            }
          } //new-entry-number

        } //container renum

        container ssh-max-sessions {
          description
              "Maximum number of concurrent SSH sessions";
          leaf number-of-sessions {
            type int32 {
              range "0..50";
            }
          } //number-of-sessions

        } //container ssh-max-sessions

        container telnet-max-sessions {
          description
              "Maximum number of concurrent TELNET sessions";
          leaf number-of-sessions {
            type int32 {
              range "0..50";
            }
          } //number-of-sessions

        } //container telnet-max-sessions

        list entry {
          key "entry-id";
          description
              "Match criteria entry for the profile";
          leaf entry-id {
            type uint32 {
              range "1..9999";
            }
          } //entry-id

          container action {
            description
                "Action to take when a user command matches this entry";
            leaf action-id {
              type enumeration {
                enum permit;
                enum deny;
                enum read-only;
                enum none;
              }
            } //action-id

          } //container action

          container description {
            description
                "Description for this entry";
            leaf description-string {
              type string {
                length "1..80";
              }
            } //description-string

          } //container description

          container match {
            description
                "Command string to match for this entry";
            leaf command-string {
              type string {
                length "1..255";
              }
              description
                  "[255 chars max]";
            } //command-string

          } //container match

        } //list entry

        container grpc {
          description
              "gRPC specific profile";
          container rpc-authorization {
            description
                "gRPC RPC command authorization";
            container get-rpc {
              status "obsolete";
              description
                  "Allow gRPC Get RPC";
              leaf permit-deny {
                type enumeration {
                  enum permit;
                  enum deny;
                }
                description
                    "keywords";
              } //permit-deny

            } //container get-rpc

            container gnmi-capabilities {
              description
                  "Allow gNMI Capabilities RPC";
              leaf permit-deny {
                type enumeration {
                  enum permit;
                  enum deny;
                }
                description
                    "keywords";
              } //permit-deny

            } //container gnmi-capabilities

            container gnmi-get {
              description
                  "Allow gNMI Get RPC";
              leaf permit-deny {
                type enumeration {
                  enum permit;
                  enum deny;
                }
                description
                    "keywords";
              } //permit-deny

            } //container gnmi-get

            container gnmi-set {
              description
                  "Allow gNMI Set RPC";
              leaf permit-deny {
                type enumeration {
                  enum permit;
                  enum deny;
                }
                description
                    "keywords";
              } //permit-deny

            } //container gnmi-set

            container gnmi-subscribe {
              description
                  "Allow gNMI Subscribe RPC";
              leaf permit-deny {
                type enumeration {
                  enum permit;
                  enum deny;
                }
                description
                    "keywords";
              } //permit-deny

            } //container gnmi-subscribe

            container gnoi-cert-mgmt-cangenerate {
              description
                  "Allow gNOI CertificateManagement CanGenerateCSR RPC";
              leaf permit-deny {
                type enumeration {
                  enum permit;
                  enum deny;
                }
                description
                    "keywords";
              } //permit-deny

            } //container gnoi-cert-mgmt-cangenerate

            container gnoi-cert-mgmt-getcert {
              description
                  "Allow gNOI CertificateManagement GetCertificates RPC";
              leaf permit-deny {
                type enumeration {
                  enum permit;
                  enum deny;
                }
                description
                    "keywords";
              } //permit-deny

            } //container gnoi-cert-mgmt-getcert

            container gnoi-cert-mgmt-install {
              description
                  "Allow gNOI CertificateManagement Install RPC";
              leaf permit-deny {
                type enumeration {
                  enum permit;
                  enum deny;
                }
                description
                    "keywords";
              } //permit-deny

            } //container gnoi-cert-mgmt-install

            container gnoi-cert-mgmt-revoke {
              description
                  "Allow gNOI CertificateManagement RevokeCertificates RPC";
              leaf permit-deny {
                type enumeration {
                  enum permit;
                  enum deny;
                }
                description
                    "keywords";
              } //permit-deny

            } //container gnoi-cert-mgmt-revoke

            container gnoi-cert-mgmt-rotate {
              description
                  "Allow gNOI CertificateManagement Rotate RPC";
              leaf permit-deny {
                type enumeration {
                  enum permit;
                  enum deny;
                }
                description
                    "keywords";
              } //permit-deny

            } //container gnoi-cert-mgmt-rotate

            container gnoi-system-cancelreboot {
              description
                  "Allow gNOI System CancelReboot RPC";
              leaf permit-deny {
                type enumeration {
                  enum permit;
                  enum deny;
                }
                description
                    "keywords";
              } //permit-deny

            } //container gnoi-system-cancelreboot

            container gnoi-system-reboot {
              description
                  "Allow gNOI System Reboot RPC";
              leaf permit-deny {
                type enumeration {
                  enum permit;
                  enum deny;
                }
                description
                    "keywords";
              } //permit-deny

            } //container gnoi-system-reboot

            container gnoi-system-rebootstatus {
              description
                  "Allow gNOI System RebootStatus RPC";
              leaf permit-deny {
                type enumeration {
                  enum permit;
                  enum deny;
                }
                description
                    "keywords";
              } //permit-deny

            } //container gnoi-system-rebootstatus

            container gnoi-system-setpackage {
              description
                  "Allow gNOI System SetPackage RPC";
              leaf permit-deny {
                type enumeration {
                  enum permit;
                  enum deny;
                }
                description
                    "keywords";
              } //permit-deny

            } //container gnoi-system-setpackage

            container gnoi-system-switchcontrolprocessor {
              description
                  "Allow gNOI System SwitchControlProcessor RPC";
              leaf permit-deny {
                type enumeration {
                  enum permit;
                  enum deny;
                }
                description
                    "keywords";
              } //permit-deny

            } //container gnoi-system-switchcontrolprocessor

            container md-cli-session {
              description
                  "Allow MdCli Session RPC";
              leaf permit-deny {
                type enumeration {
                  enum permit;
                  enum deny;
                }
                description
                    "keywords";
              } //permit-deny

            } //container md-cli-session

            container rib-api-getversion {
              description
                  "Allow RibApi GetVersion RPC";
              leaf permit-deny {
                type enumeration {
                  enum permit;
                  enum deny;
                }
                description
                    "keywords";
              } //permit-deny

            } //container rib-api-getversion

            container rib-api-modify {
              description
                  "Allow RibApi Modify RPC";
              leaf permit-deny {
                type enumeration {
                  enum permit;
                  enum deny;
                }
                description
                    "keywords";
              } //permit-deny

            } //container rib-api-modify

            container set-rpc {
              status "obsolete";
              description
                  "Allow gRPC Set RPC";
              leaf permit-deny {
                type enumeration {
                  enum permit;
                  enum deny;
                }
                description
                    "keywords";
              } //permit-deny

            } //container set-rpc

            container subscribe-rpc {
              status "obsolete";
              description
                  "Allow gRPC Subscribe RPC";
              leaf permit-deny {
                type enumeration {
                  enum permit;
                  enum deny;
                }
                description
                    "keywords";
              } //permit-deny

            } //container subscribe-rpc

          } //container rpc-authorization

        } //container grpc

        container netconf {
          description
              "netconf specific profile";
          container base-op-authorization {
            description
                "netconf basic operation authorization";
            leaf get-data {
              type boolean;
            }

            leaf kill-session {
              type boolean;
              description
                  "Allow netconf kill session";
            }

            leaf lock {
              type boolean;
              description
                  "Allow netconf lock session";
            }

          } //container base-op-authorization

        } //container netconf

      } //list profile

      container radius {
        presence
            "Configure RADIUS authentication parameters for the system";
        container access-algorithm {
          description
              "Configure the algorithm used to access the set of RADIUS servers";
          leaf direct-round-robin {
            type enumeration {
              enum direct;
              enum round-robin;
            }
            description
                "keywords";
          } //direct-round-robin

        } //container access-algorithm

        leaf accounting {
          type boolean;
          description
              "Enable/disable RADIUS command accounting";
        }

        container accounting-port {
          description
              "Port number on which to contact RADIUS server for accounting requests";
          leaf port {
            type string;
            description
                "[1..65535]";
          } //port

        } //container accounting-port

        leaf authorization {
          type boolean;
          description
              "Enable/disable RADIUS command authorization";
        }

        leaf interactive-authentication {
          type boolean;
          description
              "Enable/disable RADIUS interactive authentication";
        }

        container port {
          description
              "Port number on which to contact RADIUS server";
          leaf port {
            type int32 {
              range "1..65535";
            }
          } //port

        } //container port

        container retry {
          description
              "Number of attempts to retry contacting the RADIUS server";
          leaf count {
            type uint32 {
              range "1..10";
            }
          } //count

        } //container retry

        list server {
          key "server-index";
          description
              "Add/remove a RADIUS server";
          leaf server-index {
            type uint32 {
              range "1..5";
            }
          } //server-index

          leaf address {
            type string;
            description
                "Attribute ip-address for server";
          } //address

          leaf secret {
            type string {
              length "1..500";
            }
            description
                "secret-key - [64 chars max] 
                 hash-key 
                 hash2-key 
                 custom-key";
          } //secret

          leaf hash-hash2-custom {
            type enumeration {
              enum hash;
              enum hash2;
              enum custom;
            }
            description
                "keywords - specify hashing scheme";
          } //hash-hash2-custom

        } //list server

        leaf shutdown {
          type boolean;
          description
              "Enable/disable RADIUS protocol operation";
        }

        container timeout {
          description
              "Timeout for a response from the RADIUS server";
          leaf seconds {
            type uint32 {
              range "1..90";
            }
          } //seconds

        } //container timeout

        leaf use-default-template {
          type boolean;
          description
              "Enable-disable RADIUS default template";
        }

      } //container radius

      container snmp {
        description
            "Configure SNMP security parameters";
        list access {
          key "group security-model security-level context prefix-match read write notify";
          description
              "Configure access groups for SNMP security";
          leaf group {
            type string {
              length "1..32";
            }
          } //group

          leaf security-model {
            type enumeration {
              enum snmpv1;
              enum snmpv2c;
              enum usm;
            }
            description
                "snmpv1|snmpv2c|usm - keywords";
          } //security-model

          leaf security-level {
            type enumeration {
              enum no-auth-no-privacy;
              enum auth-no-privacy;
              enum privacy;
            }
            description
                "no-auth-no-privacy|auth-no-privacy|privacy - keywords";
          } //security-level

          leaf context {
            type string {
              length "1..32";
            }
          } //context

          leaf prefix-match {
            type enumeration {
              enum exact;
              enum prefix;
            }
          } //prefix-match

          leaf read {
            type string {
              length "1..32";
            }
          } //read

          leaf write {
            type string {
              length "1..32";
            }
          } //write

          leaf notify {
            type string {
              length "1..32";
            }
          } //notify

        } //list access

        container attempts {
          description
              "Max number of SNMP accesses with bad community names allowed in a specified 
               time frame";
          leaf count {
            type uint32 {
              range "1..64";
            }
          } //count

          leaf time {
            type uint32 {
              range "0..60";
            }
          } //time

          leaf lockout {
            type uint32 {
              range "0..1440";
            }
          } //lockout

        } //container attempts

        list community {
          key "community-string hash-hash2-custom";
          description
              "Create/delete SNMP community strings";
          leaf community-string {
            type string {
              length "1..500";
            }
            description
                "community-string - [32 chars max] 
                 hash-key 
                 hash2-key 
                 custom-key";
          } //community-string

          leaf hash-hash2-custom {
            type enumeration {
              enum hash;
              enum hash2;
              enum custom;
            }
            description
                "keywords - hashing scheme for community-string";
          } //hash-hash2-custom

          leaf access-permissions {
            type enumeration {
              enum r;
              enum rw;
              enum rwa;
              enum mgmt;
              enum vpls-mgmt;
            }
          } //access-permissions

          leaf version {
            type enumeration {
              enum v1;
              enum v2c;
              enum both;
            }
          } //version

          leaf src-access-list {
            type string {
              length "1..32";
            }
            description
                "list-name - [32 chars max]";
          } //src-access-list

        } //list community

        list usm-community {
          key "community-string hash-hash2-custom";
          description
              "Translation of SNMPv3 to SNMPv1/v2 capability";
          leaf community-string {
            type string {
              length "1..500";
            }
            description
                "community-string - [32 chars max] 
                 hash-key 
                 hash2-key 
                 custom-key";
          } //community-string

          leaf group {
            type string {
              length "1..32";
            }
          } //group

          leaf hash-hash2-custom {
            type enumeration {
              enum hash;
              enum hash2;
              enum custom;
            }
            description
                "keywords - hashing scheme for community-string";
          } //hash-hash2-custom

          leaf src-access-list {
            type string {
              length "1..32";
            }
            description
                "list-name - [32 chars max]";
          } //src-access-list

        } //list usm-community

        list src-access-list {
          key "list-name";
          description
              "Create/Delete Source Access List for Communities";
          leaf list-name {
            type string {
              length "1..32";
            }
          } //list-name

          list src-host {
            key "host-name";
            description
                "Enable/Disable source address for the access list.";
            leaf host-name {
              type string {
                length "1..32";
              }
            } //host-name

            leaf address {
              type string;
              description
                  "Attribute ip-address for src-host";
            } //address

          } //list src-host

        } //list src-access-list

        list view {
          key "view-name subtree";
          description
              "Configure an SNMP view";
          leaf view-name {
            type string {
              length "1..32";
            }
          } //view-name

          leaf subtree {
            type string {
            }
            description
                "dotted OID value a.b.c.d.e.....";
          } //subtree

          container mask {
            description
                "Mask associated with the view";
            leaf mask-value {
              type string {
                length "1..16";
              }
              description
                  "binary value (starting with 0b) or hex value (starting with 0x)";
            } //mask-value

            leaf type {
              type enumeration {
                enum included;
                enum excluded;
              }
              default "included";
              description
                  "keywords";
            } //type

          } //container mask

        } //list view

      } //container snmp

      container source-address {
        description
            "Configure source address for various applications";
        list application {
          key "app";
          description
              "Configure application to use source address";
          leaf app {
            type enumeration {
              enum cflowd;
              enum dns;
              enum ftp;
              enum ldap;
              enum ntp;
              enum ping;
              enum ptp;
              enum radius;
              enum sflow;
              enum snmptrap;
              enum sntp;
              enum ssh;
              enum syslog;
              enum tacplus;
              enum telnet;
              enum traceroute;
              enum mcreporter;
              enum icmp-error;
            }
          } //app

          leaf ip-int-name-ip-address {
            type string;
            description
                "Attribute ip-int-name|ip-address for application";
          } //ip-int-name-ip-address

        } //list application

        list application6 {
          key "app";
          description
              "Configure application to use source IPv6 address";
          leaf app {
            type enumeration {
              enum cflowd;
              enum dns;
              enum ftp;
              enum ldap;
              enum ntp;
              enum ping;
              enum ptp;
              enum radius;
              enum sflow;
              enum snmptrap;
              enum sntp;
              enum ssh;
              enum syslog;
              enum tacplus;
              enum telnet;
              enum traceroute;
              enum mcreporter;
              enum icmp6-error;
            }
          } //app

          leaf ipv6-address {
            type inet:ipv6-address;
            description
                "x:x:x:x:x:x:x:x (eight 16-bit pieces)";
          } //ipv6-address

        } //list application6

      } //container source-address

      container ssh {
        description
            "Configure SSH parameters";
        leaf preserve-key {
          type boolean;
          description
              "enable/disable persistence of host-key";
        }

        leaf server-shutdown {
          type boolean;
          description
              "start/stop SSH server";
        }

        container version {
          description
              "Configure the SSH version";
          leaf ssh-version {
            type enumeration {
              enum 1;
              enum 2;
              enum 1-2;
            }
            description
                "1 - SSH-1 only 
                 2 - SSH-2 only (default) 
                 1-2 - SSH-1 and SSH-2";
          } //ssh-version

        } //container version

        container client-cipher-list {
          description
              "Configure the list of allowed ciphers by the SSH client";
          leaf protocol-version {
            type uint32 {
              range "1..2";
            }
          } //protocol-version

          list cipher {
            key "index";
            description
                "Configure a cipher";
            leaf index {
              type uint32 {
                range "1..255";
              }
            } //index

            leaf name {
              type enumeration {
                enum aes128-ctr;
                enum aes192-ctr;
                enum aes256-ctr;
                enum des;
                enum 3des;
                enum blowfish;
                enum 3des-cbc;
                enum blowfish-cbc;
                enum cast128-cbc;
                enum arcfour;
                enum aes128-cbc;
                enum aes192-cbc;
                enum aes256-cbc;
                enum rijndael-cbc;
              }
            } //name

          } //list cipher

        } //container client-cipher-list

        container client-kex-list {
          description
              "Configure the list of allowed kex algorithms by the SSH client";
          list kex {
            key "index";
            description
                "Configure a kex algorithm";
            leaf index {
              type uint32 {
                range "1..255";
              }
            } //index

            leaf name {
              type enumeration {
                enum diffie-hellman-group16-sha512;
                enum diffie-hellman-group14-sha256;
                enum diffie-hellman-group14-sha1;
                enum diffie-hellman-group-exchange-sha1;
                enum diffie-hellman-group1-sha1;
              }
            } //name

          } //list kex

        } //container client-kex-list

        container client-mac-list {
          description
              "Configure the list of allowed mac algorithms by the SSH client";
          list mac {
            key "index";
            description
                "Configure a mac algorithm";
            leaf index {
              type uint32 {
                range "1..255";
              }
            } //index

            leaf name {
              type enumeration {
                enum hmac-sha2-512;
                enum hmac-sha2-256;
                enum hmac-sha1;
                enum hmac-sha1-96;
                enum hmac-md5;
                enum hmac-ripemd160;
                enum hmac-ripemd160-openssh-com;
                enum hmac-md5-96;
              }
            } //name

          } //list mac

        } //container client-mac-list

        container key-re-exchange {
          description
              "Configure key-re-exchange parameters";
          container client {
            description
                "Configure key-re-exchange parameters for client";
            container mbytes {
              description
                  "Number of megabytes transmitted on a ssh session after which ssh client will 
                   initiate the key-re-exchange";
              leaf megabytes {
                type uint32 {
                  range "1..64000";
                }
                description
                    "[1..64000] - Default 1024";
              } //megabytes

              leaf disable {
                type boolean;
              } //disable

            } //container mbytes

            container minutes {
              description
                  "Time interval after which ssh client will initiate the key-re-exchange";
              leaf minutes {
                type uint32 {
                  range "1..1440";
                }
                description
                    "[1..1440] - Default 60";
              } //minutes

              leaf disable {
                type boolean;
              } //disable

            } //container minutes

            leaf shutdown {
              type boolean;
              description
                  "Enable/disable initiating of the key-re-exchange when configured thresholds 
                   are reached";
            }

          } //container client

          container server {
            description
                "Configure key-re-exchange parameters for server";
            container mbytes {
              description
                  "Number of megabytes transmitted on a ssh session after which ssh server will 
                   initiate the key-re-exchange";
              leaf megabytes {
                type uint32 {
                  range "1..64000";
                }
                description
                    "[1..64000] - Default 1024";
              } //megabytes

              leaf disable {
                type boolean;
              } //disable

            } //container mbytes

            container minutes {
              description
                  "Time interval after which ssh server will initiate the key-re-exchange";
              leaf minutes {
                type uint32 {
                  range "1..1440";
                }
                description
                    "[1..1440] - Default 60";
              } //minutes

              leaf disable {
                type boolean;
              } //disable

            } //container minutes

            leaf shutdown {
              type boolean;
              description
                  "Enable/disable initiating of the key-re-exchange when configured thresholds 
                   are reached";
            }

          } //container server

        } //container key-re-exchange

        container server-cipher-list {
          description
              "Configure the list of allowed ciphers by the SSH server";
          leaf protocol-version {
            type uint32 {
              range "1..2";
            }
          } //protocol-version

          list cipher {
            key "index";
            description
                "Configure a cipher";
            leaf index {
              type uint32 {
                range "1..255";
              }
            } //index

            leaf name {
              type enumeration {
                enum aes128-ctr;
                enum aes192-ctr;
                enum aes256-ctr;
                enum des;
                enum 3des;
                enum blowfish;
                enum 3des-cbc;
                enum blowfish-cbc;
                enum cast128-cbc;
                enum arcfour;
                enum aes128-cbc;
                enum aes192-cbc;
                enum aes256-cbc;
                enum rijndael-cbc;
              }
            } //name

          } //list cipher

        } //container server-cipher-list

        container server-kex-list {
          description
              "Configure the list of allowed kex algorithms by the SSH server";
          list kex {
            key "index";
            description
                "Configure a kex algorithm";
            leaf index {
              type uint32 {
                range "1..255";
              }
            } //index

            leaf name {
              type enumeration {
                enum diffie-hellman-group16-sha512;
                enum diffie-hellman-group14-sha256;
                enum diffie-hellman-group14-sha1;
                enum diffie-hellman-group-exchange-sha1;
                enum diffie-hellman-group1-sha1;
              }
            } //name

          } //list kex

        } //container server-kex-list

        container server-mac-list {
          description
              "Configure the list of allowed mac algorithms by the SSH server";
          list mac {
            key "index";
            description
                "Configure a mac algorithm";
            leaf index {
              type uint32 {
                range "1..255";
              }
            } //index

            leaf name {
              type enumeration {
                enum hmac-sha2-512;
                enum hmac-sha2-256;
                enum hmac-sha1;
                enum hmac-sha1-96;
                enum hmac-md5;
                enum hmac-ripemd160;
                enum hmac-ripemd160-openssh-com;
                enum hmac-md5-96;
              }
            } //name

          } //list mac

        } //container server-mac-list

      } //container ssh

      container tacplus {
        presence
            "Configure TACACS+ authentication parameters for the system";
        container accounting {
          description
              "Enable/disable TACACS+ command accounting";
          leaf record-type {
            type enumeration {
              enum start-stop;
              enum stop-only;
            }
            description
                "keywords";
          } //record-type

        } //container accounting

        container authorization {
          description
              "Enable/disable TACACS+ command authorization";
          leaf use-priv-lvl {
            type boolean;
          } //use-priv-lvl

        } //container authorization

        leaf interactive-authentication {
          type boolean;
          description
              "Enable/disable TACACS+ interactive authentication";
        }

        list server {
          key "server-index";
          description
              "Add/remove a TACACS+ server";
          leaf server-index {
            type uint32 {
              range "1..5";
            }
          } //server-index

          leaf address {
            type string;
            description
                "Attribute ip-address for server";
          } //address

          leaf secret {
            type string {
              length "1..500";
            }
            description
                "secret-key - [128 chars max] 
                 hash-key 
                 hash2-key 
                 custom-key";
          } //secret

          leaf hash-hash2-custom {
            type enumeration {
              enum hash;
              enum hash2;
              enum custom;
            }
            description
                "keywords - specify hashing scheme";
          } //hash-hash2-custom

          leaf port {
            type uint16;
            default 49;
          } //port

        } //list server

        leaf shutdown {
          type boolean;
          description
              "Enable/disable TACACS+ protocol operation";
        }

        container timeout {
          description
              "Timeout for a response from the TACACS+ server";
          leaf seconds {
            type uint32 {
              range "1..90";
            }
          } //seconds

        } //container timeout

        leaf use-default-template {
          type boolean;
          description
              "Enable/disable TACACS+ default template";
        }

        container priv-lvl-map {
          presence
              "Configure privilege level mapping";
          list priv-lvl {
            key "priv-lvl";
            description
                "Configure a user profile for this privilege level";
            leaf priv-lvl {
              type uint32 {
                range "0..15";
              }
            } //priv-lvl

            leaf user-profile-name {
              type string {
                length "1..32";
              }
            } //user-profile-name

          } //list priv-lvl

        } //container priv-lvl-map

      } //container tacplus

      container tech-support {
        description
            "Configure system level security parameters for tech-support";
        container ts-location {
          description
              "Configure tech-support default file location";
          leaf file-url {
            type string {
            }
            description
                "Attribute file-url for ts-location";
          } //file-url

        } //container ts-location

      } //container tech-support

      container tls {
        description
            "Configure TLS parameters";
        list cert-profile {
          key "profile-name";
          description
              "Configure TLS Certificate profile information";
          leaf profile-name {
            type string;
          } //profile-name

          leaf shutdown {
            type boolean;
            description
                "Administratively enable/disable the certificate profile";
          }

          list entry {
            key "entry-id";
            description
                "Configure certificate profile entry information";
            leaf entry-id {
              type uint32 {
                range "1..8";
              }
            } //entry-id

            container cert {
              description
                  "Configure certificate file name";
              leaf cert-filename {
                type string {
                  length "1..95";
                }
              } //cert-filename

            } //container cert

            container key {
              description
                  "Configure key file";
              leaf key-filename {
                type string {
                  length "1..95";
                }
              } //key-filename

            } //container key

            container send-chain {
              presence
                  "Configure chain information";
              list ca-profile {
                key "name";
                description
                    "Configure a Certificate-Authority profile to the send-chain";
                leaf name {
                  type string;
                } //name

              } //list ca-profile

            } //container send-chain

          } //list entry

        } //list cert-profile

        list client-cipher-list {
          key "name";
          description
              "Configure TLS client desired ciphers";
          leaf name {
            type string;
          } //name

          list cipher {
            key "index";
            description
                "Configure TLS cipher suite code";
            leaf index {
              type uint32 {
                range "1..255";
              }
            } //index

            leaf name {
              type enumeration {
                enum tls-rsa-with-null-md5;
                enum tls-rsa-with-null-sha;
                enum tls-rsa-with-null-sha256;
                enum tls-rsa-with3des-ede-cbc-sha;
                enum tls-rsa-with-aes128-cbc-sha;
                enum tls-rsa-with-aes256-cbc-sha;
                enum tls-rsa-with-aes128-cbc-sha256;
                enum tls-rsa-with-aes256-cbc-sha256;
              }
            } //name

          } //list cipher

        } //list client-cipher-list

        list client-tls-profile {
          key "name";
          description
              "Configure TLS client information";
          leaf name {
            type string;
          } //name

          container cert-profile {
            description
                "Configure the Certificate profile";
            leaf name {
              type string;
            } //name

          } //container cert-profile

          container cipher-list {
            description
                "Configure the list of desired ciphers";
            leaf name {
              type string;
            } //name

          } //container cipher-list

          leaf shutdown {
            type boolean;
            description
                "Enable/disable the Client TLS profile";
          }

          container trust-anchor-profile {
            description
                "Configure the Trust Anchor profile";
            leaf name {
              type string;
            } //name

          } //container trust-anchor-profile

        } //list client-tls-profile

        list server-cipher-list {
          key "name";
          description
              "Configure TLS server ciphers";
          leaf name {
            type string;
          } //name

          list cipher {
            key "index";
            description
                "Configure TLS cipher suite code";
            leaf index {
              type uint32 {
                range "1..255";
              }
            } //index

            leaf name {
              type enumeration {
                enum tls-rsa-with-null-md5;
                enum tls-rsa-with-null-sha;
                enum tls-rsa-with-null-sha256;
                enum tls-rsa-with3des-ede-cbc-sha;
                enum tls-rsa-with-aes128-cbc-sha;
                enum tls-rsa-with-aes256-cbc-sha;
                enum tls-rsa-with-aes128-cbc-sha256;
                enum tls-rsa-with-aes256-cbc-sha256;
              }
            } //name

          } //list cipher

        } //list server-cipher-list

        list server-tls-profile {
          key "name";
          description
              "Configure TLS server profile";
          leaf name {
            type string;
          } //name

          container cert-profile {
            description
                "Configure the certificate profile";
            leaf name {
              type string;
            } //name

          } //container cert-profile

          container cipher-list {
            description
                "Configure the list of desired ciphers";
            leaf name {
              type string;
            } //name

          } //container cipher-list

          leaf shutdown {
            type boolean;
            description
                "Enable/disable the server TLS profile";
          }

          container tls-re-negotiate-timer {
            description
                "Configure the TLS renegotiation timer";
            leaf tls-re-negotiate-timer-id {
              type uint32 {
                range "0..65000";
              }
              default 0;
            } //tls-re-negotiate-timer-id

          } //container tls-re-negotiate-timer

          container authenticate-client {
            description
                "client authentication via certificate";
            container cn-authentication {
              description
                  "Assign Common Name list";
              leaf common-name-list {
                type string {
                  length "1..32";
                }
              } //common-name-list

            } //container cn-authentication

            container trust-anchor-profile {
              description
                  "Assign the trust anchor used by TLS profile";
              leaf name {
                type string;
              } //name

            } //container trust-anchor-profile

          } //container authenticate-client

        } //list server-tls-profile

        list trust-anchor-profile {
          key "name";
          description
              "Configure TLS Trust Anchor profile information";
          leaf name {
            type string;
          } //name

          list trust-anchor {
            key "ca-profile-name";
            description
                "Configure TLS Trust Anchor";
            leaf ca-profile-name {
              type string {
                length "1..32";
              }
            } //ca-profile-name

          } //list trust-anchor

        } //list trust-anchor-profile

      } //container tls

      list user {
        key "user-name";
        description
            "Configure a local user";
        leaf user-name {
          type string {
            length "1..32";
          }
        } //user-name

        container access {
          description
              "Grant/deny a user access permissions for console ftp grpc li netconf or snmp";
          leaf ftp {
            type boolean;
          } //ftp

          leaf snmp {
            type boolean;
          } //snmp

          leaf console {
            type boolean;
          } //console

          leaf li {
            type boolean;
          } //li

          leaf netconf {
            type boolean;
          } //netconf

          leaf grpc {
            type boolean;
          } //grpc

        } //container access

        container cli-engine {
          description
              "User-level override for CLI engine access configuration";
          leaf-list engine-type {
            type enumeration {
              enum classic-cli;
              enum md-cli;
            }
            max-elements 2;
          } //engine-type

          leaf cli-engine-id {
            type enumeration {
              enum classic-cli;
              enum classic-cli-exclusive;
              enum md-cli;
            }
            status "obsolete";
          } //cli-engine-id

        } //container cli-engine

        container home-directory {
          description
              "Home directory for the user";
          leaf url-prefix-directorydirectory-directory-.. {
            type string {
              length "1..200";
            }
          } //url-prefix-directorydirectory-directory-..

        } //container home-directory

        container password {
          description
              "Password for the user";
          leaf password {
            type string {
            }
            description
                "Attribute password for password";
          } //password

        } //container password

        leaf restricted-to-home {
          type boolean;
          description
              "Restrict user to home directory";
        }

        list rsa-key {
          key "key-id";
          status "obsolete";
          description
              "Configure RSA keys for this user";
          leaf key-id {
            type uint32 {
              range "1..32";
            }
          } //key-id

          leaf public-key-value {
            type string {
              length "1..255";
            }
          } //public-key-value

        } //list rsa-key

        container console {
          description
              "Configure user profile membership for the console";
          leaf cannot-change-password {
            type boolean;
            description
                "Allow/disallow password changing privileges";
          }

          container login-exec {
            description
                "File to be executed when a user successfully logs in";
            leaf url-prefix-source-url {
              type string {
                length "1..200";
              }
              description
                  "Attribute url-prefix:source-url for login-exec";
            } //url-prefix-source-url

          } //container login-exec

          container member {
            description
                "Allow user to access a profile";
            leaf-list user-profile-name {
              type string {
                length "1..32";
              }
              max-elements 8;
            } //user-profile-name

          } //container member

          leaf new-password-at-login {
            type boolean;
            description
                "Enable/disable prompting a user to change password at login";
          }

        } //container console

        container public-keys {
          description
              "Configure SSH public keys for the user";
          container ecdsa {
            description
                "Configure ECDSA public keys for the user";
            list ecdsa-key {
              key "ecdsa-public-key-id";
              description
                  "Associates an ECDSA public key with the user-name";
              leaf ecdsa-public-key-id {
                type uint32 {
                  range "1..32";
                }
              } //ecdsa-public-key-id

              container description {
                description
                    "Configure ECDSA key description";
                leaf description-string {
                  type string {
                    length "1..80";
                  }
                } //description-string

              } //container description

              container key-value {
                description
                    "Configure ECDSA key value";
                leaf ecdsa-public-key-value {
                  type string {
                    length "1..255";
                  }
                } //ecdsa-public-key-value

              } //container key-value

            } //list ecdsa-key

          } //container ecdsa

          container rsa {
            description
                "Configure RSA public keys for the user";
            list rsa-key {
              key "rsa-public-key-id";
              description
                  "Associates an RSA public key with the user-name";
              leaf rsa-public-key-id {
                type uint32 {
                  range "1..32";
                }
              } //rsa-public-key-id

              container description {
                description
                    "Configure RSA key description";
                leaf description-string {
                  type string {
                    length "1..80";
                  }
                } //description-string

              } //container description

              container key-value {
                description
                    "Configure RSA key value";
                leaf rsa-public-key-value {
                  type string {
                    length "1..800";
                  }
                } //rsa-public-key-value

              } //container key-value

            } //list rsa-key

          } //container rsa

        } //container public-keys

        container snmp {
          description
              "Configure SNMP group membership for the user";
          container authentication {
            description
                "Authentication in the SNMP model";
            leaf none {
              type boolean;
            } //none

            leaf authentication-id {
              type enumeration {
                enum md5;
                enum sha;
              }
            } //authentication-id

            leaf privacy {
              type enumeration {
                enum none;
                enum des-key;
                enum aes-128-cfb-key;
              }
              default "none";
              description
                  "Attribute privacy-level for authentication";
            } //privacy

            leaf key-1 {
              type string {
                length "1..500";
              }
              description
                  "[32 hex chars for md5, 40 hex chars for sha] 
                   hash-key 
                   hash2-key 
                   custom-key";
            } //key-1

            leaf key-2 {
              type string {
                length "1..500";
              }
              description
                  "[32 hex chars] - localized privacy key 
                   hash-key 
                   hash2-key 
                   custom-key";
            } //key-2

            leaf hash-hash2-custom {
              type enumeration {
                enum hash;
                enum hash2;
                enum custom;
              }
            } //hash-hash2-custom

          } //container authentication

          container group {
            description
                "Associate the user with a group name";
            leaf group-name {
              type string {
                length "1..32";
              }
            } //group-name

          } //container group

        } //container snmp

      } //list user

      list user-template {
        key "user-template-id";
        description
            "Configure default user templates";
        leaf user-template-id {
          type enumeration {
            enum tacplus_default;
            enum radius_default;
            enum ldap_default;
          }
        } //user-template-id

        container access {
          description
              "Grant/deny the user based on this template access permissions for ftp or 
               console";
          leaf ftp {
            type boolean;
          } //ftp

          leaf console {
            type boolean;
          } //console

          leaf li {
            type boolean;
          } //li

          leaf netconf {
            type boolean;
          } //netconf

          leaf grpc {
            type boolean;
          } //grpc

        } //container access

        container home-directory {
          description
              "Home directory for the user based on this template";
          leaf url-prefix-directorydirectory-directory-.. {
            type string {
              length "1..200";
            }
          } //url-prefix-directorydirectory-directory-..

        } //container home-directory

        container profile {
          description
              "User profile for the user based on this template";
          leaf user-profile-name {
            type string {
              length "1..32";
            }
          } //user-profile-name

        } //container profile

        leaf restricted-to-home {
          type boolean;
          description
              "Restrict user based on the template to home directory";
        }

        container console {
          description
              "Configure user template profile membership for the console";
          container login-exec {
            description
                "File to be executed when a user derived from the template successfully logs in";
            leaf url-prefix-source-url {
              type string {
                length "1..200";
              }
            } //url-prefix-source-url

          } //container login-exec

        } //container console

      } //list user-template

    } //container security

  } //grouping alu-conf-sys-sec-r13

} //module  alu-conf-sys-sec-r13
