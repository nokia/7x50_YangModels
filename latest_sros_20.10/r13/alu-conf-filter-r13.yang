module alu-conf-filter-r13 {
  yang-version "1";

  namespace "urn:alcatel-lucent.com:sros:ns:yang:conf-filter-r13";

  prefix "conf-filter-r13";

  import alu-conf-ip-except-r13 {
    prefix "conf-ip-except-r13";
  }
  import alu-conf-ipv6-except-r13 {
    prefix "conf-ipv6-except-r13";
  }
  import alu-types {
    prefix "alu";
  }
  import ietf-inet-types {
    prefix "inet";
  }

  alu:alu-major-release "rel20";

  organization "Alcatel-Lucent";

  contact
      "Alcatel-Lucent SR OS Support 
       Web: <http://www.alcatel-lucent.com>";

  description
      "Alcatel-Lucent YANG Data model to configure line card ACL Filters on SR OS 
       based routers. 
       
       Copyright 2014-2015 Alcatel-Lucent, 2016 Nokia. All rights reserved. 
       Reproduction of this document is authorized on the condition that the 
       foregoing copyright notice is included. 
       
       This alu-conf-filter-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2022-09-21";

  grouping alu-conf-filter-r13 {
    container filter {
      description
          "Configure line card ACL Filters";
      container copy {
        description
            "Copy filters and entries";
        container ip-filter {
          description
              "Copy ip filter and entry";
          leaf src-filter-id {
            type string;
            description
                "[1..65535]|<name:64 char max>";
          } //src-filter-id

          leaf src-entry {
            type uint32 {
              range "1..2097151";
            }
            description
                "Attribute src-entry-id for ip-filter";
          } //src-entry

          leaf to {
            type string;
            description
                "[1..65535]|<name:64 char max>";
          } //to

          leaf dst-entry {
            type uint32 {
              range "1..2097151";
            }
            description
                "Attribute dst-entry-id for ip-filter";
          } //dst-entry

          leaf overwrite {
            type boolean;
          } //overwrite

        } //container ip-filter

        container ipv6-filter {
          description
              "Copy IPv6 filter and entry";
          leaf src-filter-id {
            type string;
            description
                "[1..65535]|<name:64 char max>";
          } //src-filter-id

          leaf src-entry {
            type uint32 {
              range "1..2097151";
            }
            description
                "Attribute src-entry-id for ipv6-filter";
          } //src-entry

          leaf to {
            type string;
            description
                "[1..65535]|<name:64 char max>";
          } //to

          leaf dst-entry {
            type uint32 {
              range "1..2097151";
            }
            description
                "Attribute dst-entry-id for ipv6-filter";
          } //dst-entry

          leaf overwrite {
            type boolean;
          } //overwrite

        } //container ipv6-filter

        container mac-filter {
          description
              "Copy MAC filter and entry";
          leaf src-filter-id {
            type string;
            description
                "[1..65535]|<name:64 char max>";
          } //src-filter-id

          leaf src-entry {
            type uint32 {
              range "1..2097151";
            }
            description
                "Attribute src-entry-id for mac-filter";
          } //src-entry

          leaf to {
            type string;
            description
                "[1..65535]|<name:64 char max>";
          } //to

          leaf dst-entry {
            type uint32 {
              range "1..2097151";
            }
            description
                "Attribute dst-entry-id for mac-filter";
          } //dst-entry

          leaf overwrite {
            type boolean;
          } //overwrite

        } //container mac-filter

      } //container copy

      list dhcp-filter {
        key "filter-id";
        description
            "Configure a DHCP filter";
        leaf filter-id {
          type uint32 {
            range "1..65535";
          }
        } //filter-id

        container default-action {
          description
              "Default action for this dhcp-filter";
          leaf default-action-id {
            type enumeration {
              enum bypass-host-creation;
              enum drop;
            }
          } //default-action-id

        } //container default-action

        container description {
          description
              "Description for this dhcp-filter";
          leaf description-string {
            type string {
              length "1..80";
            }
          } //description-string

        } //container description

        list entry {
          key "entry-id";
          description
              "Configure dhcp-filter entry";
          leaf entry-id {
            type uint32 {
              range "1..65535";
            }
          } //entry-id

          container action {
            description
                "Configure action for this DHCP filter entry";
            leaf bypass-host-creation {
              type boolean;
            } //bypass-host-creation

            leaf drop {
              type boolean;
            } //drop

          } //container action

          container option {
            description
                "Configure match criteria for this DHCP filter entry";
            leaf dhcp-option-number {
              type int32 {
                range "0..255";
              }
            } //dhcp-option-number

            leaf option-id {
              type enumeration {
                enum present;
                enum absent;
              }
            } //option-id

            leaf match {
              type boolean;
            } //match

            leaf string {
              type string {
                length "1..127";
              }
            } //string

            leaf hex {
              type string {
              }
              description
                  "[0x0..0xFFFFFFFF...(max 254 hex nibbles)]";
            } //hex

            leaf exact {
              type boolean;
            } //exact

            leaf invert-match {
              type boolean;
            } //invert-match

          } //container option

        } //list entry

      } //list dhcp-filter

      list dhcp6-filter {
        key "filter-id";
        description
            "Configure a DHCP6 filter";
        leaf filter-id {
          type uint32 {
            range "1..65535";
          }
        } //filter-id

        container default-action {
          description
              "Default action for this dhcp6-filter";
          leaf bypass-host-creation {
            type boolean;
          } //bypass-host-creation

          leaf drop {
            type boolean;
          } //drop

          leaf na {
            type boolean;
          } //na

          leaf pd {
            type boolean;
          } //pd

        } //container default-action

        container description {
          description
              "Description for this dhcp6-filter";
          leaf description-string {
            type string {
              length "1..80";
            }
          } //description-string

        } //container description

        list entry {
          key "entry-id";
          description
              "Configure dhcp6-filter entry";
          leaf entry-id {
            type uint32 {
              range "1..65535";
            }
          } //entry-id

          container action {
            description
                "Configure action for this DHCP6 filter entry";
            leaf bypass-host-creation {
              type boolean;
            } //bypass-host-creation

            leaf drop {
              type boolean;
            } //drop

            leaf na {
              type boolean;
            } //na

            leaf pd {
              type boolean;
            } //pd

          } //container action

          container option {
            description
                "Configure match criteria for this DHCP6 filter entry";
            leaf dhcp6-option-number {
              type int32 {
                range "0..255";
              }
            } //dhcp6-option-number

            leaf option-id {
              type enumeration {
                enum present;
                enum absent;
              }
            } //option-id

            leaf match {
              type boolean;
            } //match

            leaf string {
              type string {
                length "1..127";
              }
            } //string

            leaf hex {
              type string {
              }
              description
                  "[0x0..0xFFFFFFFF...(max 254 hex nibbles)]";
            } //hex

            leaf exact {
              type boolean;
            } //exact

            leaf invert-match {
              type boolean;
            } //invert-match

          } //container option

        } //list entry

      } //list dhcp6-filter

      list gre-tunnel-template {
        key "name";
        description
            "Configure a gre-tunnel-template";
        leaf name {
          type string;
        } //name

        container description {
          description
              "Description for this gre-tunnel-template";
          leaf description-string {
            type string {
              length "1..80";
            }
          } //description-string

        } //container description

        container ipv4 {
          list destination-address {
            key "ip-address";
            description
                "Destination address";
            leaf ip-address {
              type inet:ip-address;
            } //ip-address

          } //list destination-address

          container gre-key {
            description
                "GRE key";
            leaf if-index {
              type boolean;
            } //if-index

          } //container gre-key

          leaf skip-ttl-decrement {
            type boolean;
            description
                "Decrement TTL";
          }

          container source-address {
            description
                "Source address";
            leaf ip-address {
              type inet:ip-address;
            } //ip-address

          } //container source-address

        } //container ipv4

      } //list gre-tunnel-template

      uses "conf-ip-except-r13:alu-conf-ip-except-r13";
      list ip-filter {
        key "filter-id";
        description
            "Configure an IP-filter";
        leaf filter-id {
          type string;
          description
              "Attribute filter-id for ip-filter";
        } //filter-id

        leaf name {
          type string;
          description
              "[64 chars max]";
        } //name

        leaf chain-to-system-filter {
          type boolean;
          description
              "Configure chaining to an active IP system filter";
        }

        container default-action {
          description
              "Configure default-action for the filter";
          leaf drop-forward {
            type enumeration {
              enum drop;
              enum forward;
            }
            description
                "keywords - specify filter action";
          } //drop-forward

        } //container default-action

        container description {
          description
              "Description for this ip-filter";
          leaf description-string {
            type string {
              length "1..80";
            }
          } //description-string

        } //container description

        container embed-filter {
          description
              "Embed a filter into this ip-filter";
          leaf ip-filter-id {
            type string;
            description
                "Attribute ip-filter-id for embed-filter";
          } //ip-filter-id

          leaf open-flow {
            type string;
          } //open-flow

          leaf system {
            type boolean;
          } //system

          leaf service {
            type string;
            description
                "Attribute service-id for embed-filter";
          } //service

          leaf sap {
            type string;
            description
                "Attribute sap-id for embed-filter";
          } //sap

          leaf offset {
            type uint32 {
              range "0..2097151";
            }
          } //offset

          leaf embed-filter-id {
            type enumeration {
              enum active;
              enum inactive;
            }
          } //embed-filter-id

          leaf flowspec {
            type boolean;
          } //flowspec

          leaf group {
            type uint32 {
              range "0..16383";
            }
          } //group

          leaf router {
            type boolean;
          } //router

          leaf router-instance {
            type string {
              length "1..32";
            }
            description
                "Attribute router-instance for embed-filter";
          } //router-instance

          leaf service-name {
            type string;
          } //service-name

          leaf vsd {
            type string;
            description
                "Attribute vsd-filter-id for embed-filter";
          } //vsd

        } //container embed-filter

        container filter-name {
          status "obsolete";
          description
              "Configure a name to the filter";
          leaf filter-name {
            type string;
          } //filter-name

        } //container filter-name

        container group-inserted-entries {
          description
              "group together the auto inserted entries";
          leaf application {
            type enumeration {
              enum radius;
              enum credit-control;
            }
          } //application

          leaf location {
            type enumeration {
              enum top;
              enum bottom;
            }
          } //location

        } //container group-inserted-entries

        container renum {
          description
              "Renumber an entry";
          leaf old-entry-id {
            type uint32 {
              range "1..2097151";
            }
            description
                "Attribute old-entry-id for renum";
          } //old-entry-id

          leaf new-entry-id {
            type uint32 {
              range "1..2097151";
            }
            description
                "Attribute new-entry-id for renum";
          } //new-entry-id

        } //container renum

        container scope {
          description
              "Configure scope for this filter";
          leaf scope-id {
            type enumeration {
              enum exclusive;
              enum template;
              enum embedded;
              enum system;
            }
          } //scope-id

        } //container scope

        container shared-radius-filter-wmark {
          description
              "Configure the low and high watermark for the number of radius shared filters 
               reporting";
          leaf low {
            type uint32 {
              range "0..7999";
            }
          } //low

          leaf high {
            type uint32 {
              range "1..8000";
            }
          } //high

        } //container shared-radius-filter-wmark

        container sub-insert-credit-control {
          description
              "Configure insert point info for credit control for the filter";
          leaf start-entry {
            type uint32 {
              range "1..2097151";
            }
          } //start-entry

          leaf count {
            type uint32 {
              range "1..65535";
            }
          } //count

        } //container sub-insert-credit-control

        container sub-insert-radius {
          description
              "Configure insert point for host-specific rules from RADIUS/Diameter";
          leaf start-entry {
            type uint32 {
              range "1..2097151";
            }
          } //start-entry

          leaf count {
            type uint32 {
              range "1..65535";
            }
          } //count

        } //container sub-insert-radius

        container sub-insert-shared-pccrule {
          description
              "Configure insert point for shared PCC-rules";
          leaf start-entry {
            type uint32 {
              range "1..2097151";
            }
          } //start-entry

          leaf count {
            type uint32 {
              range "1..65535";
            }
          } //count

        } //container sub-insert-shared-pccrule

        container sub-insert-shared-radius {
          description
              "Configure insert point for shared host rules from RADIUS/Diameter";
          leaf start-entry {
            type uint32 {
              range "1..2097151";
            }
          } //start-entry

          leaf count {
            type uint32 {
              range "1..65535";
            }
          } //count

        } //container sub-insert-shared-radius

        container sub-insert-wmark {
          description
              "Configure the low and high watermark percentage for inserted filter entry 
               usage reporting";
          leaf low {
            type uint32 {
              range "0..100";
            }
          } //low

          leaf high {
            type uint32 {
              range "0..100";
            }
          } //high

        } //container sub-insert-wmark

        container type {
          description
              "Configure the type of IP filter";
          leaf type-id {
            type enumeration {
              enum normal;
              enum src-mac;
              enum packet-length;
              enum destination-class;
            }
          } //type-id

        } //container type

        list entry {
          key "entry-id";
          description
              "Configure ip-filter entry";
          leaf entry-id {
            type uint32 {
              range "1..2097151";
            }
            description
                "Attribute entry-id for entry";
          } //entry-id

          leaf time-range {
            type string {
              length "1..32";
            }
            status "obsolete";
            description
                "[32-chars max]";
          } //time-range

          container description {
            description
                "Description for this filter entry";
            leaf description-string {
              type string {
                length "1..80";
              }
            } //description-string

          } //container description

          container egress-pbr {
            description
                "Enable egress PBR";
            leaf egress-pbr-id {
              type enumeration {
                enum default-load-balancing;
                enum l4-load-balancing;
              }
            } //egress-pbr-id

          } //container egress-pbr

          leaf filter-sample {
            type boolean;
            description
                "Enable/Disable Cflowd sampling";
          }

          leaf interface-disable-sample {
            type boolean;
            description
                "Disable/Enable Cflowd sampling on the interfaces";
          }

          container log {
            description
                "Configure log for the filter entry";
            leaf log-id {
              type uint16 {
                range "101..199";
              }
            } //log-id

          } //container log

          container pbr-down-action-override {
            description
                "Configure action that overrides default PBR/PBF down action. 'no 
                 pbr-down-action-override' preserves default PBR/PBF down action, which varies 
                 for different actions.";
            leaf filter-action {
              type enumeration {
                enum drop;
                enum forward;
                enum filter-default-action;
              }
            } //filter-action

          } //container pbr-down-action-override

          container sample-profile {
            description
                "Cflowd sample profile which will be used for packets matching this filter 
                 entry";
            leaf sample-profile-id {
              type uint32 {
                range "1..5";
              }
            } //sample-profile-id

          } //container sample-profile

          container sticky-dest {
            description
                "Set stickiness of PBR/PBF destinations and hold-time-up for stickiness to take 
                 effect";
            leaf hold-time-up {
              type uint32 {
                range "0..65535";
              }
              description
                  "0..65535 seconds";
            } //hold-time-up

            leaf no-hold-time-up {
              type boolean;
            } //no-hold-time-up

          } //container sticky-dest

          list action {
            key "secondary";
            description
                "Configure action for the filter entry";
            leaf secondary {
              type boolean;
            } //secondary

            container drop {
              description
                  "Set filter entry action to drop";
              leaf packet-length {
                type boolean;
              } //packet-length

              leaf ttl {
                type boolean;
              } //ttl

              leaf drop-id {
                type enumeration {
                  enum lt;
                  enum gt;
                  enum eq;
                }
              } //drop-id

              leaf packet-length-value {
                type uint32 {
                  range "0..65535";
                }
              } //packet-length-value

              leaf ttl-value {
                type uint32 {
                  range "0..255";
                }
              } //ttl-value

              leaf range {
                type boolean;
              } //range

              leaf-list drop-id-2 {
                type uint32 {
                  range "0..65535";
                }
                max-elements 2;
                description
                    "packet-length-value";
              } //drop-id-2

              leaf-list drop-id-3 {
                type uint32 {
                  range "0..255";
                }
                max-elements 2;
                description
                    "ttl-value";
              } //drop-id-3

              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container drop

            leaf drop-extracted-traffic {
              type boolean;
              description
                  "Drop packets extracted to CPM and matching the entry";
            }

            container fc {
              description
                  "Replace forwarding class for packets matching the entry";
              leaf fc-name {
                type enumeration {
                  enum be;
                  enum l2;
                  enum af;
                  enum l1;
                  enum h2;
                  enum ef;
                  enum h1;
                  enum nc;
                }
                description
                    "be|l2|af|l1|h2|ef|h1|nc - keywords";
              } //fc-name

            } //container fc

            container forward {
              description
                  "Set filter entry action to forward";
              leaf esi {
                type string;
                description
                    "Attribute esi for forward";
              } //esi

              leaf next-hop {
                type boolean;
              } //next-hop

              leaf ip-address {
                type inet:ip-address;
                description
                    "Attribute ip-address for forward";
              } //ip-address

              leaf indirect {
                type inet:ip-address;
                description
                    "ip-address";
              } //indirect

              leaf interface {
                type string {
                  length "1..32";
                }
                description
                    "egress interface name";
              } //interface

              leaf redirect-policy {
                type string {
                  length "1..32";
                }
                description
                    "redirect policy name";
              } //redirect-policy

              leaf sap {
                type string;
                description
                    "Attribute sap-id for forward";
              } //sap

              leaf sdp {
                type string;
                description
                    "sdp-id - [1..32767] 
                     vc-id - [1..4294967295]";
              } //sdp

              leaf service-id {
                type string;
                description
                    "Attribute vpls-service-id for forward";
              } //service-id

              leaf sf-ip {
                type inet:ip-address;
                description
                    "ip-address";
              } //sf-ip

              leaf vas-interface {
                type string {
                  length "1..32";
                }
              } //vas-interface

              leaf vprn-target {
                type boolean;
              } //vprn-target

              leaf bgp-nh {
                type inet:ip-address;
                description
                    "ip-address";
              } //bgp-nh

              leaf router {
                type boolean;
              } //router

              leaf router-instance {
                type string {
                  length "1..32";
                }
                default "Base";
                description
                    "Attribute router-instance for forward";
              } //router-instance

              leaf service-name {
                type string;
              } //service-name

              leaf adv-prefix {
                type inet:ip-prefix;
                description
                    "ip-address - a.b.c.d (host bits must be 0) 
                     mask - [0..32] 
                     ";
              } //adv-prefix

              leaf lsp {
                type string;
                description
                    "Attribute lsp-name for forward";
              } //lsp

              leaf bonding-connection {
                type uint32 {
                  range "1..2";
                }
                description
                    "[1,2]";
              } //bonding-connection

              leaf gre-tunnel {
                type string {
                  length "1..32";
                }
              } //gre-tunnel

              leaf mpls-policy {
                type inet:ip-address;
                description
                    "ip-address";
              } //mpls-policy

              leaf srte-policy {
                type inet:ip-address;
                description
                    "ip-address";
              } //srte-policy

              leaf color {
                type uint32;
              } //color

            } //container forward

            container forward-when {
              description
                  "Packets matching the entry and the forward-when condition will be forwarded";
              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container forward-when

            leaf gtp-local-breakout {
              type boolean;
              description
                  "Set filter entry action to gtp-local-breakout";
            }

            container http-redirect {
              description
                  "Set filter entry action to http-redirect";
              leaf rdr-url-string {
                type string {
                  length "1..255";
                }
                description
                    "Attribute rdr-url-string for http-redirect";
              } //rdr-url-string

              leaf allow-radius-override {
                type boolean;
              } //allow-radius-override

            } //container http-redirect

            leaf ignore-match {
              type boolean;
              description
                  "Entry is not active";
            }

            leaf l2-aware-nat-bypass {
              type boolean;
              description
                  "Bypass NAT for packets pertaining to L2Aware hosts and matching this entry";
            }

            container nat {
              description
                  "Set filter entry action to nat";
              leaf nat-policy {
                type string {
                  length "1..32";
                }
              } //nat-policy

            } //container nat

            container rate-limit {
              description
                  "Set rate limit for the traffic matching the entry";
              leaf value {
                type string;
                description
                    "[0..2000000000 | max] Kbps";
              } //value

              leaf packet-length {
                type boolean;
              } //packet-length

              leaf ttl {
                type boolean;
              } //ttl

              leaf rate-limit-id {
                type enumeration {
                  enum lt;
                  enum gt;
                  enum eq;
                }
              } //rate-limit-id

              leaf packet-length-value {
                type string;
                description
                    "[0..65535]";
              } //packet-length-value

              leaf ttl-value {
                type string;
                description
                    "[0..255]";
              } //ttl-value

              leaf range {
                type boolean;
              } //range

              leaf-list rate-limit-string-2 {
                type string;
                max-elements 2;
                description
                    "packet-length-value";
              } //rate-limit-string-2

              leaf-list rate-limit-string-3 {
                type string;
                max-elements 2;
                description
                    "ttl-value";
              } //rate-limit-string-3

              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container rate-limit

            leaf reassemble {
              type boolean;
              description
                  "Set filter entry action to reassemble";
            }

            container remark {
              description
                  "Activate dscp remarking for packets matching the entry";
              leaf dscp {
                type string {
                  length "1..32";
                }
                description
                    "Attribute dscp-name for remark";
              } //dscp

            } //container remark

            leaf tcp-mss-adjust {
              type boolean;
              description
                  "Activate adjustment of maximum segment size (MSS) option of TCP packets 
                   matching the entry";
            }

            container extended-action {
              presence
                  "Set action which will be taken along with PBR action";
              container remark {
                description
                    "Activate dscp remarking for packets matching the entry";
                leaf dscp {
                  type string {
                    length "1..32";
                  }
                  description
                      "Attribute dscp-name for remark";
                } //dscp

              } //container remark

            } //container extended-action

          } //list action

          container match {
            description
                "Configure match criteria for this ip filter entry";
            leaf protocol {
              type string;
              description
                  "Attribute protocol-id for match";
            } //protocol

            leaf protocol-list {
              type string {
                length "1..32";
              }
            } //protocol-list

            container destination-class {
              description
                  "Configure destination class match condition";
              leaf index {
                type uint32 {
                  range "1..255";
                }
              } //index

            } //container destination-class

            container dscp {
              description
                  "Configure DSCP match condition";
              leaf dscp-name {
                type string {
                  length "1..32";
                }
                description
                    "Attribute dscp-name for dscp";
              } //dscp-name

            } //container dscp

            container dst-ip {
              description
                  "Configure dest. ip match condition";
              leaf ip-address-mask {
                type inet:ip-prefix;
                description
                    "<ip-address>/<mask>";
              } //ip-address-mask

              leaf ip-address {
                type inet:ip-address;
                description
                    "Attribute ip-address for dst-ip";
              } //ip-address

              leaf ipv4-address-mask {
                type string;
                description
                    "a.b.c.d any address mask expressed as dotted quad [0..255]";
              } //ipv4-address-mask

              leaf ip-prefix-list {
                type string {
                  length "1..32";
                }
              } //ip-prefix-list

            } //container dst-ip

            container dst-port {
              description
                  "Configure destination port match condition";
              leaf dst-port-id {
                type enumeration {
                  enum lt;
                  enum gt;
                  enum eq;
                }
                description
                    "Attribute for dst-port";
              } //dst-port-id

              leaf dst-port-number {
                type string;
                description
                    "Attribute dst-port-number for dst-port";
              } //dst-port-number

              leaf-list range {
                type string;
                max-elements 2;
                description
                    "dst-port-number";
              } //range

              leaf port-list {
                type string {
                  length "1..32";
                }
              } //port-list

            } //container dst-port

            container fragment {
              description
                  "Configure fragmentation match condition";
              leaf fragment-id {
                type enumeration {
                  enum true;
                  enum false;
                  enum first-only;
                  enum non-first-only;
                }
                description
                    "Attribute for fragment";
              } //fragment-id

            } //container fragment

            container icmp-code {
              description
                  "Configure ICMP code match condition";
              leaf icmp-code {
                type string;
                description
                    "Attribute icmp-code for icmp-code";
              } //icmp-code

            } //container icmp-code

            container icmp-type {
              description
                  "Configure ICMP type match condition";
              leaf icmp-type {
                type string;
                description
                    "Attribute icmp-type for icmp-type";
              } //icmp-type

            } //container icmp-type

            container ip-option {
              description
                  "Configure ip-option match condition";
              leaf ip-option-value {
                type string;
                description
                    "[0..255] - accepted in decimal hex or binary";
              } //ip-option-value

              leaf ip-option-mask {
                type string;
                description
                    "[0..255] - accepted in decimal hex or binary";
              } //ip-option-mask

            } //container ip-option

            container multiple-option {
              description
                  "Configure multiple-option match condition";
              leaf true-false {
                type enumeration {
                  enum true;
                  enum false;
                }
                description
                    "keywords - sets/resets multiple-option check";
              } //true-false

            } //container multiple-option

            container option-present {
              description
                  "Configure option-present match condition";
              leaf true-false {
                type enumeration {
                  enum true;
                  enum false;
                }
                description
                    "keywords - sets/resets option-present check";
              } //true-false

            } //container option-present

            container packet-length {
              description
                  "Configure packet length match condition";
              leaf lt-gt-eq {
                type enumeration {
                  enum lt;
                  enum gt;
                  enum eq;
                }
              } //lt-gt-eq

              leaf range {
                type boolean;
              } //range

              leaf packet-length-value {
                type uint32 {
                  range "0..65535";
                }
              } //packet-length-value

              leaf packet-length-id {
                type uint32 {
                  range "0..65535";
                }
                description
                    "packet-length-value";
              } //packet-length-id

            } //container packet-length

            container port {
              description
                  "Configure port match condition";
              leaf lt-gt-eq {
                type enumeration {
                  enum lt;
                  enum gt;
                  enum eq;
                }
                description
                    "operators";
              } //lt-gt-eq

              leaf port-number {
                type string;
                description
                    "Attribute port-number for port";
              } //port-number

              leaf-list range {
                type string;
                max-elements 2;
                description
                    "port-number";
              } //range

              leaf port-list {
                type string {
                  length "1..32";
                }
              } //port-list

            } //container port

            container src-ip {
              description
                  "Configure source ip match condition";
              leaf ip-address-mask {
                type inet:ip-prefix;
                description
                    "<ip-address>/<mask>";
              } //ip-address-mask

              leaf ip-address {
                type inet:ip-address;
                description
                    "Attribute ip-address for src-ip";
              } //ip-address

              leaf ipv4-address-mask {
                type string;
                description
                    "a.b.c.d any address mask expressed as dotted quad [0..255]";
              } //ipv4-address-mask

              leaf ip-prefix-list {
                type string {
                  length "1..32";
                }
              } //ip-prefix-list

            } //container src-ip

            container src-mac {
              description
                  "Configure source MAC match condition";
              leaf ieee-address {
                type alu:ieee-address;
                description
                    "xx:xx:xx:xx:xx:xx or xx-xx-xx-xx-xx-xx";
              } //ieee-address

              leaf ieee-address-mask {
                type string;
                description
                    "xx:xx:xx:xx:xx:xx or xx-xx-xx-xx-xx-xx";
              } //ieee-address-mask

            } //container src-mac

            container src-port {
              description
                  "Configure source port match condition";
              leaf src-port-id {
                type enumeration {
                  enum lt;
                  enum gt;
                  enum eq;
                }
                description
                    "Attribute for src-port";
              } //src-port-id

              leaf src-port-number {
                type string;
                description
                    "Attribute src-port-number for src-port";
              } //src-port-number

              leaf-list range {
                type string;
                max-elements 2;
                description
                    "src-port-number";
              } //range

              leaf port-list {
                type string {
                  length "1..32";
                }
              } //port-list

            } //container src-port

            container src-route-option {
              description
                  "Configure source route option match condition";
              leaf true-false {
                type enumeration {
                  enum true;
                  enum false;
                }
                description
                    "keywords - sets/resets source route option check";
              } //true-false

            } //container src-route-option

            container tcp-ack {
              description
                  "Configure TCP ACK match condition";
              leaf true-false {
                type enumeration {
                  enum true;
                  enum false;
                }
                description
                    "keywords - sets/resets TCP ACK check";
              } //true-false

            } //container tcp-ack

            container tcp-cwr {
              description
                  "Configure TCP CWR match condition";
              leaf true-false {
                type enumeration {
                  enum true;
                  enum false;
                }
              } //true-false

            } //container tcp-cwr

            container tcp-ece {
              description
                  "Configure TCP ECE match condition";
              leaf true-false {
                type enumeration {
                  enum true;
                  enum false;
                }
              } //true-false

            } //container tcp-ece

            container tcp-fin {
              description
                  "Configure TCP FIN match condition";
              leaf true-false {
                type enumeration {
                  enum true;
                  enum false;
                }
              } //true-false

            } //container tcp-fin

            container tcp-ns {
              description
                  "Configure TCP NS match condition";
              leaf true-false {
                type enumeration {
                  enum true;
                  enum false;
                }
              } //true-false

            } //container tcp-ns

            container tcp-psh {
              description
                  "Configure TCP PSH match condition";
              leaf true-false {
                type enumeration {
                  enum true;
                  enum false;
                }
              } //true-false

            } //container tcp-psh

            container tcp-rst {
              description
                  "Configure TCP RST match condition";
              leaf true-false {
                type enumeration {
                  enum true;
                  enum false;
                }
              } //true-false

            } //container tcp-rst

            container tcp-syn {
              description
                  "Configure TCP SYN match condition";
              leaf true-false {
                type enumeration {
                  enum true;
                  enum false;
                }
                description
                    "keywords - sets/resets TCP SYN check";
              } //true-false

            } //container tcp-syn

            container tcp-urg {
              description
                  "Configure TCP URG match condition";
              leaf true-false {
                type enumeration {
                  enum true;
                  enum false;
                }
              } //true-false

            } //container tcp-urg

          } //container match

        } //list entry

      } //list ip-filter

      uses "conf-ipv6-except-r13:alu-conf-ipv6-except-r13";
      list ipv6-filter {
        key "filter-id";
        description
            "Configure an IPv6-filter";
        leaf filter-id {
          type string;
          description
              "Attribute filter-id for ipv6-filter";
        } //filter-id

        leaf name {
          type string;
          description
              "[64 chars max]";
        } //name

        leaf chain-to-system-filter {
          type boolean;
          description
              "Configure chaining to an active IPv6 system filter";
        }

        container default-action {
          description
              "Configure default-action for the IPv6-filter";
          leaf drop-forward {
            type enumeration {
              enum drop;
              enum forward;
            }
            description
                "keywords - specify filter action";
          } //drop-forward

        } //container default-action

        container description {
          description
              "Description for the IPv6-filter";
          leaf description-string {
            type string {
              length "1..80";
            }
          } //description-string

        } //container description

        container embed-filter {
          description
              "Embed a filter into this IPv6-filter";
          leaf ipv6-filter-id {
            type string;
            description
                "Attribute ipv6-filter-id for embed-filter";
          } //ipv6-filter-id

          leaf open-flow {
            type string;
          } //open-flow

          leaf system {
            type boolean;
          } //system

          leaf service {
            type string;
            description
                "Attribute service-id for embed-filter";
          } //service

          leaf sap {
            type string;
            description
                "Attribute sap-id for embed-filter";
          } //sap

          leaf offset {
            type uint32 {
              range "0..2097151";
            }
          } //offset

          leaf embed-filter-id {
            type enumeration {
              enum active;
              enum inactive;
            }
          } //embed-filter-id

          leaf flowspec {
            type boolean;
          } //flowspec

          leaf group {
            type uint32 {
              range "0..16383";
            }
          } //group

          leaf router {
            type boolean;
          } //router

          leaf router-instance {
            type string {
              length "1..32";
            }
            description
                "Attribute router-instance for embed-filter";
          } //router-instance

          leaf service-name {
            type string;
          } //service-name

          leaf vsd {
            type string;
            description
                "Attribute vsd-filter-id for embed-filter";
          } //vsd

        } //container embed-filter

        container filter-name {
          status "obsolete";
          description
              "Configure a name to the filter";
          leaf filter-name {
            type string;
          } //filter-name

        } //container filter-name

        container group-inserted-entries {
          description
              "group together the auto inserted entries";
          leaf application {
            type enumeration {
              enum radius;
              enum credit-control;
            }
          } //application

          leaf location {
            type enumeration {
              enum top;
              enum bottom;
            }
          } //location

        } //container group-inserted-entries

        container renum {
          description
              "Renumber an IPv6-filter entry";
          leaf old-entry-id {
            type uint32 {
              range "1..2097151";
            }
            description
                "Attribute old-entry-id for renum";
          } //old-entry-id

          leaf new-entry-id {
            type uint32 {
              range "1..2097151";
            }
            description
                "Attribute new-entry-id for renum";
          } //new-entry-id

        } //container renum

        container scope {
          description
              "Configure scope for this IPv6-filter";
          leaf scope-id {
            type enumeration {
              enum exclusive;
              enum template;
              enum embedded;
              enum system;
            }
          } //scope-id

        } //container scope

        container shared-radius-filter-wmark {
          description
              "Configure the low and high watermark for the number of radius shared filters 
               reporting";
          leaf low {
            type uint32 {
              range "0..7999";
            }
          } //low

          leaf high {
            type uint32 {
              range "1..8000";
            }
          } //high

        } //container shared-radius-filter-wmark

        container sub-insert-credit-control {
          description
              "Configure insert point info for credit control for the filter";
          leaf start-entry {
            type uint32 {
              range "1..2097151";
            }
          } //start-entry

          leaf count {
            type uint32 {
              range "1..65535";
            }
          } //count

        } //container sub-insert-credit-control

        container sub-insert-radius {
          description
              "Configure insert point for host-specific rules from RADIUS/Diameter";
          leaf start-entry {
            type uint32 {
              range "1..2097151";
            }
          } //start-entry

          leaf count {
            type uint32 {
              range "1..65535";
            }
          } //count

        } //container sub-insert-radius

        container sub-insert-shared-pccrule {
          description
              "Configure insert point for shared PCC-rules";
          leaf start-entry {
            type uint32 {
              range "1..2097151";
            }
          } //start-entry

          leaf count {
            type uint32 {
              range "1..65535";
            }
          } //count

        } //container sub-insert-shared-pccrule

        container sub-insert-shared-radius {
          description
              "Configure insert point for shared host rules from RADIUS/Diameter";
          leaf start-entry {
            type uint32 {
              range "1..2097151";
            }
          } //start-entry

          leaf count {
            type uint32 {
              range "1..65535";
            }
          } //count

        } //container sub-insert-shared-radius

        container sub-insert-wmark {
          description
              "Configure the low and high watermark percentage for inserted filter entry 
               usage reporting";
          leaf low {
            type uint32 {
              range "0..100";
            }
          } //low

          leaf high {
            type uint32 {
              range "0..100";
            }
          } //high

        } //container sub-insert-wmark

        container type {
          description
              "Configure the type of IPv6 filter";
          leaf type-id {
            type enumeration {
              enum normal;
              enum src-mac;
              enum packet-length;
              enum destination-class;
            }
          } //type-id

        } //container type

        list entry {
          key "entry-id";
          description
              "Configure an IPv6-filter entry";
          leaf entry-id {
            type uint32 {
              range "1..2097151";
            }
            description
                "Attribute entry-id for entry";
          } //entry-id

          leaf time-range {
            type string {
              length "1..32";
            }
            status "obsolete";
          } //time-range

          container description {
            description
                "Description for this IPv6-filter entry";
            leaf description-string {
              type string {
                length "1..80";
              }
            } //description-string

          } //container description

          container egress-pbr {
            description
                "Enable egress PBR";
            leaf egress-pbr-id {
              type enumeration {
                enum default-load-balancing;
                enum l4-load-balancing;
              }
            } //egress-pbr-id

          } //container egress-pbr

          leaf filter-sample {
            type boolean;
            description
                "Enable/Disable Cflowd sampling";
          }

          leaf interface-disable-sample {
            type boolean;
            description
                "Disable/Enable Cflowd sampling on the interfaces";
          }

          container log {
            description
                "Configure log for the IPv6-filter entry";
            leaf log-id {
              type uint16 {
                range "101..199";
              }
            } //log-id

          } //container log

          container pbr-down-action-override {
            description
                "Configure action that overrides default PBR/PBF down action. 'no 
                 pbr-down-action-override' preserves default PBR/PBF down action, which varies 
                 for different actions.";
            leaf filter-action {
              type enumeration {
                enum drop;
                enum forward;
                enum filter-default-action;
              }
            } //filter-action

          } //container pbr-down-action-override

          container sample-profile {
            description
                "Cflowd sample profile which will be used for packets matching this filter 
                 entry";
            leaf sample-profile-id {
              type uint32 {
                range "1..5";
              }
            } //sample-profile-id

          } //container sample-profile

          container sticky-dest {
            description
                "Set stickiness of PBR/PBF destinations and hold-time-up for stickiness to take 
                 effect";
            leaf hold-time-up {
              type uint32 {
                range "0..65535";
              }
              description
                  "0..65535 seconds";
            } //hold-time-up

            leaf no-hold-time-up {
              type boolean;
            } //no-hold-time-up

          } //container sticky-dest

          list action {
            key "secondary";
            description
                "Configure action for the IPv6-filter entry";
            leaf secondary {
              type boolean;
            } //secondary

            container drop {
              description
                  "Set ipv6-filter action to drop";
              leaf packet-length {
                type boolean;
                status "obsolete";
              } //packet-length

              leaf hop-limit {
                type boolean;
              } //hop-limit

              leaf payload-length {
                type boolean;
              } //payload-length

              leaf drop-id {
                type enumeration {
                  enum lt;
                  enum gt;
                  enum eq;
                }
              } //drop-id

              leaf payload-length-value {
                type uint32 {
                  range "0..65535";
                }
              } //payload-length-value

              leaf hop-limit-value {
                type uint32 {
                  range "0..255";
                }
              } //hop-limit-value

              leaf range {
                type boolean;
              } //range

              leaf-list drop-id-2 {
                type uint32 {
                  range "0..65535";
                }
                max-elements 2;
                description
                    "payload-length-value";
              } //drop-id-2

              leaf-list drop-id-3 {
                type uint32 {
                  range "0..255";
                }
                max-elements 2;
                description
                    "hop-limit-value";
              } //drop-id-3

              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container drop

            leaf drop-extracted-traffic {
              type boolean;
              description
                  "Drop packets extracted to CPM and matching the entry";
            }

            container fc {
              description
                  "Replace forwarding class for packets matching the entry";
              leaf fc-name {
                type enumeration {
                  enum be;
                  enum l2;
                  enum af;
                  enum l1;
                  enum h2;
                  enum ef;
                  enum h1;
                  enum nc;
                }
                description
                    "be|l2|af|l1|h2|ef|h1|nc - keywords";
              } //fc-name

            } //container fc

            container forward {
              description
                  "Set ipv6-filter action to forward";
              leaf esi {
                type string;
                description
                    "Attribute esi for forward";
              } //esi

              leaf next-hop {
                type boolean;
              } //next-hop

              leaf ipv6-address {
                type inet:ipv6-address;
                description
                    "Attribute ipv6-address for forward";
              } //ipv6-address

              leaf indirect {
                type inet:ipv6-address;
                description
                    "ipv6-address";
              } //indirect

              leaf redirect-policy {
                type string {
                  length "1..32";
                }
                description
                    "redirect policy name";
              } //redirect-policy

              leaf sap {
                type string;
                description
                    "Attribute sap-id for forward";
              } //sap

              leaf sdp {
                type string;
                description
                    "sdp-id - [1..32767] 
                     vc-id - [1..4294967295]";
              } //sdp

              leaf service-id {
                type string;
                description
                    "Attribute vpls-service-id for forward";
              } //service-id

              leaf sf-ip {
                type inet:ipv6-address;
                description
                    "ipv6-address";
              } //sf-ip

              leaf vas-interface {
                type string {
                  length "1..32";
                }
              } //vas-interface

              leaf vprn-target {
                type boolean;
              } //vprn-target

              leaf bgp-nh {
                type inet:ip-address;
                description
                    "Attribute ip-address for forward";
              } //bgp-nh

              leaf router {
                type boolean;
              } //router

              leaf router-instance {
                type string {
                  length "1..32";
                }
                default "Base";
                description
                    "Attribute router-instance for forward";
              } //router-instance

              leaf service-name {
                type string;
              } //service-name

              leaf adv-prefix {
                type string;
                description
                    "ipv6-address x:x:x:x:x:x:x:x (eight 16-bit pieces) 
                     x:x:x:x:x:x:d.d.d.d 
                     x [0..FFFF]H 
                     d [0..255]D 
                     prefix-length [0..128]";
              } //adv-prefix

              leaf lsp {
                type string;
                description
                    "Attribute lsp-name for forward";
              } //lsp

              leaf bonding-connection {
                type uint32 {
                  range "1..2";
                }
                description
                    "[1,2]";
              } //bonding-connection

              leaf gre-tunnel {
                type string {
                  length "1..32";
                }
              } //gre-tunnel

              leaf mpls-policy {
                type inet:ipv6-address;
                description
                    "ipv6-address";
              } //mpls-policy

              leaf srte-policy {
                type inet:ipv6-address;
                description
                    "ipv6-address";
              } //srte-policy

              leaf color {
                type uint32;
              } //color

            } //container forward

            container forward-when {
              description
                  "Packets matching the entry and the forward-when condition will be forwarded";
              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container forward-when

            container http-redirect {
              description
                  "Set ipv6-filter action to http-redirect";
              leaf rdr-url-string {
                type string {
                  length "1..255";
                }
                description
                    "Attribute rdr-url-string for http-redirect";
              } //rdr-url-string

              leaf allow-radius-override {
                type boolean;
              } //allow-radius-override

            } //container http-redirect

            leaf ignore-match {
              type boolean;
              description
                  "Entry is not active";
            }

            container nat {
              description
                  "Set ipv6-filter action to nat";
              leaf nat-policy-name {
                type string {
                  length "1..32";
                }
                status "obsolete";
              } //nat-policy-name

              leaf nat-type {
                type enumeration {
                  enum dslite;
                  enum nat64;
                }
              } //nat-type

              leaf nat-policy {
                type string {
                  length "1..32";
                }
              } //nat-policy

            } //container nat

            container rate-limit {
              description
                  "Set rate limit for the traffic matching the entry";
              leaf value {
                type string;
                description
                    "[0..2000000000 | max] Kbps";
              } //value

              leaf payload-length {
                type boolean;
              } //payload-length

              leaf hop-limit {
                type boolean;
              } //hop-limit

              leaf rate-limit-id {
                type enumeration {
                  enum lt;
                  enum gt;
                  enum eq;
                }
              } //rate-limit-id

              leaf payload-length-value {
                type string;
                description
                    "[0..65535]";
              } //payload-length-value

              leaf hop-limit-value {
                type string;
                description
                    "[0..255]";
              } //hop-limit-value

              leaf range {
                type boolean;
              } //range

              leaf-list rate-limit-string-2 {
                type string;
                max-elements 2;
                description
                    "payload-length-value";
              } //rate-limit-string-2

              leaf-list rate-limit-string-3 {
                type string;
                max-elements 2;
                description
                    "hop-limit-value";
              } //rate-limit-string-3

              leaf pattern {
                type boolean;
              } //pattern

              leaf expression {
                type string;
                description
                    "[0x0000000000000000 - 0xffffffffffffffff]";
              } //expression

              leaf mask {
                type string;
                description
                    "hex-string";
              } //mask

              leaf offset-type {
                type enumeration {
                  enum layer-3;
                  enum layer-4;
                  enum data;
                  enum dns-qtype;
                }
              } //offset-type

              leaf offset-value {
                type int32 {
                  range "0..255";
                }
              } //offset-value

            } //container rate-limit

            container remark {
              description
                  "Activate dscp remarking for packets matching the entry";
              leaf dscp {
                type string {
                  length "1..32";
                }
                description
                    "Attribute dscp-name for remark";
              } //dscp

            } //container remark

            leaf tcp-mss-adjust {
              type boolean;
              description
                  "Activate adjustment of maximum segment size (MSS) option of TCP packets 
                   matching the entry";
            }

            container extended-action {
              presence
                  "Set action which will be taken along with PBR action";
              container remark {
                description
                    "Activate dscp remarking for packets matching the entry";
                leaf dscp {
                  type string {
                    length "1..32";
                  }
                  description
                      "Attribute dscp-name for remark";
                } //dscp

              } //container remark

            } //container extended-action

          } //list action

          container match {
            description
                "Configure match criteria for this IPv6-filter entry";
            leaf next-header {
              type string;
              description
                  "Attribute next-header for match";
            } //next-header

            leaf next-header-list {
              type string {
                length "1..32";
              }
            } //next-header-list

            container ah-ext-hdr {
              description
                  "Configure the Authentication Header ext header match condition";
              leaf true-false {
                type enumeration {
                  enum true;
                  enum false;
                }
                description
                    "keywords - sets/resets Authentication Header check";
              } //true-false

            } //container ah-ext-hdr

            container destination-class {
              description
                  "Configure destination class match condition";
              leaf index {
                type uint32 {
                  range "1..255";
                }
              } //index

            } //container destination-class

            container dscp {
              description
                  "Configure DSCP match condition";
              leaf dscp-name {
                type string {
                  length "1..32";
                }
                description
                    "Attribute dscp-name for dscp";
              } //dscp-name

            } //container dscp

            container dst-ip {
              description
                  "Configure dest. IPv6 address match condition";
              leaf ipv6-address-prefix-length {
                type string;
                description
                    "<ipv6-address>/<prefix-length>";
              } //ipv6-address-prefix-length

              leaf ipv6-address {
                type inet:ipv6-address;
                description
                    "Attribute ipv6-address for dst-ip";
              } //ipv6-address

              leaf ipv6-address-mask {
                type inet:ipv6-address;
                description
                    "Attribute ipv6-address-mask for dst-ip";
              } //ipv6-address-mask

              leaf ipv6-prefix-list {
                type string {
                  length "1..32";
                }
              } //ipv6-prefix-list

            } //container dst-ip

            container dst-port {
              description
                  "Configure destination port match condition";
              leaf dst-port-id {
                type enumeration {
                  enum lt;
                  enum gt;
                  enum eq;
                }
                description
                    "Attribute for dst-port";
              } //dst-port-id

              leaf dst-port-number {
                type string;
                description
                    "Attribute dst-port-number for dst-port";
              } //dst-port-number

              leaf-list range {
                type string;
                max-elements 2;
                description
                    "dst-port-number";
              } //range

              leaf port-list {
                type string {
                  length "1..32";
                }
              } //port-list

            } //container dst-port

            container esp-ext-hdr {
              description
                  "Configure the Encapsulating Security Payload ext header match condition";
              leaf true-false {
                type enumeration {
                  enum true;
                  enum false;
                }
                description
                    "keywords - sets/resets Encapsulating Security Payload check";
              } //true-false

            } //container esp-ext-hdr

            container flow-label {
              description
                  "Configure flow-label and optional mask match condition";
              leaf flow-label {
                type string;
                description
                    "[0..1048575]D 
                     [0x0..0xFFFFF]H 
                     [0b0..0b11111111111111111111]B 
                     ";
              } //flow-label

              leaf mask {
                type string;
                description
                    "[0..1048575]D 
                     [0x0..0xFFFFF]H 
                     [0b0..0b11111111111111111111]B 
                     ";
              } //mask

            } //container flow-label

            container fragment {
              description
                  "Configure fragmentation match condition";
              leaf fragment-id {
                type enumeration {
                  enum true;
                  enum false;
                  enum first-only;
                  enum non-first-only;
                }
                description
                    "Attribute for fragment";
              } //fragment-id

            } //container fragment

            container hop-by-hop-opt {
              description
                  "Configure hop-by-hop options ext header match condition";
              leaf true-false {
                type enumeration {
                  enum true;
                  enum false;
                }
                description
                    "keywords - sets/resets hop-by-hop options check";
              } //true-false

            } //container hop-by-hop-opt

            container icmp-code {
              description
                  "Configure ICMP code match condition";
              leaf icmp-code {
                type string;
                description
                    "Attribute icmp-code for icmp-code";
              } //icmp-code

            } //container icmp-code

            container icmp-type {
              description
                  "Configure ICMP type match condition";
              leaf icmp-type {
                type string;
                description
                    "Attribute icmp-type for icmp-type";
              } //icmp-type

            } //container icmp-type

            container packet-length {
              description
                  "Configure payload length match condition";
              leaf lt-gt-eq {
                type enumeration {
                  enum lt;
                  enum gt;
                  enum eq;
                }
              } //lt-gt-eq

              leaf range {
                type boolean;
              } //range

              leaf packet-length-value {
                type uint32 {
                  range "40..65575";
                }
              } //packet-length-value

              leaf packet-length-id {
                type uint32 {
                  range "40..65575";
                }
                description
                    "packet-length-value";
              } //packet-length-id

            } //container packet-length

            container port {
              description
                  "Configure port match condition";
              leaf lt-gt-eq {
                type enumeration {
                  enum lt;
                  enum gt;
                  enum eq;
                }
                description
                    "operator";
              } //lt-gt-eq

              leaf port-number {
                type string;
                description
                    "Attribute port-number for port";
              } //port-number

              leaf-list range {
                type string;
                max-elements 2;
                description
                    "port-number";
              } //range

              leaf port-list {
                type string {
                  length "1..32";
                }
              } //port-list

            } //container port

            container routing-type0 {
              description
                  "Configure type 0 routing ext header match condition";
              leaf true-false {
                type enumeration {
                  enum true;
                  enum false;
                }
                description
                    "keywords - sets/resets routing-type0 check";
              } //true-false

            } //container routing-type0

            container src-ip {
              description
                  "Configure source IPv6 address match condition";
              leaf ipv6-address-prefix-length {
                type string;
                description
                    "<ipv6-address>/<prefix-length>";
              } //ipv6-address-prefix-length

              leaf ipv6-address {
                type inet:ipv6-address;
                description
                    "Attribute ipv6-address for src-ip";
              } //ipv6-address

              leaf ipv6-address-mask {
                type inet:ipv6-address;
                description
                    "Attribute ipv6-address-mask for src-ip";
              } //ipv6-address-mask

              leaf ipv6-prefix-list {
                type string {
                  length "1..32";
                }
              } //ipv6-prefix-list

            } //container src-ip

            container src-mac {
              description
                  "Configure source MAC match condition";
              leaf ieee-address {
                type alu:ieee-address;
                description
                    "xx:xx:xx:xx:xx:xx or xx-xx-xx-xx-xx-xx";
              } //ieee-address

              leaf ieee-address-mask {
                type string;
                description
                    "xx:xx:xx:xx:xx:xx or xx-xx-xx-xx-xx-xx";
              } //ieee-address-mask

            } //container src-mac

            container src-port {
              description
                  "Configure source port match condition";
              leaf src-port-id {
                type enumeration {
                  enum lt;
                  enum gt;
                  enum eq;
                }
                description
                    "Attribute for src-port";
              } //src-port-id

              leaf src-port-number {
                type string;
                description
                    "Attribute src-port-number for src-port";
              } //src-port-number

              leaf-list range {
                type string;
                max-elements 2;
                description
                    "src-port-number";
              } //range

              leaf port-list {
                type string {
                  length "1..32";
                }
              } //port-list

            } //container src-port

            container tcp-ack {
              description
                  "Configure TCP ACK match condition";
              leaf true-false {
                type enumeration {
                  enum true;
                  enum false;
                }
                description
                    "keywords - sets/resets TCP ACK check";
              } //true-false

            } //container tcp-ack

            container tcp-cwr {
              description
                  "Configure TCP CWR match condition";
              leaf true-false {
                type enumeration {
                  enum true;
                  enum false;
                }
              } //true-false

            } //container tcp-cwr

            container tcp-ece {
              description
                  "Configure TCP ECE match condition";
              leaf true-false {
                type enumeration {
                  enum true;
                  enum false;
                }
              } //true-false

            } //container tcp-ece

            container tcp-fin {
              description
                  "Configure TCP FIN match condition";
              leaf true-false {
                type enumeration {
                  enum true;
                  enum false;
                }
              } //true-false

            } //container tcp-fin

            container tcp-ns {
              description
                  "Configure TCP NS match condition";
              leaf true-false {
                type enumeration {
                  enum true;
                  enum false;
                }
              } //true-false

            } //container tcp-ns

            container tcp-psh {
              description
                  "Configure TCP PSH match condition";
              leaf true-false {
                type enumeration {
                  enum true;
                  enum false;
                }
              } //true-false

            } //container tcp-psh

            container tcp-rst {
              description
                  "Configure TCP RST match condition";
              leaf true-false {
                type enumeration {
                  enum true;
                  enum false;
                }
              } //true-false

            } //container tcp-rst

            container tcp-syn {
              description
                  "Configure TCP SYN match condition";
              leaf true-false {
                type enumeration {
                  enum true;
                  enum false;
                }
                description
                    "keywords - sets/resets TCP SYN check";
              } //true-false

            } //container tcp-syn

            container tcp-urg {
              description
                  "Configure TCP URG match condition";
              leaf true-false {
                type enumeration {
                  enum true;
                  enum false;
                }
              } //true-false

            } //container tcp-urg

          } //container match

        } //list entry

      } //list ipv6-filter

      list log {
        key "log-id";
        description
            "Configure a filter-log";
        leaf log-id {
          type uint16 {
            range "101..199";
          }
        } //log-id

        container description {
          description
              "Description for this filter-log";
          leaf description-string {
            type string {
              length "1..80";
            }
          } //description-string

        } //container description

        container destination {
          description
              "Destination for this filter-log";
          leaf memory {
            type uint32 {
              range "1..50000";
            }
          } //memory

          leaf syslog {
            type uint16 {
              range "1..10";
            }
          } //syslog

        } //container destination

        leaf shutdown {
          type boolean;
          description
              "Administratively enable/disable the log";
        }

        leaf wrap-around {
          type boolean;
          description
              "Enable wrap-arounds";
        }

        container summary {
          description
              "Configure log summarization";
          leaf shutdown {
            type boolean;
            description
                "Administratively enable/disable the summarization";
          }

          container summary-crit {
            description
                "Define the summarization criterion";
            leaf src-addr {
              type boolean;
            } //src-addr

            leaf dst-addr {
              type boolean;
            } //dst-addr

          } //container summary-crit

        } //container summary

      } //list log

      list mac-filter {
        key "filter-id";
        description
            "Configure a mac-filter";
        leaf filter-id {
          type string;
          description
              "Attribute filter-id for mac-filter";
        } //filter-id

        leaf name {
          type string;
          description
              "[64 chars max]";
        } //name

        container default-action {
          description
              "Configure default-action for the filter";
          leaf drop-forward {
            type enumeration {
              enum drop;
              enum forward;
            }
            description
                "keywords - specify filter action";
          } //drop-forward

        } //container default-action

        container description {
          description
              "Description for this mac-filter";
          leaf description-string {
            type string {
              length "1..80";
            }
          } //description-string

        } //container description

        list embed-filter {
          key "vsd";
          description
              "Embed a filter into this mac-filter";
          leaf vsd {
            type string;
            description
                "Attribute vsd-filter-id for embed-filter";
          } //vsd

          leaf offset {
            type uint32 {
              range "0..2097151";
            }
          } //offset

          leaf embed-filter-id {
            type enumeration {
              enum active;
              enum inactive;
            }
          } //embed-filter-id

        } //list embed-filter

        container filter-name {
          status "obsolete";
          description
              "Configure a name to the filter";
          leaf filter-name {
            type string;
          } //filter-name

        } //container filter-name

        container renum {
          description
              "Renumber an entry";
          leaf old-entry-id {
            type uint32 {
              range "1..2097151";
            }
            description
                "Attribute old-entry-id for renum";
          } //old-entry-id

          leaf new-entry-id {
            type uint32 {
              range "1..2097151";
            }
            description
                "Attribute new-entry-id for renum";
          } //new-entry-id

        } //container renum

        container scope {
          description
              "Configure scope for this filter";
          leaf exclusive-template {
            type enumeration {
              enum exclusive;
              enum template;
            }
            description
                "keywords - specify type of policy";
          } //exclusive-template

        } //container scope

        container type {
          description
              "Set the mac-filter type";
          leaf filter-type {
            type enumeration {
              enum normal;
              enum isid;
              enum vid;
            }
          } //filter-type

        } //container type

        list entry {
          key "entry-id";
          description
              "Configure mac-filter entry";
          leaf entry-id {
            type uint32 {
              range "1..2097151";
            }
            description
                "Attribute entry-id for entry";
          } //entry-id

          leaf time-range {
            type string {
              length "1..32";
            }
            status "obsolete";
          } //time-range

          container description {
            description
                "Description for this filter entry";
            leaf description-string {
              type string {
                length "1..80";
              }
            } //description-string

          } //container description

          container log {
            description
                "Configure log for the filter entry";
            leaf log-id {
              type uint16 {
                range "101..199";
              }
            } //log-id

          } //container log

          container pbr-down-action-override {
            description
                "Configure action that overrides default PBR/PBF down action. 'no 
                 pbr-down-action-override' preserves default PBR/PBF down action, which varies 
                 for different actions.";
            leaf filter-action {
              type enumeration {
                enum drop;
                enum forward;
                enum filter-default-action;
              }
            } //filter-action

          } //container pbr-down-action-override

          container sticky-dest {
            description
                "Set stickiness of PBF destinations and hold-time-up for stickiness to take 
                 effect";
            leaf hold-time-up {
              type uint32 {
                range "0..65535";
              }
              description
                  "0..65535 seconds";
            } //hold-time-up

            leaf no-hold-time-up {
              type boolean;
            } //no-hold-time-up

          } //container sticky-dest

          list action {
            key "secondary";
            description
                "Configure action for the filter entry";
            leaf secondary {
              type boolean;
            } //secondary

            leaf drop {
              type boolean;
              description
                  "Set mac-filter action to drop";
            }

            container forward {
              description
                  "Set mac-filter action to forward";
              leaf sap {
                type string;
                description
                    "Attribute sap-id for forward";
              } //sap

              leaf sdp {
                type string;
                description
                    "sdp-id - [1..32767] 
                     vc-id - [1..4294967295]";
              } //sdp

              leaf esi {
                type string;
                description
                    "Attribute esi for forward";
              } //esi

              leaf service-id {
                type string {
                }
                description
                    "Attribute vpls-service-id for forward";
              } //service-id

            } //container forward

            container http-redirect {
              description
                  "Set mac-filter action to http-redirect";
              leaf url {
                type string {
                  length "1..255";
                }
              } //url

            } //container http-redirect

            leaf ignore-match {
              type boolean;
              description
                  "Entry is not active";
            }

            container rate-limit {
              description
                  "Set rate limit for the traffic matching the entry";
              leaf value {
                type string;
                description
                    "[0..2000000000 | max] Kbps";
              } //value

            } //container rate-limit

          } //list action

          container match {
            description
                "Configure match criteria for this mac filter entry";
            leaf frame-type {
              type enumeration {
                enum 802dot3;
                enum 802dot2-llc;
                enum 802dot2-snap;
                enum ethernet_II;
              }
            } //frame-type

            container dot1p {
              description
                  "Configure Dot1p match condition";
              leaf dot1p-value {
                type int32 {
                  range "0..7";
                }
              } //dot1p-value

              leaf dot1p-mask {
                type string;
                description
                    "[0..7] - accepts in decimal hex or binary";
              } //dot1p-mask

            } //container dot1p

            container dsap {
              description
                  "Configure dsap match condition";
              leaf dsap-value {
                type string;
                description
                    "[0..255] - accepts in decimal hex or binary";
              } //dsap-value

              leaf dsap-mask {
                type string;
                description
                    "[0..255] - accepts in decimal hex or binary";
              } //dsap-mask

            } //container dsap

            container dst-mac {
              description
                  "Configure dest. mac match condition";
              leaf ieee-address {
                type alu:ieee-address;
                description
                    "xx:xx:xx:xx:xx:xx or xx-xx-xx-xx-xx-xx";
              } //ieee-address

              leaf ieee-address-mask {
                type string;
                description
                    "xx:xx:xx:xx:xx:xx or xx-xx-xx-xx-xx-xx";
              } //ieee-address-mask

            } //container dst-mac

            container etype {
              description
                  "Configure e-type match condition";
              leaf t0x0600..0xffff {
                type string;
                description
                    "[1536..65535] - accepts in decimal or hex";
              } //t0x0600..0xffff

            } //container etype

            container inner-tag {
              description
                  "Configure vid inner tag match condition";
              leaf value {
                type string;
                description
                    "[0..4095] decimal or [0x0..0xFFF] hex";
              } //value

              leaf vid-mask {
                type string;
                description
                    "[1..4095] decimal or [0x1..0xFFF] hex";
              } //vid-mask

            } //container inner-tag

            container isid {
              description
                  "Configure isid match condition";
              leaf value {
                type int32 {
                  range "0..16777215";
                }
              } //value

              leaf to {
                type int32 {
                  range "0..16777215";
                }
                description
                    "Used to specify a range of matching isid values";
              } //to

            } //container isid

            container outer-tag {
              description
                  "Configure vid outer tag match condition";
              leaf value {
                type string;
                description
                    "[0..4095] decimal or [0x0..0xFFF] hex";
              } //value

              leaf vid-mask {
                type string;
                description
                    "[1..4095] decimal or [0x1..0xFFF] hex";
              } //vid-mask

            } //container outer-tag

            container snap-oui {
              description
                  "Configure snap-oui match condition";
              leaf zero-non-zero {
                type enumeration {
                  enum zero;
                  enum non-zero;
                }
                description
                    "keywords - specify snap-oui value";
              } //zero-non-zero

            } //container snap-oui

            container snap-pid {
              description
                  "Configure snap-pid match condition";
              leaf snap-pid {
                type string;
                description
                    "[0..65535] - accepts in decimal or hex";
              } //snap-pid

            } //container snap-pid

            container src-mac {
              description
                  "Configure source mac match condition";
              leaf ieee-address {
                type alu:ieee-address;
                description
                    "xx:xx:xx:xx:xx:xx or xx-xx-xx-xx-xx-xx";
              } //ieee-address

              leaf ieee-address-mask {
                type string;
                description
                    "xx:xx:xx:xx:xx:xx or xx-xx-xx-xx-xx-xx";
              } //ieee-address-mask

            } //container src-mac

            container ssap {
              description
                  "Configure ssap match condition";
              leaf ssap-value {
                type string;
                description
                    "[0.255] - accepts in decimal hex or binary";
              } //ssap-value

              leaf ssap-mask {
                type string;
                description
                    "[0.255] - accepts in decimal hex or binary";
              } //ssap-mask

            } //container ssap

          } //container match

        } //list entry

      } //list mac-filter

      container match-list {
        description
            "Configure a match-list for use in a filter";
        list ip-prefix-list {
          key "ip-prefix-list-name";
          description
              "Configure an ip prefix list";
          leaf ip-prefix-list-name {
            type string {
              length "1..32";
            }
          } //ip-prefix-list-name

          container description {
            description
                "Description for this ip prefix list";
            leaf description-string {
              type string {
                length "1..80";
              }
            } //description-string

          } //container description

          list prefix {
            key "ip-prefix-prefix-length";
            description
                "Create/delete an entry in the ip prefix list";
            leaf ip-prefix-prefix-length {
              type inet:ip-prefix;
              description
                  "ip-prefix - a.b.c.d (host bits must be 0) 
                   prefix-length - [0..32] 
                   ";
            } //ip-prefix-prefix-length

          } //list prefix

          list prefix-exclude {
            key "ip-prefix-prefix-length";
            description
                "Create/delete an entry in the ip prefix list";
            leaf ip-prefix-prefix-length {
              type inet:ip-prefix;
              description
                  "ip-prefix-exclude - a.b.c.d (host bits must be 0) 
                   prefix-length - [0..32] 
                   ";
            } //ip-prefix-prefix-length

          } //list prefix-exclude

          container apply-path {
            presence
                "Configure auto-generated prefixes";
            list bgp-peers {
              key "criterion-index";
              description
                  "Configure BGP peers to be added to the prefix list";
              leaf criterion-index {
                type uint32 {
                  range "1..255";
                }
              } //criterion-index

              leaf router {
                type boolean;
              } //router

              leaf router-instance {
                type string {
                  length "1..32";
                }
                default "Base";
                description
                    "Attribute router-instance for bgp-peers";
              } //router-instance

              leaf service-name {
                type string;
              } //service-name

              leaf group {
                type string {
                  length "1..255";
                }
              } //group

              leaf neighbor {
                type string {
                  length "1..255";
                }
                description
                    "reg-exp";
              } //neighbor

            } //list bgp-peers

          } //container apply-path

        } //list ip-prefix-list

        list ipv6-prefix-list {
          key "ipv6-prefix-list-name";
          description
              "Configure an ipv6 prefix list";
          leaf ipv6-prefix-list-name {
            type string {
              length "1..32";
            }
          } //ipv6-prefix-list-name

          container description {
            description
                "Description for this ipv6 prefix list";
            leaf description-string {
              type string {
                length "1..80";
              }
            } //description-string

          } //container description

          list prefix {
            key "ipv6-prefix-prefix-length";
            description
                "Create/delete an entry in the ipv6 prefix list";
            leaf ipv6-prefix-prefix-length {
              type string;
              description
                  "ipv6-prefix x:x:x:x:x:x:x:x (eight 16-bit pieces) 
                   x:x:x:x:x:x:d.d.d.d 
                   x [0..FFFF]H 
                   d [0..255]D 
                   prefix-length [1..128]";
            } //ipv6-prefix-prefix-length

          } //list prefix

          list prefix-exclude {
            key "ipv6-prefix-prefix-length";
            description
                "Create/delete an entry in the ipv6 prefix list";
            leaf ipv6-prefix-prefix-length {
              type string;
              description
                  "ipv6-prefix-exclude x:x:x:x:x:x:x:x (eight 16-bit pieces) 
                   x:x:x:x:x:x:d.d.d.d 
                   x [0..FFFF]H 
                   d [0..255]D 
                   prefix-length [1..128]";
            } //ipv6-prefix-prefix-length

          } //list prefix-exclude

          container apply-path {
            presence
                "Configure auto-generated prefixes";
            list bgp-peers {
              key "criterion-index";
              description
                  "Configure BGP peers to be added to the prefix list";
              leaf criterion-index {
                type uint32 {
                  range "1..255";
                }
              } //criterion-index

              leaf router {
                type boolean;
              } //router

              leaf router-instance {
                type string {
                  length "1..32";
                }
                default "Base";
                description
                    "Attribute router-instance for bgp-peers";
              } //router-instance

              leaf service-name {
                type string;
              } //service-name

              leaf group {
                type string {
                  length "1..255";
                }
              } //group

              leaf neighbor {
                type string {
                  length "1..255";
                }
                description
                    "reg-exp";
              } //neighbor

            } //list bgp-peers

          } //container apply-path

        } //list ipv6-prefix-list

        list port-list {
          key "port-list-name";
          description
              "Configure a port list";
          leaf port-list-name {
            type string {
              length "1..32";
            }
          } //port-list-name

          container description {
            description
                "Description for this port list";
            leaf description-string {
              type string {
                length "1..80";
              }
            } //description-string

          } //container description

          container port {
            description
                "Create/delete a port (range) in the port list";
            leaf port-number {
              type string;
              description
                  "Attribute port-number for port";
            } //port-number

            leaf-list range {
              type string;
              max-elements 2;
              description
                  "port-number";
            } //range

          } //container port

        } //list port-list

        list protocol-list {
          key "protocol-list-name";
          description
              "Configure an ip protocol/next-header list";
          leaf protocol-list-name {
            type string {
              length "1..32";
            }
          } //protocol-list-name

          container description {
            description
                "Description for this protocol list";
            leaf description-string {
              type string {
                length "1..80";
              }
            } //description-string

          } //container description

          list protocol {
            key "protocol-id";
            description
                "Create/delete a protocol in the protocol list";
            leaf protocol-id {
              type string;
              description
                  "Attribute protocol-id for protocol";
            } //protocol-id

          } //list protocol

        } //list protocol-list

      } //container match-list

      container md-auto-id {
        description
            "Configure auto identifier ranges for model-driven CLI";
        container filter-id-range {
          description
              "Configure filter identifier range";
          leaf start {
            type uint32 {
              range "1..65535";
            }
          } //start

          leaf end {
            type uint32 {
              range "1..65535";
            }
          } //end

        } //container filter-id-range

      } //container md-auto-id

      list redirect-policy {
        key "redirect-policy-name";
        description
            "Configure a redirect-policy";
        leaf redirect-policy-name {
          type string {
            length "1..32";
          }
        } //redirect-policy-name

        container description {
          description
              "Description for this policy";
          leaf description-string {
            type string {
              length "1..80";
            }
          } //description-string

        } //container description

        leaf notify-dest-change {
          type boolean;
          description
              "Enable/disable sending of notification on active destination change";
        }

        container router {
          description
              "Configure router instance in which context destination reachability tests are 
               performed";
          leaf router-instance {
            type string {
              length "1..32";
            }
            description
                "Attribute router-instance for router";
          } //router-instance

          leaf service-name {
            type string;
          } //service-name

        } //container router

        leaf shutdown {
          type boolean;
          description
              "Administratively shut down this redirect policy";
        }

        container sticky-dest {
          description
              "Set stickiness of redirect-policy destinations and hold-time-up for stickiness 
               to take effect";
          leaf hold-time-up {
            type uint32 {
              range "0..65535";
            }
            description
                "0..65535 seconds";
          } //hold-time-up

          leaf no-hold-time-up {
            type boolean;
          } //no-hold-time-up

        } //container sticky-dest

        list destination {
          key "ip-address";
          description
              "Configure destinations within the redirect policy";
          leaf ip-address {
            type string;
            description
                "Attribute ip-address for destination";
          } //ip-address

          container description {
            description
                "Description for this destination";
            leaf description-string {
              type string {
                length "1..80";
              }
            } //description-string

          } //container description

          container priority {
            description
                "Configure the priority";
            leaf priority {
              type uint16 {
                range "1..255";
              }
            } //priority

          } //container priority

          leaf shutdown {
            type boolean;
            description
                "Administratively shut down this destination";
          }

          leaf unicast-rt-test {
            type boolean;
            description
                "Configure a unicast route test";
          }

          container ping-test {
            presence
                "Configure a ping-test";
            container drop-count {
              description
                  "Configure the drop-count";
              leaf consecutive-failures {
                type uint32 {
                  range "1..60";
                }
              } //consecutive-failures

              leaf hold-down {
                type uint32 {
                  range "0..86400";
                }
              } //hold-down

            } //container drop-count

            container interval {
              description
                  "Configure the interval";
              leaf seconds {
                type uint32 {
                  range "1..60";
                }
              } //seconds

            } //container interval

            container source-address {
              description
                  "Configure the source address used by the ping test";
              leaf ip-address {
                type string;
              } //ip-address

            } //container source-address

            container timeout {
              description
                  "Configure the timeout";
              leaf seconds {
                type uint32 {
                  range "1..60";
                }
              } //seconds

            } //container timeout

          } //container ping-test

          container snmp-test {
            status "obsolete";
            description
                "Configure a snmp-test";
            leaf test-name {
              type string {
                length "1..32";
              }
            } //test-name

            container drop-count {
              status "obsolete";
              description
                  "Configure the drop-count";
              leaf consecutive-failures {
                type uint32 {
                  range "1..60";
                }
              } //consecutive-failures

              leaf hold-down {
                type uint32 {
                  range "0..86400";
                }
              } //hold-down

            } //container drop-count

            container interval {
              status "obsolete";
              description
                  "Configure the interval";
              leaf seconds {
                type uint32 {
                  range "1..60";
                }
              } //seconds

            } //container interval

            container oid {
              status "obsolete";
              description
                  "Specify the OID to be requested";
              leaf oid-string {
                type string {
                }
                description
                    "[256 char max]";
              } //oid-string

              leaf community {
                type string {
                  length "1..32";
                }
              } //community

            } //container oid

            container return-value {
              status "obsolete";
              description
                  "Specify the action for the return value";
              leaf return-value {
                type string {
                }
                description
                    "[256 char max]";
              } //return-value

              leaf type {
                type enumeration {
                  enum integer;
                  enum unsigned;
                  enum string;
                  enum ip-address;
                  enum counter;
                  enum time-ticks;
                  enum opaque;
                }
              } //type

              leaf raise-priority {
                type uint16 {
                  range "1..255";
                }
              } //raise-priority

              leaf lower-priority {
                type uint16 {
                  range "1..255";
                }
              } //lower-priority

              leaf disable {
                type boolean;
                description
                    "keyword - disables the destination";
              } //disable

            } //container return-value

            container timeout {
              status "obsolete";
              description
                  "Configure the timeout";
              leaf seconds {
                type uint32 {
                  range "1..60";
                }
              } //seconds

            } //container timeout

          } //container snmp-test

          container url-test {
            status "obsolete";
            description
                "Configure a url-test";
            leaf test-name {
              type string {
                length "1..32";
              }
            } //test-name

            container drop-count {
              status "obsolete";
              description
                  "Configure the drop-count";
              leaf consecutive-failures {
                type uint32 {
                  range "1..60";
                }
              } //consecutive-failures

              leaf hold-down {
                type uint32 {
                  range "0..86400";
                }
              } //hold-down

            } //container drop-count

            container interval {
              status "obsolete";
              description
                  "Configure the interval";
              leaf seconds {
                type uint32 {
                  range "1..60";
                }
              } //seconds

            } //container interval

            container return-code {
              status "obsolete";
              description
                  "Specify the action for range of return codes";
              leaf-list return-code-1-return-code-2 {
                type uint32 {
                  range "1..4294967295";
                }
                max-elements 2;
                description
                    "return-code-1 [1..4294967295] 
                     return-code-2 [2..4294967295]";
              } //return-code-1-return-code-2

              leaf raise-priority {
                type uint16 {
                  range "1..255";
                }
              } //raise-priority

              leaf lower-priority {
                type uint16 {
                  range "1..255";
                }
              } //lower-priority

              leaf disable {
                type boolean;
                description
                    "keyword - disables the destination";
              } //disable

            } //container return-code

            container timeout {
              status "obsolete";
              description
                  "Configure the timeout";
              leaf seconds {
                type uint32 {
                  range "1..60";
                }
              } //seconds

            } //container timeout

            container url {
              status "obsolete";
              description
                  "The URL to be probed by this test";
              leaf url-string {
                type string {
                  length "1..255";
                }
              } //url-string

              leaf http-version {
                type string {
                  length "1..80";
                }
                description
                    "1.0|1.1";
              } //http-version

            } //container url

          } //container url-test

        } //list destination

      } //list redirect-policy

      list redirect-policy-binding {
        key "name";
        description
            "Configure a redirect-policy-binding";
        leaf name {
          type string;
        } //name

        container binding-operator {
          description
              "Set binding operator to use for evaluation of different redirect policies' 
               tests results";
          leaf binding-operator-id {
            type enumeration {
              enum and;
              enum or;
            }
          } //binding-operator-id

        } //container binding-operator

        list redirect-policy {
          key "redirect-policy-name destination";
          description
              "Add redirect policy destination to this binding";
          leaf redirect-policy-name {
            type string {
              length "1..32";
            }
          } //redirect-policy-name

          leaf destination {
            type string;
            description
                "Attribute ip-address for redirect-policy";
          } //destination

        } //list redirect-policy

      } //list redirect-policy-binding

      container system-filter {
        description
            "Configure active system filters";
        list ip {
          key "ip-filter-id";
          description
              "Select active IP system filter";
          leaf ip-filter-id {
            type string;
            description
                "Attribute ip-filter-id for ip";
          } //ip-filter-id

        } //list ip

        list ipv6 {
          key "ipv6-filter-id";
          description
              "Select active IPv6 system filter";
          leaf ipv6-filter-id {
            type string;
            description
                "Attribute ipv6-filter-id for ipv6";
          } //ipv6-filter-id

        } //list ipv6

      } //container system-filter

    } //container filter

  } //grouping alu-conf-filter-r13

} //module  alu-conf-filter-r13
