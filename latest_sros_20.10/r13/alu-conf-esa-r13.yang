module alu-conf-esa-r13 {
  yang-version "1";

  namespace "urn:alcatel-lucent.com:sros:ns:yang:conf-esa-r13";

  prefix "conf-esa-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure ESA parameters on SR OS based 
       routers. 
       
       Copyright 2014-2015 Alcatel-Lucent, 2016 Nokia. All rights reserved. 
       Reproduction of this document is authorized on the condition that the 
       foregoing copyright notice is included. 
       
       This alu-conf-esa-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-11-21";

  grouping alu-conf-esa-r13 {
    list esa {
      key "esa-id";
      description
          "Configure ESA parameters";
      leaf esa-id {
        type int32 {
          range "1..16";
        }
      } //esa-id

      container description {
        description
            "Description for this ESA";
        leaf description-string {
          type string {
            length "1..80";
          }
        } //description-string

      } //container description

      container host-port {
        description
            "Configure host-port IDs for this ESA";
        leaf port-id {
          type string {
            length "1..17";
          }
          description
              "Attribute port-id for host-port";
        } //port-id

        leaf port-id-1 {
          type string {
            length "1..17";
          }
        } //port-id-1

      } //container host-port

      leaf shutdown {
        type boolean;
        description
            "Administratively enable/disable this ESA";
      }

      list vm {
        key "vm-id";
        description
            "Configure VM parameters";
        leaf vm-id {
          type uint32 {
            range "1..4";
          }
        } //vm-id

        container cores {
          description
              "Configure core count for this VM";
          leaf core-count {
            type uint32 {
              range "0..128";
            }
          } //core-count

        } //container cores

        container description {
          description
              "Description for this VM";
          leaf description-string {
            type string {
              length "1..80";
            }
          } //description-string

        } //container description

        container host-port {
          description
              "Configure the host-port ID for this VM";
          leaf port-id {
            type string {
              length "1..17";
            }
          } //port-id

        } //container host-port

        container memory {
          description
              "Configure memory in GB for this VM";
          leaf memory-size {
            type uint32 {
              range "0..256";
            }
            description
                "[0..256] - memory size in GB";
          } //memory-size

        } //container memory

        leaf shutdown {
          type boolean;
          description
              "Administratively enable/disable this VM";
        }

        container vm-type {
          description
              "Configure vm-type for this VM";
          leaf vm-type {
            type enumeration {
              enum aa;
              enum bb;
              enum tunnel;
            }
            description
                "Attribute vm-type for vm-type";
          } //vm-type

        } //container vm-type

      } //list vm

    } //list esa

  } //grouping alu-conf-esa-r13

} //module  alu-conf-esa-r13
