module alu-conf-macsec-r13 {
  yang-version "1";

  namespace "urn:alcatel-lucent.com:sros:ns:yang:conf-macsec-r13";

  prefix "conf-macsec-r13";

  import alu-types {
    prefix "alu";
  }
  import ietf-yang-types {
    prefix "yang";
  }

  alu:alu-major-release "rel20";

  organization "Alcatel-Lucent";

  contact
      "Alcatel-Lucent SR OS Support 
       Web: <http://www.alcatel-lucent.com>";

  description
      "Alcatel-Lucent YANG Data model to configure MACsec parameters on SR OS based 
       routers. 
       
       Copyright 2014-2015 Alcatel-Lucent, 2016 Nokia. All rights reserved. 
       Reproduction of this document is authorized on the condition that the 
       foregoing copyright notice is included. 
       
       This alu-conf-macsec-r13 YANG module embodies Alcatel-Lucent's proprietary 
       intellectual property. Alcatel-Lucent retains all title and ownership in the 
       Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2020-07-27";

  grouping alu-conf-macsec-r13 {
    container macsec {
      description
          "Configure MACsec parameters";
      list connectivity-association {
        key "ca-name";
        description
            "Configure a connectivity association";
        leaf ca-name {
          type string {
            length "1..32";
          }
          description
              "The name of the connectivity association";
        } //ca-name

        container cipher-suite {
          description
              "Configure the cipher suite";
          leaf cipher-suite {
            type enumeration {
              enum gcm-aes-128;
              enum gcm-aes-256;
              enum gcm-aes-xpn-128;
              enum gcm-aes-xpn-256;
            }
            description
                "[gcm-aes-128|gcm-aes-256| 
                 gcm-aes-xpn-128|gcm-aes-xpn-256]";
          } //cipher-suite

        } //container cipher-suite

        container clear-tag-mode {
          description
              "Enables or disables clear tag mode";
          leaf clear-tag-mode {
            type enumeration {
              enum single-tag;
              enum dual-tag;
            }
          } //clear-tag-mode

        } //container clear-tag-mode

        leaf delay-protection {
          type boolean;
          description
              "Configure data delay protection for this connectivity association";
        }

        container description {
          description
              "Description for this connectivity association";
          leaf description-string {
            type string {
              length "1..80";
            }
          } //description-string

        } //container description

        container encryption-offset {
          description
              "Configure the encryption offset";
          leaf encryption-offset {
            type enumeration {
              enum 0;
              enum 30;
              enum 50;
            }
            default 0;
            description
                "[0|30|50] - default: 0";
          } //encryption-offset

        } //container encryption-offset

        leaf macsec-encrypt {
          type boolean;
          description
              "Enable or disable PDU encryption";
        }

        leaf replay-protection {
          type boolean;
          description
              "Enable or disable replay protection";
        }

        container replay-window-size {
          description
              "Configure the size of the replay protection window";
          leaf number-of-packets {
            type uint32 {
              range "0..4294967294";
            }
            default 0;
            description
                "[0..4294967294] - default : 0";
          } //number-of-packets

        } //container replay-window-size

        leaf shutdown {
          type boolean;
          description
              "Administratively enable/disable MACsec";
        }

        container static-cak {
          presence
              "Configure static CAK settings";
          container active-psk {
            description
                "Configure the active pre-shared-key";
            leaf active-pre-shared-key {
              type uint32 {
                range "1..2";
              }
              default 1;
              description
                  "[1..2] - default : 1";
            } //active-pre-shared-key

          } //container active-psk

          container mka-hello-interval {
            description
                "Configure the MKA hello interval";
            leaf mka-hello-interval {
              type enumeration {
                enum 500ms;
                enum 1;
                enum 2;
                enum 3;
                enum 4;
                enum 5;
                enum 6;
              }
              description
                  "[1..6 | 500ms] - default 2 seconds";
            } //mka-hello-interval

          } //container mka-hello-interval

          container mka-key-server-priority {
            description
                "Configure the key server priority";
            leaf key-server-priority {
              type uint32 {
                range "0..255";
              }
              default 16;
              description
                  "[0..255] - default: 16";
            } //key-server-priority

          } //container mka-key-server-priority

          list pre-shared-key {
            key "pre-shared-key-index";
            description
                "Configure a pre-shared-key";
            leaf pre-shared-key-index {
              type uint32 {
                range "1..2";
              }
              description
                  "[1..2]";
            } //pre-shared-key-index

            leaf encryption-type {
              type enumeration {
                enum aes-128-cmac;
                enum aes-256-cmac;
              }
            } //encryption-type

            container cak {
              description
                  "Configure the cak for this pre-shared-key";
              leaf hex-string {
                type string {
                  length "1..500";
                }
                description
                    "32 hex characters for aes-128-cmac 
                     64 hex characters for aes-256-cmac";
              } //hex-string

              leaf hash-hash2-custom {
                type enumeration {
                  enum hash;
                  enum hash2;
                  enum custom;
                }
                description
                    "keywords - specify hashing scheme";
              } //hash-hash2-custom

            } //container cak

            container ckn {
              description
                  "Configure the ckn for this pre-shared-key";
              leaf hex-string {
                type string {
                  length "1..64";
                }
              } //hex-string

            } //container ckn

          } //list pre-shared-key

        } //container static-cak

      } //list connectivity-association

      list mac-policy {
        key "mac-policy-id";
        description
            "Configure mac address policy groups";
        leaf mac-policy-id {
          type uint32 {
            range "1..1024";
          }
        } //mac-policy-id

        list dest-mac-address {
          key "mac-address";
          description
              "Configure a destination mac address under this policy";
          leaf mac-address {
            type yang:mac-address;
          } //mac-address

        } //list dest-mac-address

      } //list mac-policy

    } //container macsec

  } //grouping alu-conf-macsec-r13

} //module  alu-conf-macsec-r13
