module alu-conf-svc-vprn-ntp-r13 {
  yang-version "1";

  namespace "urn:alcatel-lucent.com:sros:ns:yang:conf-svc-vprn-ntp-r13";

  prefix "conf-svc-vprn-ntp-r13";

  import alu-types {
    prefix "alu";
  }

  alu:alu-major-release "rel20";

  organization "Alcatel-Lucent";

  contact
      "Alcatel-Lucent SR OS Support 
       Web: <http://www.alcatel-lucent.com>";

  description
      "Alcatel-Lucent YANG Data model to configure parameters for NTP protocol for 
       VPRN services on SR OS based routers. 
       
       Copyright 2014-2015 Alcatel-Lucent, 2016 Nokia. All rights reserved. 
       Reproduction of this document is authorized on the condition that the 
       foregoing copyright notice is included. 
       
       This alu-conf-svc-vprn-ntp-r13 YANG module embodies Alcatel-Lucent's 
       proprietary intellectual property. Alcatel-Lucent retains all title and 
       ownership in the Specification, including any revisions. 
       
       Alcatel-Lucent grants all interested parties a non-exclusive license to use 
       and distribute an unmodified copy of this Specification in connection with 
       management of Alcatel-Lucent products, and without fee, provided this 
       copyright notice and license appear on all copies. 
       
       This Specification is supplied `as is', and Alcatel-Lucent makes no warranty, 
       either express or implied, as to the use, operation, condition, or performance 
       of the Specification.";

  revision  "2019-08-08";

  grouping alu-conf-svc-vprn-ntp-r13 {
    container ntp {
      presence
          "Configure parameters for NTP protocol for VPRN services";
      leaf authenticate {
        type boolean;
        description
            "Enable/Disable authentication for the NTP server";
      }

      leaf authentication-check {
        type boolean;
        description
            "Configure the option to skip the rejection of NTP PDUs";
      }

      list authentication-key {
        key "key-id";
        description
            "Configure the authentication key and type used to verify NTP PDUs";
        leaf key-id {
          type uint16 {
            range "1..255";
          }
        } //key-id

        leaf key {
          type string {
            length "1..500";
          }
          description
              "Max 32 chars";
        } //key

        leaf hash-hash2-custom {
          type enumeration {
            enum hash;
            enum hash2;
            enum custom;
          }
          description
              "keyword";
        } //hash-hash2-custom

        leaf type {
          type enumeration {
            enum des;
            enum message-digest;
          }
        } //type

      } //list authentication-key

      list broadcast {
        key "interface";
        description
            "Configure an interface to transmit NTP broadcast PDUs";
        leaf interface {
          type string {
            length "1..32";
          }
          description
              "Max 32 chars";
        } //interface

        leaf key-id {
          type uint16 {
            range "1..255";
          }
        } //key-id

        leaf version {
          type int32 {
            range "2..4";
          }
        } //version

        leaf ttl {
          type uint8 {
            range "1..255";
          }
          description
              "[1..255]";
        } //ttl

      } //list broadcast

      leaf shutdown {
        type boolean;
        description
            "Enable/disable NTP protocol execution";
      }

    } //container ntp

  } //grouping alu-conf-svc-vprn-ntp-r13

} //module  alu-conf-svc-vprn-ntp-r13
